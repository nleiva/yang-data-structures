/*
 * Copyright (c) 2024 Juniper Networks, Inc.
 * All rights reserved.
 */
 module junos-conf-routing-instances {
   namespace "http://yang.juniper.net/junos/conf/routing-instances";

   prefix jc-routing-instances;

   import junos-common-types {
     prefix jt;
     revision-date 2023-01-01;
   }

   import junos-conf-root {
     prefix jc;
     revision-date 2023-01-01;
   }

   organization "Juniper Networks, Inc.";

   contact "yang-support@juniper.net";

   description "Junos routing-instances configuration module";

   revision 2023-01-01 {
     description "Junos: 23.4R2.13";
   }

   augment /jc:configuration {
     uses routing-instances-group;
   }
  //  augment /jc:configuration/jc:groups {
  //    uses routing-instances-group;
  //  }
   grouping routing-instances-group {
     container routing-instances {
       description "Routing instance configuration";
       // uses apply-advanced;
       list instance {
         key name;
         uses juniper-routing-instance;
       }
     }
   }
  //  grouping apply-advanced {
  //    description "Apply advanced configuration logic";
  //    leaf-list apply-groups {
  //      ordered-by user;
  //      description "Groups from which to inherit configuration data";
  //      type string;
  //    }
  //    leaf-list apply-groups-except {
  //      ordered-by user;
  //      description "Don't inherit configuration data from these groups";
  //      type string;
  //    }
  //   //  list apply-macro {
  //   //    key name;
  //   //    ordered-by user;
  //   //    description "Macro and parameters for commit script expansion";
  //   //    uses apply-macro-type;
  //   //  }
  //  }
  //  grouping apply-macro-type {
  //    description "Macro data for commit-script expansion";
  //    leaf name {
  //      description "Name of the macro to be expanded";
  //      type string;
  //    }
  //    list data {
  //      key name;
  //      uses macro-data-type;
  //    }
  //  }
   grouping juniper-routing-instance {
     description "Routing instance";
     leaf name {
       description "Routing instance name";
       type string {
       }
     }
     // uses apply-advanced;
     leaf instance-type {
       description "Type of routing instance";
       type enumeration {
        //  enum "virtual-switch" {
        //    description "Virtual switch routing instance";
        //  }
        //  enum "layer2-control" {
        //    description "Layer 2 control protocols";
        //  }
        //  enum "mac-vrf" {
        //    description "MAC-VRF routing instance";
        //  }
         enum "forwarding" {
           description "Forwarding instance";
         }
         enum "no-forwarding" {
           description "Nonforwarding instance";
         }
        //  enum "l2vpn" {
        //    description "Layer 2 VPN routing instance";
        //  }
        //  enum "vpls" {
        //    description "VPLS routing instance";
        //  }
         enum "virtual-router" {
           description "Virtual routing instance";
         }
        //  enum "l2backhaul-vpn" {
        //    description "L2Backhaul/L2Wholesale routing instance";
        //  }
        //  enum "mpls-internet-multicast" {
        //    description "Internet Multicast over MPLS routing instance";
        //  }
        //  enum "evpn" {
        //    description "EVPN routing instance";
        //  }
         enum "mpls-forwarding" {
           description "Routing instance provides a MPLS forwarding-context";
         }
        //  enum "evpn-vpws" {
        //    description "EVPN VPWS routing instance";
        //  }
         enum "vrf" {
           description "Virtual routing forwarding instance";
         }
       }
     }
    //  container l2vpn-id {
    //    description "Layer-2 vpn-id for this instance";
    //    // uses apply-advanced;
    //    leaf community {
    //      description "L2VPN ID community for FEC129 VPLS/VPWS with BGP auto-discovery";
    //      type string {
    //      }
    //    }
    //  }
     container routing-options {
       description "Protocol-independent routing option configuration";
       uses juniper-routing-options;
     }
    //  container egress-protection {
    //    description "Egress instance protection";
    //    // uses apply-advanced;
    //    leaf protector {
    //      description "Enable Edge Protector functionality for this VPN";
    //      type empty;
    //    }
    //    container context-identifier {
    //      description "Context identifier";
    //      // uses apply-advanced;
    //      leaf context-id {
    //        description "IP address";
    //        type jt:ipv4addr;
    //      }
    //    }
    //  }
     container protocols {
       description "Routing protocol configuration";
       // uses apply-advanced;
       container bfd {
         presence "enable bfd";
         uses juniper-ri-protocols-bfd;
       }
      //  container igmp-snooping {
      //    description "IGMP snooping configuration";
      //    presence "enable igmp-snooping";
      //    uses juniper-ri-protocols-igmp-snooping;
      //  }
      //  container mld-snooping {
      //    description "MLD snooping configuration";
      //    presence "enable mld-snooping";
      //    uses juniper-ri-protocols-mld-snooping;
      //  }
      //  container amt {
      //    description "AMT relay configuration";
      //    uses juniper-protocols-amt;
      //  }
       container bgp {
         description "BGP options";
         uses juniper-protocols-bgp;
       }
      //  container esis {
      //    description "ES-IS configuration";
      //    uses juniper-protocols-esis;
      //  }
      //  container evpn {
      //    description "EVPN configuration";
      //    presence "enable evpn";
      //    uses juniper-protocols-l2vpn;
      //  }
      //  container router-discovery {
      //    description "ICMP router discovery options";
      //    uses juniper-protocols-router-discovery;
      //  }
      //  container isis {
      //    description "IS-IS configuration";
      //    uses juniper-protocols-isis;
      //  }
      //  container l2vpn {
      //    description "Layer 2 VPN configuration";
      //    uses juniper-protocols-l2vpn;
      //  }
      //  container vpls {
      //    description "VPLS configuration";
      //    presence "enable vpls";
      //    uses juniper-protocols-l2vpn;
      //  }
       container ldp {
         description "LDP configuration";
         uses juniper-protocols-ldp;
       }
       container mpls {
         description "MPLS configuration";
         uses juniper-protocols-mpls;
       }
      //  container msdp {
      //    description "MSDP configuration";
      //    uses juniper-protocols-msdp;
      //  }
      //  container mvpn {
      //    description "BGP-MVPN configuration";
      //    presence "enable mvpn";
      //    uses juniper-protocols-mvpn;
      //  }
       container ospf {
         description "OSPF configuration";
         uses juniper-protocols-ospf;
       }
      //  container ospf3 {
      //    description "OSPF3 configuration";
      //    uses juniper-protocols-ospf3;
      //  }
      //  container pim {
      //    description "PIM configuration";
      //    uses juniper-protocols-pim;
      //  }
      //  container ripng {
      //    description "RIPng options";
      //    uses juniper-protocols-ripng;
      //  }
      //  container rip {
      //    description "RIP options";
      //    uses juniper-protocols-rip;
      //  }
      //  container rsvp {
      //    description "RSVP configuration";
      //    uses juniper-protocols-rsvp;
      //  }
      //  container pim-snooping {
      //    description "PIM snooping configuration";
      //    presence "enable pim-snooping";
      //    uses juniper-protocols-pim-snooping;
      //  }
      //  container rstp {
      //    description "RSTP configuration";
      //    uses juniper-protocols-stp;
      //  }
      //  container mstp {
      //    description "MSTP configuration";
      //    uses juniper-protocols-mstp;
      //  }
      //  container vstp {
      //    description "VSTP configuration";
      //    uses juniper-protocols-vstp;
      //  }
      //  container mvrp {
      //    description "MVRP configuration";
      //    uses juniper-protocols-mvrp;
      //  }
     }
     leaf description {
       description "Text description of routing instance";
       type string {
       }
     }
    //  leaf vlan-model {
    //    description "Subscriber vlan-model in L2Wholesale framework";
    //    type enumeration {
    //      enum "one-to-one" {
    //        description "Customer VLAN model (1:1)";
    //      }
    //    }
    //  }
    //  container vtep-source-interface {
    //    description "Source layer-3 IFL for VXLAN";
    //    leaf interface-name {
    //      type union {
    //        type jt:interface-name;
    //        type string {
    //          pattern "<.*>|$.*";
    //        }
    //      }
    //    }
    //    choice family {
    //      case case_1 {
    //        container inet {
    //          presence "enable inet";
    //          description "IPv4 source";
    //          // uses apply-advanced;
    //          choice address {
    //            case case_1 {
    //              container evpn-mpls-encap {
    //                presence "enable evpn-mpls-encap";
    //                description "EVPN MPLS/VXLAN stitching";
    //                // uses apply-advanced;
    //                leaf vxlan-source-ip {
    //                  description "Source IP in outer header of vxlan packet";
    //                  type jt:ipv4addr;
    //                }
    //              }
    //            }
    //          }
    //        }
    //      }
    //      case case_2 {
    //        container inet6 {
    //          presence "enable inet6";
    //          description "IPv6 source";
    //          // uses apply-advanced;
    //        }
    //      }
    //    }
    //  }
    //  container vtep-remote-interface {
    //    description "Remote VTEP interface";
    //    // uses apply-advanced;
    //    list remote-ip {
    //      key name;
    //      ordered-by user;
    //      description "Remote VTEP IP address";
    //      leaf name {
    //        description "IP address";
    //        type jt:ipv4addr;
    //      }
    //      // uses apply-advanced;
    //      leaf dynamic-profile {
    //        description "Define associate dynamic profile";
    //        type string;
    //      }
    //    }
    //    container default {
    //      description "To all remote vtep interface";
    //      // uses apply-advanced;
    //      leaf dynamic-profile {
    //        description "Define associate dynamic profile";
    //        type string;
    //      }
    //    }
    //  }
    //  leaf-list remote-vtep-list {
    //    description "Configure static remote VXLAN tunnel endpoints";
    //    type jt:ipaddr;
    //    max-elements 1024;
    //  }
    //  leaf-list remote-vtep-v6-list {
    //    description "Configurate static ipv6 remote VXLAN tunnel endpoints";
    //    type jt:ipv6addr;
    //    max-elements 1024;
    //  }
    //  leaf instance-role {
    //    description "Primary role of L2Backhaul-vpn router";
    //    type enumeration {
    //      enum "access" {
    //        description "Role of Access/Aggregation router";
    //      }
    //      enum "nni" {
    //        description "Role of Provider network interfacing router";
    //      }
    //    }
    //  }
    //  choice vlan_choice {
    //    case case_1 {
    //      leaf vlan-id {
    //        description "IEEE 802.1q VLAN identifier for bridging domain";
    //        type string;
    //      }
    //    }
    //    case case_2 {
    //      container vlan-tags {
    //        presence "enable vlan-tags";
    //        description "IEEE 802.1q VLAN tags for bridging domain";
    //        leaf outer {
    //          description "[tpid.]vlan-id, tpid format is 0xNNNN and is optional";
    //          type string {
    //          }
    //        }
    //        leaf inner {
    //          description "[tpid.]vlan-id, tpid format is 0xNNNN and is optional";
    //          type string {
    //          }
    //        }
    //      }
    //    }
    //  }
    //  container system {
    //    description "System parameters";
    //    // uses apply-advanced;
    //    container services {
    //      description "System services";
    //      // uses apply-advanced;
    //      container dhcp-local-server {
    //        description "Dynamic Host Configuration Protocol server configuration";
    //        uses jdhcp-local-server-type;
    //      }
    //      container dhcp-proxy-client {
    //        description "Dynamic Host Configuration Protocol Proxy client configuration";
    //        uses jdhcp-proxy-client-type;
    //      }
    //      container static-subscribers {
    //        description "Static Subscriber Client configuration";
    //        uses jsscd-static-subscribers-type;
    //      }
    //      container remote-device-management {
    //        description "Remote device management configuration";
    //        // uses apply-advanced;
    //        list service-device {
    //          key name;
    //          description "Service device configuraiton";
    //          uses service-device-object;
    //        }
    //      }
    //      container tcp-forwarding {
    //        description "TCP forwarding configuration";
    //        // uses apply-advanced;
    //        list listening-port {
    //          key "port-number listening-address";
    //          ordered-by user;
    //          description "TCP listener configuration";
    //          leaf port-number {
    //            description "Listening port";
    //            type union {
    //              type string {
    //                pattern "<.*>|$.*";
    //              }
    //              type uint16 {
    //                range "8000 .. 8063";
    //              }
    //            }
    //          }
    //          leaf listening-address {
    //            description "Listening address";
    //            type jt:ipv4addr;
    //          }
    //          // uses apply-advanced;
    //          leaf forwarding-address {
    //            description "Forwarding address";
    //            type jt:ipv4addr;
    //          }
    //          leaf forwarding-port {
    //            description "Forwarding port";
    //            type union {
    //              type string {
    //                pattern "<.*>|$.*";
    //              }
    //              type uint16 {
    //                range "1 .. 65535";
    //              }
    //            }
    //          }
    //          leaf max-connections {
    //            description "Maxmimum allowed connections";
    //            type union {
    //              type string {
    //                pattern "<.*>|$.*";
    //              }
    //              type uint16 {
    //                range "1 .. 16";
    //              }
    //            }
    //          }
    //          list allowed-source {
    //            key name;
    //            ordered-by user;
    //            description "Allowed source prefix";
    //            leaf name {
    //              description "Source prefix";
    //              type jt:ipv4prefix;
    //            }
    //            // uses apply-advanced;
    //          }
    //        }
    //      }
    //    }
    //  }
    //  container access {
    //    description "Network access configuration";
    //    // uses apply-advanced;
    //    container address-assignment {
    //      description "Address assignment configuration";
    //      uses address-assignment-type;
    //    }
    //    container address-protection {
    //      presence "enable address-protection";
    //      description "Initiate Duplicate Address Protection";
    //      // uses apply-advanced;
    //      leaf reassign-on-match {
    //        description "Disconnect owning session and reassign to this session";
    //        type empty;
    //      }
    //    }
    //  }
    //  container access-profile {
    //    description "Access profile for this instance";
    //    leaf access-profile-name {
    //      description "Profile name";
    //      type string;
    //    }
    //  }
     leaf routing-interface {
       description "Routing interface name for this routing-instance";
       type union {
         type jt:interface-unit;
         type string {
           pattern "<.*>|$.*";
         }
       }
     }
    //  container vxlan {
    //    description "VXLAN options";
    //    // uses apply-advanced;
    //    leaf ovsdb-managed {
    //      description "Managed remotely via VXLAN OVSDB Controller";
    //      type empty;
    //    }
    //    leaf vni {
    //      description "VXLAN identifier";
    //      type union {
    //        type string {
    //          pattern "<.*>|$.*";
    //        }
    //        type uint32 {
    //          range "0 .. 16777214";
    //        }
    //      }
    //    }
    //    leaf translation-vni {
    //      description "Translated VXLAN identifier";
    //      type union {
    //        type string {
    //          pattern "<.*>|$.*";
    //        }
    //        type uint32 {
    //          range "1 .. 16777214";
    //        }
    //      }
    //    }
    //    leaf multicast-group {
    //      description "Multicast group registered for VXLAN segment";
    //      type jt:ipv4addr;
    //    }
    //    leaf multicast-v6-group {
    //      description "Multicast IPv6 group registered for VXLAN segment";
    //      type jt:ipv6addr;
    //    }
    //    leaf encapsulate-inner-vlan {
    //      description "Retain inner VLAN in the packet";
    //      type empty;
    //    }
    //    leaf decapsulate-accept-inner-vlan {
    //      description "Accept VXLAN packets with inner VLAN";
    //      type empty;
    //    }
    //    leaf unreachable-vtep-aging-timer {
    //      description "Unreachable VXLAN tunnel endpoint removal timer";
    //      units "seconds";
    //      type union {
    //        type string {
    //          pattern "<.*>|$.*";
    //        }
    //        type uint16 {
    //          range "300 .. 1800";
    //        }
    //      }
    //    }
    //    leaf destination-udp-port {
    //      description "VXLAN destination UDP port";
    //      default "4789";
    //      type union {
    //        type string {
    //          pattern "<.*>|$.*";
    //        }
    //        type uint16 {
    //          range "4789 .. 65535";
    //        }
    //      }
    //    }
    //    leaf ingress-node-replication {
    //      description "Enable ingress node replication";
    //      type empty;
    //    }
    //  }
     leaf l3-interface {
       description "L3 interface name for this routing-instance";
       type union {
         type jt:interface-unit;
         type string {
           pattern "<.*>|$.*";
         }
       }
     }
    //  leaf no-local-switching {
    //    description "Disable local switching within CE-facing interfaces";
    //    type empty;
    //  }
    //  leaf no-normalization {
    //    description "Disable vlan id normalization for interfaces";
    //    type empty;
    //  }
    //  leaf qualified-bum-pruning-mode {
    //    description "Enable BUM pruning for VPLS instance";
    //    type empty;
    //  }
    //  leaf no-irb-layer-2-copy {
    //    description "Disable transmission of layer-2 copy of packets of irb routing-interface";
    //    type empty;
    //  }
    //  leaf connector-id-advertise {
    //    description "Advertise connector-id attribute";
    //    type empty;
    //  }
    //  container forwarding-options {
    //    description "Forwarding options configuration";
    //    uses juniper-forwarding-options;
    //  }
    //  container bridge-domains {
    //    description "Bridge domain configuration";
    //    // uses apply-advanced;
    //    list domain {
    //      key name;
    //      uses juniper-bridge-domains;
    //    }
    //  }
    //  container switch-options {
    //    description "L2 options for routing-instance of type virtual-switch";
    //    uses juniper-routing-instance-switch-options;
    //  }
    //  container pbb-options {
    //    description "Provider backbone bridging options for routing-instance";
    //    uses juniper-routing-instance-pbb-options;
    //  }
    //  list service-groups {
    //    key name;
    //    description "Service group configuration for routing-instance";
    //    uses juniper-routing-instance-service-groups;
    //  }
    //  leaf layer3-domain-identifier {
    //    description "Layer3 domain identifier";
    //    type union {
    //      type string {
    //        pattern "<.*>|$.*";
    //      }
    //      type uint32 {
    //        range "2 .. 8192";
    //      }
    //    }
    //  }
    //  leaf l2-domain-id-for-l3 {
    //    description "Layer2 domain identifier for L3";
    //    type union {
    //      type string {
    //        pattern "<.*>|$.*";
    //      }
    //      type uint32 {
    //        range "2 .. 4095";
    //      }
    //    }
    //  }
     container forwarding-instance {
       description "Forwarding instance parameters for a mac-vrf instance";
       leaf identifier {
         description "Forwarding instance identifier";
         type union {
           type string {
             pattern "<.*>|$.*";
           }
           type uint32 {
             range "1 .. 99";
           }
         }
       }
     }
    //  leaf service-type {
    //    description "Sevice type";
    //    type enumeration {
    //      enum "vlan-based" {
    //        description "Instance service type vlan-based";
    //      }
    //      enum "vlan-bundle" {
    //        description "Instance service type vlan-bundle";
    //      }
    //      enum "vlan-aware" {
    //        description "Instance service type vlan-aware";
    //      }
    //    }
    //  }
     list interface {
       key name;
       description "Interface name for this routing instance";
       leaf name {
         type string;
       }
       // uses apply-advanced;
       choice mode {
         case case_1 {
           leaf any {
             description "Interface used for both unicast and multicast traffic";
             type empty;
           }
         }
         case case_2 {
           leaf unicast {
             description "Interface used for unicast traffic only";
             type empty;
           }
         }
         case case_3 {
           leaf multicast {
             description "Interface used for multicast traffic only";
             type empty;
           }
         }
       }
       leaf primary {
         description "Preferred multicast vt interface for the routing-instance";
         type empty;
       }
       leaf protect-interface {
         description "Name of protect interface";
         type union {
           type jt:interface-name;
           type string {
             pattern "<.*>|$.*";
           }
         }
       }
     }
     container route-distinguisher {
       description "Route distinguisher for this instance";
       leaf rd-type {
         description "Number in (16 bit:32 bit) or (32 bit 'L':16 bit) or (IP address:16 bit) format";
         type string {
         }
       }
     }
     leaf-list vrf-import {
       ordered-by user;
       description "Import policy for VRF instance RIBs";
       type jt:policy-algebra;
     }
     leaf-list vrf-export {
       ordered-by user;
       description "Export policy for VRF instance RIBs";
       type jt:policy-algebra;
     }
     leaf export-default-action {
       description "Default action for export in routing-instance";
       type enumeration {
         enum "accept" {
           description "Default action is accept";
         }
         enum "reject" {
           description "Default action is reject";
         }
       }
     }
     leaf import-default-action {
       description "Default action for import in routing-instance";
       type enumeration {
         enum "accept" {
           description "Default action is accept";
         }
         enum "reject" {
           description "Default action is reject";
         }
       }
     }
     container vrf-target {
       description "VRF target community configuration";
       // uses apply-advanced;
       leaf community {
         description "Target community to use in import and export";
         type string {
         }
       }
       leaf import {
         description "Target community to use when filtering on import";
         type string {
         }
       }
       leaf export {
         description "Target community to use when marking routes on export";
         type string {
         }
       }
       leaf auto {
         description "Auto derive import and export target community from BGP AS & L2";
         type empty;
       }
     }
     leaf no-vrf-advertise {
       description "Don't advertise this instance to remote PEs";
       type empty;
     }
     leaf non-forwarding-vrf {
       description "Don't create VRF forwarding table for local or transit routes belonging to this VPN";
       type empty;
     }
     container vrf-advertise-selective {
       presence "enable vrf-advertise-selective";
       description "Override no-vrf-advertise knob for the specified address family";
       // uses apply-advanced;
       container family {
         description "Protocol family to be selectively advertised";
         // uses apply-advanced;
         leaf inet-mvpn {
           description "IPv4 MVPN Address Family";
           type empty;
         }
         leaf inet6-mvpn {
           description "IPv6 MVPN Address Family";
           type empty;
         }
       }
     }
     container vrf-table-label {
       presence "enable vrf-table-label";
       description "Advertise a single VPN label for all routes in the VRF";
       leaf static {
         description "Specify label value to be used";
         type union {
           type string {
             pattern "<.*>|$.*";
           }
           type uint32 {
             range "16 .. 1048575";
           }
         }
       }
       leaf source-class-usage {
         description "Enable source class usage";
         type empty;
       }
     }
     choice vrf-propagate-ttl-or-no-vrf-propagate-ttl {
       case case_1 {
         leaf no-vrf-propagate-ttl {
           description "Disable TTL propagation from IP to MPLS (on push) and MPLS to IP (on pop)";
           type empty;
         }
       }
       case case_2 {
         leaf vrf-propagate-ttl {
           description "Enable TTL propagation from IP to MPLS (on push) and MPLS to IP (on pop)";
           type empty;
         }
       }
     }
    //  container provider-tunnel {
    //    description "Provider tunnel configuration";
    //    // uses apply-advanced;
    //    container external-controller {
    //      description "External point-to-multipoint LSP provider for flooding";
    //      // uses apply-advanced;
    //      choice external-provider {
    //        case case_1 {
    //          leaf pccd {
    //            description "Use PCCD for external point-to-multipoint LSP computation entity";
    //            type empty;
    //          }
    //        }
    //      }
    //    }
    //    choice tunnel-type {
    //      case case_1 {
    //        container rsvp-te {
    //          description "RSVP-TE point-to-multipoint LSP for flooding";
    //          // uses apply-advanced;
    //          choice static-or-dynamic {
    //            case case_1 {
    //              leaf static-lsp {
    //                description "Name of point-to-multipoint LSP";
    //                type string {
    //                }
    //              }
    //            }
    //            case case_2 {
    //              container label-switched-path-template {
    //                description "Template for dynamic point-to-multipoint LSP parameters";
    //                // uses apply-advanced;
    //                choice dynamic-template {
    //                  case case_1 {
    //                    leaf template-name {
    //                      description "Name of point-to-multipoint LSP template";
    //                      type string {
    //                      }
    //                    }
    //                  }
    //                  case case_2 {
    //                    leaf default-template {
    //                      description "Use default parameters";
    //                      type empty;
    //                    }
    //                  }
    //                }
    //              }
    //            }
    //          }
    //        }
    //      }
    //      case case_2 {
    //        container ldp-p2mp {
    //          presence "enable ldp-p2mp";
    //          description "LDP point-to-multipoint LSP for flooding";
    //        }
    //      }
    //      case case_3 {
    //        container ingress-replication {
    //          description "Ingress replication tunnel";
    //          // uses apply-advanced;
    //          leaf create-new-ucast-tunnel {
    //            description "Create new unicast tunnel for ingress replication";
    //            type empty;
    //          }
    //          container label-switched-path {
    //            presence "enable label-switched-path";
    //            description "Point-to-point LSP unicast tunnel";
    //            // uses apply-advanced;
    //            container label-switched-path-template {
    //              description "Template for dynamic point-to-point LSP parameters";
    //              // uses apply-advanced;
    //              choice dynamic-template {
    //                case case_1 {
    //                  leaf template-name {
    //                    description "Name of point-to-point LSP template";
    //                    type string {
    //                    }
    //                  }
    //                }
    //                case case_2 {
    //                  leaf default-template {
    //                    description "Use default parameters";
    //                    type empty;
    //                  }
    //                }
    //              }
    //            }
    //          }
    //        }
    //      }
    //      case case_4 {
    //        container bier {
    //          presence "enable bier";
    //          description "Use BIER for multicast forwarding";
    //          // uses apply-advanced;
    //          leaf subdomain-id {
    //            description "SubDomain ID";
    //            type union {
    //              type uint8;
    //              type string {
    //                pattern "<.*>|$.*";
    //              }
    //            }
    //          }
    //          leaf label {
    //            description "Domain-wide unique label for the tunnel";
    //            type union {
    //              type string {
    //                pattern "<.*>|$.*";
    //              }
    //              type uint32 {
    //                range "16 .. 1048575";
    //              }
    //            }
    //          }
    //        }
    //      }
    //      case case_5 {
    //        container pim-asm {
    //          description "PIM-SM provider tunnel";
    //          // uses apply-advanced;
    //          leaf group-address {
    //            description "PIM-SM provider tunnel group address";
    //            type jt:ipv4addr;
    //          }
    //          container family {
    //            presence "enable family";
    //            description "PIM-SM provider tunnel address family";
    //            status deprecated;
    //            // uses apply-advanced;
    //            container inet {
    //              presence "enable inet";
    //              description "IPv4 PIM-SM provider tunnel";
    //              // uses apply-advanced;
    //              leaf group-address {
    //                description "PIM-SM provider tunnel group address for IPV4";
    //                type jt:ipv4addr;
    //              }
    //              leaf tunnel-source {
    //                description "Source address for the provider space mGRE tunnel";
    //                type jt:ipv4addr;
    //              }
    //            }
    //            container inet6 {
    //              presence "enable inet6";
    //              description "IPv6 PIM-SM provider tunnel";
    //              // uses apply-advanced;
    //              leaf group-address {
    //                description "PIM-SM provider tunnel group address for IPV6";
    //                type jt:ipv4addr;
    //              }
    //              leaf tunnel-source {
    //                description "Source address for the provider space mGRE tunnel";
    //                type jt:ipv4addr;
    //              }
    //            }
    //          }
    //        }
    //      }
    //      case case_6 {
    //        container pim-ssm {
    //          description "PIM-SSM provider tunnel";
    //          // uses apply-advanced;
    //          leaf group-address {
    //            description "PIM-SSM provider tunnel group address";
    //            type jt:ipv4addr;
    //          }
    //          container family {
    //            presence "enable family";
    //            description "PIM-SSM provider tunnel address family";
    //            status deprecated;
    //            // uses apply-advanced;
    //            container inet {
    //              presence "enable inet";
    //              description "IPv4 PIM-SSM provider tunnel";
    //              // uses apply-advanced;
    //              leaf group-address {
    //                description "PIM-SSM provider tunnel group address for IPV4";
    //                type jt:ipv4addr;
    //              }
    //              leaf tunnel-source {
    //                description "Source address for the provider space mGRE tunnel";
    //                type jt:ipv4addr;
    //              }
    //            }
    //            container inet6 {
    //              presence "enable inet6";
    //              description "IPv6 PIM-SSM provider tunnel";
    //              // uses apply-advanced;
    //              leaf group-address {
    //                description "PIM-SSM provider tunnel group address for IPV6";
    //                type jt:ipv4addr;
    //              }
    //              leaf tunnel-source {
    //                description "Source address for the provider space mGRE tunnel";
    //                type jt:ipv4addr;
    //              }
    //            }
    //          }
    //        }
    //      }
    //    }
    //    container inter-as {
    //      description "Inter-AS segmented tunnels";
    //      // uses apply-advanced;
    //      choice tunnel-type {
    //        case case_1 {
    //          container ingress-replication {
    //            description "Ingress replication tunnel";
    //            // uses apply-advanced;
    //            leaf create-new-ucast-tunnel {
    //              description "Create new unicast tunnel for ingress replication";
    //              type empty;
    //            }
    //            container label-switched-path {
    //              presence "enable label-switched-path";
    //              description "Point-to-point LSP unicast tunnel";
    //              // uses apply-advanced;
    //              container label-switched-path-template {
    //                description "Template for dynamic point-to-point LSP parameters";
    //                // uses apply-advanced;
    //                choice dynamic-template {
    //                  case case_1 {
    //                    leaf template-name {
    //                      description "Name of point-to-point LSP template";
    //                      type string {
    //                      }
    //                    }
    //                  }
    //                  case case_2 {
    //                    leaf default-template {
    //                      description "Use default parameters";
    //                      type empty;
    //                    }
    //                  }
    //                }
    //              }
    //            }
    //          }
    //        }
    //        case case_2 {
    //          container rsvp-te {
    //            description "RSVP-TE point-to-multipoint LSP for flooding";
    //            // uses apply-advanced;
    //            choice static-or-dynamic {
    //              case case_1 {
    //                container label-switched-path-template {
    //                  description "Template for dynamic point-to-multipoint LSP parameters";
    //                  // uses apply-advanced;
    //                  choice dynamic-template {
    //                    case case_1 {
    //                      leaf template-name {
    //                        description "Name of point-to-multipoint LSP template";
    //                        type string {
    //                        }
    //                      }
    //                    }
    //                    case case_2 {
    //                      leaf default-template {
    //                        description "Use default parameters";
    //                        type empty;
    //                      }
    //                    }
    //                  }
    //                }
    //              }
    //            }
    //          }
    //        }
    //        case case_3 {
    //          container ldp-p2mp {
    //            presence "enable ldp-p2mp";
    //            description "LDP point-to-multipoint LSP for flooding";
    //          }
    //        }
    //      }
    //      container inter-region-segmented {
    //        description "Inter-Region Segmented LSP triggered by threshold rate and/or fan-out";
    //        // uses apply-advanced;
    //        leaf threshold {
    //          description "Data threshold rate to trigger segmentation";
    //          units "kilobits";
    //          type union {
    //            type string {
    //              pattern "<.*>|$.*";
    //            }
    //            type uint32 {
    //              range "0 .. 1000000";
    //            }
    //          }
    //        }
    //        leaf fan-out {
    //          description "Number of remote Leaf-AD routes";
    //          type union {
    //            type string {
    //              pattern "<.*>|$.*";
    //            }
    //            type uint32 {
    //              range "1 .. 10000";
    //            }
    //          }
    //        }
    //      }
    //    }
    //    container inter-region {
    //      description "Inter-region segmented tunnels";
    //      // uses apply-advanced;
    //      choice segmented-or-not {
    //        case case_1 {
    //          leaf template {
    //            description "Use inter-region segmentation template";
    //            type string;
    //          }
    //        }
    //        case case_2 {
    //          leaf no-inter-region-segmentation {
    //            description "Do not participate in inter-region segmentation";
    //            type empty;
    //          }
    //        }
    //      }
    //    }
    //    container inter-region-segmented {
    //      description "Inter-Region Segmented LSP triggered by fan-out factor only";
    //      // uses apply-advanced;
    //      leaf fan-out {
    //        description "Number of remote Leaf-AD routes";
    //        type union {
    //          type string {
    //            pattern "<.*>|$.*";
    //          }
    //          type uint32 {
    //            range "1 .. 10000";
    //          }
    //        }
    //      }
    //    }
    //    container selective {
    //      description "Selective tunnels";
    //      // uses apply-advanced;
    //      leaf tunnel-limit {
    //        description "Maximum number of selective tunnels";
    //        type union {
    //          type string {
    //            pattern "<.*>|$.*";
    //          }
    //          type uint32 {
    //            range "0 .. 30000";
    //          }
    //        }
    //      }
    //      leaf leaf-tunnel-limit-inet {
    //        description "Maximum number of selective leaf tunnels for v4";
    //        type union {
    //          type string {
    //            pattern "<.*>|$.*";
    //          }
    //          type uint32 {
    //            range "0 .. 15000";
    //          }
    //        }
    //      }
    //      leaf leaf-tunnel-limit-inet6 {
    //        description "Maximum number of selective leaf tunnels for v6";
    //        type union {
    //          type string {
    //            pattern "<.*>|$.*";
    //          }
    //          type uint32 {
    //            range "0 .. 15000";
    //          }
    //        }
    //      }
    //      container wildcard-group-inet {
    //        description "IPv4 wilcard group matching any group address";
    //        // uses apply-advanced;
    //        container wildcard-source {
    //          presence "enable wildcard-source";
    //          description "Use Selective-Tunnel for wildcard-source (*,G) joins";
    //          // uses apply-advanced;
    //          leaf threshold-rate {
    //            description "Data threshold to create new tunnel";
    //            units "kilobits";
    //            type union {
    //              type string {
    //                pattern "<.*>|$.*";
    //              }
    //              type uint32 {
    //                range "0 .. 1000000";
    //              }
    //            }
    //          }
    //          choice tunnel-type {
    //            case case_1 {
    //              container bier {
    //                presence "enable bier";
    //                description "Use BIER for multicast forwarding";
    //                // uses apply-advanced;
    //                leaf subdomain-id {
    //                  description "SubDomain ID";
    //                  type union {
    //                    type uint8;
    //                    type string {
    //                      pattern "<.*>|$.*";
    //                    }
    //                  }
    //                }
    //                leaf label {
    //                  description "Domain-wide unique label for the tunnel";
    //                  type union {
    //                    type string {
    //                      pattern "<.*>|$.*";
    //                    }
    //                    type uint32 {
    //                      range "16 .. 1048575";
    //                    }
    //                  }
    //                }
    //              }
    //            }
    //            case case_2 {
    //              container ingress-replication {
    //                description "Ingress replication tunnel";
    //                // uses apply-advanced;
    //                leaf create-new-ucast-tunnel {
    //                  description "Create new unicast tunnel for ingress replication";
    //                  type empty;
    //                }
    //                container label-switched-path {
    //                  presence "enable label-switched-path";
    //                  description "Point-to-point LSP unicast tunnel";
    //                  // uses apply-advanced;
    //                  container label-switched-path-template {
    //                    description "Template for dynamic point-to-point LSP parameters";
    //                    // uses apply-advanced;
    //                    choice dynamic-template {
    //                      case case_1 {
    //                        leaf template-name {
    //                          description "Name of point-to-point LSP template";
    //                          type string {
    //                          }
    //                        }
    //                      }
    //                      case case_2 {
    //                        leaf default-template {
    //                          description "Use default parameters";
    //                          type empty;
    //                        }
    //                      }
    //                    }
    //                  }
    //                }
    //              }
    //            }
    //            case case_3 {
    //              container rsvp-te {
    //                description "RSVP-TE point-to-multipoint LSP for flooding";
    //                // uses apply-advanced;
    //                choice static-or-dynamic {
    //                  case case_1 {
    //                    leaf static-lsp {
    //                      description "Name of point-to-multipoint LSP";
    //                      type string {
    //                      }
    //                    }
    //                  }
    //                  case case_2 {
    //                    container label-switched-path-template {
    //                      description "Template for dynamic point-to-multipoint LSP parameters";
    //                      // uses apply-advanced;
    //                      choice dynamic-template {
    //                        case case_1 {
    //                          leaf template-name {
    //                            description "Name of point-to-multipoint LSP template";
    //                            type string {
    //                            }
    //                          }
    //                        }
    //                        case case_2 {
    //                          leaf default-template {
    //                            description "Use default parameters";
    //                            type empty;
    //                          }
    //                        }
    //                      }
    //                    }
    //                  }
    //                }
    //              }
    //            }
    //            case case_4 {
    //              container ldp-p2mp {
    //                presence "enable ldp-p2mp";
    //                description "LDP point-to-multipoint LSP for flooding";
    //              }
    //            }
    //            case case_5 {
    //              container pim-ssm {
    //                description "PIM-SSM provider tunnel";
    //                // uses apply-advanced;
    //                leaf group-range {
    //                  description "PIM-SSM provider tunnel group range";
    //                  type jt:ipv4prefix;
    //                }
    //              }
    //            }
    //          }
    //          container inter-region-segmented {
    //            description "Inter-Region Segmented LSP triggered by fan-out factor only";
    //            // uses apply-advanced;
    //            leaf fan-out {
    //              description "Number of remote Leaf-AD routes";
    //              type union {
    //                type string {
    //                  pattern "<.*>|$.*";
    //                }
    //                type uint32 {
    //                  range "1 .. 10000";
    //                }
    //              }
    //            }
    //          }
    //        }
    //      }
    //      container wildcard-group-inet6 {
    //        description "IPv6 wilcard group matching any group address";
    //        // uses apply-advanced;
    //        container wildcard-source {
    //          presence "enable wildcard-source";
    //          description "Use Selective-Tunnel for wildcard-source (*,G) joins";
    //          // uses apply-advanced;
    //          leaf threshold-rate {
    //            description "Data threshold to create new tunnel";
    //            units "kilobits";
    //            type union {
    //              type string {
    //                pattern "<.*>|$.*";
    //              }
    //              type uint32 {
    //                range "0 .. 1000000";
    //              }
    //            }
    //          }
    //          choice tunnel-type {
    //            case case_1 {
    //              container bier {
    //                presence "enable bier";
    //                description "Use BIER for multicast forwarding";
    //                // uses apply-advanced;
    //                leaf subdomain-id {
    //                  description "SubDomain ID";
    //                  type union {
    //                    type uint8;
    //                    type string {
    //                      pattern "<.*>|$.*";
    //                    }
    //                  }
    //                }
    //                leaf label {
    //                  description "Domain-wide unique label for the tunnel";
    //                  type union {
    //                    type string {
    //                      pattern "<.*>|$.*";
    //                    }
    //                    type uint32 {
    //                      range "16 .. 1048575";
    //                    }
    //                  }
    //                }
    //              }
    //            }
    //            case case_2 {
    //              container ingress-replication {
    //                description "Ingress replication tunnel";
    //                // uses apply-advanced;
    //                leaf create-new-ucast-tunnel {
    //                  description "Create new unicast tunnel for ingress replication";
    //                  type empty;
    //                }
    //                container label-switched-path {
    //                  presence "enable label-switched-path";
    //                  description "Point-to-point LSP unicast tunnel";
    //                  // uses apply-advanced;
    //                  container label-switched-path-template {
    //                    description "Template for dynamic point-to-point LSP parameters";
    //                    // uses apply-advanced;
    //                    choice dynamic-template {
    //                      case case_1 {
    //                        leaf template-name {
    //                          description "Name of point-to-point LSP template";
    //                          type string {
    //                          }
    //                        }
    //                      }
    //                      case case_2 {
    //                        leaf default-template {
    //                          description "Use default parameters";
    //                          type empty;
    //                        }
    //                      }
    //                    }
    //                  }
    //                }
    //              }
    //            }
    //            case case_3 {
    //              container rsvp-te {
    //                description "RSVP-TE point-to-multipoint LSP for flooding";
    //                // uses apply-advanced;
    //                choice static-or-dynamic {
    //                  case case_1 {
    //                    leaf static-lsp {
    //                      description "Name of point-to-multipoint LSP";
    //                      type string {
    //                      }
    //                    }
    //                  }
    //                  case case_2 {
    //                    container label-switched-path-template {
    //                      description "Template for dynamic point-to-multipoint LSP parameters";
    //                      // uses apply-advanced;
    //                      choice dynamic-template {
    //                        case case_1 {
    //                          leaf template-name {
    //                            description "Name of point-to-multipoint LSP template";
    //                            type string {
    //                            }
    //                          }
    //                        }
    //                        case case_2 {
    //                          leaf default-template {
    //                            description "Use default parameters";
    //                            type empty;
    //                          }
    //                        }
    //                      }
    //                    }
    //                  }
    //                }
    //              }
    //            }
    //            case case_4 {
    //              container ldp-p2mp {
    //                presence "enable ldp-p2mp";
    //                description "LDP point-to-multipoint LSP for flooding";
    //              }
    //            }
    //            case case_5 {
    //              container pim-ssm {
    //                description "PIM-SSM provider tunnel";
    //                // uses apply-advanced;
    //                leaf group-range {
    //                  description "PIM-SSM provider tunnel group range";
    //                  type jt:ipv4prefix;
    //                }
    //              }
    //            }
    //          }
    //          container inter-region-segmented {
    //            description "Inter-Region Segmented LSP triggered by fan-out factor only";
    //            // uses apply-advanced;
    //            leaf fan-out {
    //              description "Number of remote Leaf-AD routes";
    //              type union {
    //                type string {
    //                  pattern "<.*>|$.*";
    //                }
    //                type uint32 {
    //                  range "1 .. 10000";
    //                }
    //              }
    //            }
    //          }
    //        }
    //      }
    //      list group {
    //        key name;
    //        ordered-by user;
    //        description "IP prefix of multicast group";
    //        leaf name {
    //          description "IP prefix of group";
    //          type jt:ipprefix;
    //        }
    //        // uses apply-advanced;
    //        container wildcard-source {
    //          presence "enable wildcard-source";
    //          description "Use Selective-Tunnel for wildcard-source (*,G) joins";
    //          // uses apply-advanced;
    //          leaf threshold-rate {
    //            description "Data threshold to create new tunnel";
    //            units "kilobits";
    //            type union {
    //              type string {
    //                pattern "<.*>|$.*";
    //              }
    //              type uint32 {
    //                range "0 .. 1000000";
    //              }
    //            }
    //          }
    //          choice tunnel-type {
    //            case case_1 {
    //              container bier {
    //                presence "enable bier";
    //                description "Use BIER for multicast forwarding";
    //                // uses apply-advanced;
    //                leaf subdomain-id {
    //                  description "SubDomain ID";
    //                  type union {
    //                    type uint8;
    //                    type string {
    //                      pattern "<.*>|$.*";
    //                    }
    //                  }
    //                }
    //                leaf label {
    //                  description "Domain-wide unique label for the tunnel";
    //                  type union {
    //                    type string {
    //                      pattern "<.*>|$.*";
    //                    }
    //                    type uint32 {
    //                      range "16 .. 1048575";
    //                    }
    //                  }
    //                }
    //              }
    //            }
    //            case case_2 {
    //              container ingress-replication {
    //                description "Ingress replication tunnel";
    //                // uses apply-advanced;
    //                leaf create-new-ucast-tunnel {
    //                  description "Create new unicast tunnel for ingress replication";
    //                  type empty;
    //                }
    //                container label-switched-path {
    //                  presence "enable label-switched-path";
    //                  description "Point-to-point LSP unicast tunnel";
    //                  // uses apply-advanced;
    //                  container label-switched-path-template {
    //                    description "Template for dynamic point-to-point LSP parameters";
    //                    // uses apply-advanced;
    //                    choice dynamic-template {
    //                      case case_1 {
    //                        leaf template-name {
    //                          description "Name of point-to-point LSP template";
    //                          type string {
    //                          }
    //                        }
    //                      }
    //                      case case_2 {
    //                        leaf default-template {
    //                          description "Use default parameters";
    //                          type empty;
    //                        }
    //                      }
    //                    }
    //                  }
    //                }
    //              }
    //            }
    //            case case_3 {
    //              container rsvp-te {
    //                description "RSVP-TE point-to-multipoint LSP for flooding";
    //                // uses apply-advanced;
    //                choice static-or-dynamic {
    //                  case case_1 {
    //                    leaf static-lsp {
    //                      description "Name of point-to-multipoint LSP";
    //                      type string {
    //                      }
    //                    }
    //                  }
    //                  case case_2 {
    //                    container label-switched-path-template {
    //                      description "Template for dynamic point-to-multipoint LSP parameters";
    //                      // uses apply-advanced;
    //                      choice dynamic-template {
    //                        case case_1 {
    //                          leaf template-name {
    //                            description "Name of point-to-multipoint LSP template";
    //                            type string {
    //                            }
    //                          }
    //                        }
    //                        case case_2 {
    //                          leaf default-template {
    //                            description "Use default parameters";
    //                            type empty;
    //                          }
    //                        }
    //                      }
    //                    }
    //                  }
    //                }
    //              }
    //            }
    //            case case_4 {
    //              container ldp-p2mp {
    //                presence "enable ldp-p2mp";
    //                description "LDP point-to-multipoint LSP for flooding";
    //              }
    //            }
    //            case case_5 {
    //              container pim-ssm {
    //                description "PIM-SSM provider tunnel";
    //                // uses apply-advanced;
    //                leaf group-range {
    //                  description "PIM-SSM provider tunnel group range";
    //                  type jt:ipv4prefix;
    //                }
    //              }
    //            }
    //          }
    //          container inter-region-segmented {
    //            description "Inter-Region Segmented LSP triggered by threshold rate and/or fan-out";
    //            // uses apply-advanced;
    //            leaf threshold {
    //              description "Data threshold rate to trigger segmentation";
    //              units "kilobits";
    //              type union {
    //                type string {
    //                  pattern "<.*>|$.*";
    //                }
    //                type uint32 {
    //                  range "0 .. 1000000";
    //                }
    //              }
    //            }
    //            leaf fan-out {
    //              description "Number of remote Leaf-AD routes";
    //              type union {
    //                type string {
    //                  pattern "<.*>|$.*";
    //                }
    //                type uint32 {
    //                  range "1 .. 10000";
    //                }
    //              }
    //            }
    //          }
    //        }
    //        list source {
    //          key name;
    //          ordered-by user;
    //          description "IP prefix of one or more multicast sources";
    //          leaf name {
    //            description "IP prefix of source";
    //            type jt:ipprefix;
    //          }
    //          // uses apply-advanced;
    //          choice tunnel-type {
    //            case case_1 {
    //              container bier {
    //                presence "enable bier";
    //                description "Use BIER for multicast forwarding";
    //                // uses apply-advanced;
    //                leaf subdomain-id {
    //                  description "SubDomain ID";
    //                  type union {
    //                    type uint8;
    //                    type string {
    //                      pattern "<.*>|$.*";
    //                    }
    //                  }
    //                }
    //                leaf label {
    //                  description "Domain-wide unique label for the tunnel";
    //                  type union {
    //                    type string {
    //                      pattern "<.*>|$.*";
    //                    }
    //                    type uint32 {
    //                      range "16 .. 1048575";
    //                    }
    //                  }
    //                }
    //              }
    //            }
    //            case case_2 {
    //              container ingress-replication {
    //                description "Ingress replication tunnel";
    //                // uses apply-advanced;
    //                leaf create-new-ucast-tunnel {
    //                  description "Create new unicast tunnel for ingress replication";
    //                  type empty;
    //                }
    //                container label-switched-path {
    //                  presence "enable label-switched-path";
    //                  description "Point-to-point LSP unicast tunnel";
    //                  // uses apply-advanced;
    //                  container label-switched-path-template {
    //                    description "Template for dynamic point-to-point LSP parameters";
    //                    // uses apply-advanced;
    //                    choice dynamic-template {
    //                      case case_1 {
    //                        leaf template-name {
    //                          description "Name of point-to-point LSP template";
    //                          type string {
    //                          }
    //                        }
    //                      }
    //                      case case_2 {
    //                        leaf default-template {
    //                          description "Use default parameters";
    //                          type empty;
    //                        }
    //                      }
    //                    }
    //                  }
    //                }
    //              }
    //            }
    //            case case_3 {
    //              container rsvp-te {
    //                description "RSVP-TE point-to-multipoint LSP for flooding";
    //                // uses apply-advanced;
    //                choice static-or-dynamic {
    //                  case case_1 {
    //                    leaf static-lsp {
    //                      description "Name of point-to-multipoint LSP";
    //                      type string {
    //                      }
    //                    }
    //                  }
    //                  case case_2 {
    //                    container label-switched-path-template {
    //                      description "Template for dynamic point-to-multipoint LSP parameters";
    //                      // uses apply-advanced;
    //                      choice dynamic-template {
    //                        case case_1 {
    //                          leaf template-name {
    //                            description "Name of point-to-multipoint LSP template";
    //                            type string {
    //                            }
    //                          }
    //                        }
    //                        case case_2 {
    //                          leaf default-template {
    //                            description "Use default parameters";
    //                            type empty;
    //                          }
    //                        }
    //                      }
    //                    }
    //                  }
    //                }
    //              }
    //            }
    //            case case_4 {
    //              container pim-ssm {
    //                description "PIM-SSM provider tunnel";
    //                // uses apply-advanced;
    //                leaf group-range {
    //                  description "PIM-SSM provider tunnel group range";
    //                  type jt:ipv4prefix;
    //                }
    //              }
    //            }
    //            case case_5 {
    //              container ldp-p2mp {
    //                presence "enable ldp-p2mp";
    //                description "LDP point-to-multipoint LSP for flooding";
    //              }
    //            }
    //          }
    //          leaf threshold-rate {
    //            description "Data threshold to create new tunnel";
    //            units "kilobits";
    //            type union {
    //              type string {
    //                pattern "<.*>|$.*";
    //              }
    //              type uint32 {
    //                range "0 .. 1000000";
    //              }
    //            }
    //          }
    //          container inter-region-segmented {
    //            description "Inter-Region Segmented LSP triggered by threshold rate and/or fan-out";
    //            // uses apply-advanced;
    //            leaf threshold {
    //              description "Data threshold rate to trigger segmentation";
    //              units "kilobits";
    //              type union {
    //                type string {
    //                  pattern "<.*>|$.*";
    //                }
    //                type uint32 {
    //                  range "0 .. 1000000";
    //                }
    //              }
    //            }
    //            leaf fan-out {
    //              description "Number of remote Leaf-AD routes";
    //              type union {
    //                type string {
    //                  pattern "<.*>|$.*";
    //                }
    //                type uint32 {
    //                  range "1 .. 10000";
    //                }
    //              }
    //            }
    //          }
    //        }
    //      }
    //    }
    //    container mdt {
    //      description "Data MDT tunnels for PIM MVPN";
    //      status deprecated;
    //      // uses apply-advanced;
    //      container threshold {
    //        description "Threshold for creation of multicast tunnels";
    //        // uses apply-advanced;
    //        list group {
    //          key name;
    //          ordered-by user;
    //          description "IP prefix of multicast group";
    //          leaf name {
    //            description "IP prefix of group";
    //            type jt:ipprefix;
    //          }
    //          // uses apply-advanced;
    //          list source {
    //            key name;
    //            ordered-by user;
    //            description "IP prefix of one or more multicast sources ";
    //            leaf name {
    //              description "IP prefix of source";
    //              type jt:ipprefix;
    //            }
    //            // uses apply-advanced;
    //            leaf rate {
    //              description "Data threshold to create new tunnel";
    //              units "kilobits";
    //              type union {
    //                type string {
    //                  pattern "<.*>|$.*";
    //                }
    //                type uint32 {
    //                  range "10 .. 1000000";
    //                }
    //              }
    //            }
    //          }
    //        }
    //      }
    //      leaf data-mdt-reuse {
    //        description "Allow multiple customer streams to be transmitted over one data tunnel ";
    //        type empty;
    //      }
    //      leaf tunnel-limit {
    //        description "Maximum multicast data tunnels";
    //        type union {
    //          type string {
    //            pattern "<.*>|$.*";
    //          }
    //          type uint32 {
    //            range "0 .. 8192";
    //          }
    //        }
    //      }
    //      leaf group-range {
    //        description "Group address range for multicast data tunnels";
    //        type jt:ipprefix;
    //      }
    //    }
    //    container family {
    //      presence "enable family";
    //      // uses apply-advanced;
    //      container inet {
    //        presence "enable inet";
    //        // uses apply-advanced;
    //        choice tunnel-type {
    //          case case_1 {
    //            container rsvp-te {
    //              description "RSVP-TE point-to-multipoint LSP for flooding";
    //              // uses apply-advanced;
    //              choice static-or-dynamic {
    //                case case_1 {
    //                  leaf static-lsp {
    //                    description "Name of point-to-multipoint LSP";
    //                    type string {
    //                    }
    //                  }
    //                }
    //                case case_2 {
    //                  container label-switched-path-template {
    //                    description "Template for dynamic point-to-multipoint LSP parameters";
    //                    // uses apply-advanced;
    //                    choice dynamic-template {
    //                      case case_1 {
    //                        leaf template-name {
    //                          description "Name of point-to-multipoint LSP template";
    //                          type string {
    //                          }
    //                        }
    //                      }
    //                      case case_2 {
    //                        leaf default-template {
    //                          description "Use default parameters";
    //                          type empty;
    //                        }
    //                      }
    //                    }
    //                  }
    //                }
    //              }
    //            }
    //          }
    //          case case_2 {
    //            container ldp-p2mp {
    //              presence "enable ldp-p2mp";
    //              description "LDP point-to-multipoint LSP for flooding";
    //            }
    //          }
    //          case case_3 {
    //            container bier {
    //              presence "enable bier";
    //              description "Use BIER for multicast forwarding";
    //              // uses apply-advanced;
    //              leaf subdomain-id {
    //                description "SubDomain ID";
    //                type union {
    //                  type uint8;
    //                  type string {
    //                    pattern "<.*>|$.*";
    //                  }
    //                }
    //              }
    //              leaf label {
    //                description "Domain-wide unique label for the tunnel";
    //                type union {
    //                  type string {
    //                    pattern "<.*>|$.*";
    //                  }
    //                  type uint32 {
    //                    range "16 .. 1048575";
    //                  }
    //                }
    //              }
    //            }
    //          }
    //          case case_4 {
    //            container ingress-replication {
    //              description "Ingress replication tunnel";
    //              // uses apply-advanced;
    //              leaf create-new-ucast-tunnel {
    //                description "Create new unicast tunnel for ingress replication";
    //                type empty;
    //              }
    //              container label-switched-path {
    //                presence "enable label-switched-path";
    //                description "Point-to-point LSP unicast tunnel";
    //                // uses apply-advanced;
    //                container label-switched-path-template {
    //                  description "Template for dynamic point-to-point LSP parameters";
    //                  // uses apply-advanced;
    //                  choice dynamic-template {
    //                    case case_1 {
    //                      leaf template-name {
    //                        description "Name of point-to-point LSP template";
    //                        type string {
    //                        }
    //                      }
    //                    }
    //                    case case_2 {
    //                      leaf default-template {
    //                        description "Use default parameters";
    //                        type empty;
    //                      }
    //                    }
    //                  }
    //                }
    //              }
    //            }
    //          }
    //          case case_5 {
    //            container pim-asm {
    //              description "PIM-SM provider tunnel";
    //              // uses apply-advanced;
    //              leaf group-address {
    //                description "PIM-SM provider tunnel group address";
    //                type jt:ipv4addr;
    //              }
    //              leaf tunnel-source {
    //                description "Source address for the provider space mGRE tunnel";
    //                type jt:ipv4addr;
    //              }
    //            }
    //          }
    //          case case_6 {
    //            container pim-ssm {
    //              description "PIM-SSM provider tunnel";
    //              // uses apply-advanced;
    //              leaf group-address {
    //                description "PIM-SSM provider tunnel group address";
    //                type jt:ipv4addr;
    //              }
    //              leaf tunnel-source {
    //                description "Source address for the provider space mGRE tunnel";
    //                type jt:ipv4addr;
    //              }
    //            }
    //          }
    //        }
    //        container mdt {
    //          description "IPv4 Data MDT tunnels for PIM MVPN";
    //          // uses apply-advanced;
    //          container threshold {
    //            description "Threshold for creation of multicast tunnels";
    //            // uses apply-advanced;
    //            list group {
    //              key name;
    //              ordered-by user;
    //              description "IP prefix of multicast group";
    //              leaf name {
    //                description "IP prefix of group";
    //                type jt:ipprefix;
    //              }
    //              // uses apply-advanced;
    //              list source {
    //                key name;
    //                ordered-by user;
    //                description "IP prefix of one or more multicast sources ";
    //                leaf name {
    //                  description "IP prefix of source";
    //                  type jt:ipprefix;
    //                }
    //                // uses apply-advanced;
    //                leaf rate {
    //                  description "Data threshold to create new tunnel";
    //                  units "kilobits";
    //                  type union {
    //                    type string {
    //                      pattern "<.*>|$.*";
    //                    }
    //                    type uint32 {
    //                      range "10 .. 1000000";
    //                    }
    //                  }
    //                }
    //              }
    //            }
    //          }
    //          leaf data-mdt-reuse {
    //            description "Allow multiple customer streams to be transmitted over one data tunnel ";
    //            type empty;
    //          }
    //          leaf tunnel-limit {
    //            description "Maximum multicast data tunnels";
    //            type union {
    //              type string {
    //                pattern "<.*>|$.*";
    //              }
    //              type uint32 {
    //                range "0 .. 8192";
    //              }
    //            }
    //          }
    //          leaf group-range {
    //            description "Group address range for multicast data tunnels";
    //            type jt:ipprefix;
    //          }
    //        }
    //      }
    //      container inet6 {
    //        presence "enable inet6";
    //        // uses apply-advanced;
    //        choice tunnel-type {
    //          case case_1 {
    //            container rsvp-te {
    //              description "RSVP-TE point-to-multipoint LSP for flooding";
    //              // uses apply-advanced;
    //              choice static-or-dynamic {
    //                case case_1 {
    //                  leaf static-lsp {
    //                    description "Name of point-to-multipoint LSP";
    //                    type string {
    //                    }
    //                  }
    //                }
    //                case case_2 {
    //                  container label-switched-path-template {
    //                    description "Template for dynamic point-to-multipoint LSP parameters";
    //                    // uses apply-advanced;
    //                    choice dynamic-template {
    //                      case case_1 {
    //                        leaf template-name {
    //                          description "Name of point-to-multipoint LSP template";
    //                          type string {
    //                          }
    //                        }
    //                      }
    //                      case case_2 {
    //                        leaf default-template {
    //                          description "Use default parameters";
    //                          type empty;
    //                        }
    //                      }
    //                    }
    //                  }
    //                }
    //              }
    //            }
    //          }
    //          case case_2 {
    //            container ldp-p2mp {
    //              presence "enable ldp-p2mp";
    //              description "LDP point-to-multipoint LSP for flooding";
    //            }
    //          }
    //          case case_3 {
    //            container bier {
    //              presence "enable bier";
    //              description "Use BIER for multicast forwarding";
    //              // uses apply-advanced;
    //              leaf subdomain-id {
    //                description "SubDomain ID";
    //                type union {
    //                  type uint8;
    //                  type string {
    //                    pattern "<.*>|$.*";
    //                  }
    //                }
    //              }
    //              leaf label {
    //                description "Domain-wide unique label for the tunnel";
    //                type union {
    //                  type string {
    //                    pattern "<.*>|$.*";
    //                  }
    //                  type uint32 {
    //                    range "16 .. 1048575";
    //                  }
    //                }
    //              }
    //            }
    //          }
    //          case case_4 {
    //            container ingress-replication {
    //              description "Ingress replication tunnel";
    //              // uses apply-advanced;
    //              leaf create-new-ucast-tunnel {
    //                description "Create new unicast tunnel for ingress replication";
    //                type empty;
    //              }
    //              container label-switched-path {
    //                presence "enable label-switched-path";
    //                description "Point-to-point LSP unicast tunnel";
    //                // uses apply-advanced;
    //                container label-switched-path-template {
    //                  description "Template for dynamic point-to-point LSP parameters";
    //                  // uses apply-advanced;
    //                  choice dynamic-template {
    //                    case case_1 {
    //                      leaf template-name {
    //                        description "Name of point-to-point LSP template";
    //                        type string {
    //                        }
    //                      }
    //                    }
    //                    case case_2 {
    //                      leaf default-template {
    //                        description "Use default parameters";
    //                        type empty;
    //                      }
    //                    }
    //                  }
    //                }
    //              }
    //            }
    //          }
    //          case case_5 {
    //            container pim-asm {
    //              description "PIM-SM provider tunnel";
    //              // uses apply-advanced;
    //              leaf group-address {
    //                description "PIM-SM provider tunnel group address";
    //                type jt:ipv4addr;
    //              }
    //              leaf tunnel-source {
    //                description "Source address for the provider space mGRE tunnel";
    //                type jt:ipv4addr;
    //              }
    //            }
    //          }
    //          case case_6 {
    //            container pim-ssm {
    //              description "PIM-SSM provider tunnel";
    //              // uses apply-advanced;
    //              leaf group-address {
    //                description "PIM-SSM provider tunnel group address";
    //                type jt:ipv4addr;
    //              }
    //              leaf tunnel-source {
    //                description "Source address for the provider space mGRE tunnel";
    //                type jt:ipv4addr;
    //              }
    //            }
    //          }
    //        }
    //        container mdt {
    //          description "IPv6 Data MDT tunnels for PIM MVPN";
    //          // uses apply-advanced;
    //          container threshold {
    //            description "Threshold for creation of multicast tunnels";
    //            // uses apply-advanced;
    //            list group {
    //              key name;
    //              ordered-by user;
    //              description "IP prefix of multicast group";
    //              leaf name {
    //                description "IP prefix of group";
    //                type jt:ipprefix;
    //              }
    //              // uses apply-advanced;
    //              list source {
    //                key name;
    //                ordered-by user;
    //                description "IP prefix of one or more multicast sources ";
    //                leaf name {
    //                  description "IP prefix of source";
    //                  type jt:ipprefix;
    //                }
    //                // uses apply-advanced;
    //                leaf rate {
    //                  description "Data threshold to create new tunnel";
    //                  units "kilobits";
    //                  type union {
    //                    type string {
    //                      pattern "<.*>|$.*";
    //                    }
    //                    type uint32 {
    //                      range "10 .. 1000000";
    //                    }
    //                  }
    //                }
    //              }
    //            }
    //          }
    //          leaf data-mdt-reuse {
    //            description "Allow multiple customer streams to be transmitted over one data tunnel ";
    //            type empty;
    //          }
    //          leaf tunnel-limit {
    //            description "Maximum multicast data tunnels";
    //            type union {
    //              type string {
    //                pattern "<.*>|$.*";
    //              }
    //              type uint32 {
    //                range "0 .. 8192";
    //              }
    //            }
    //          }
    //          leaf group-range {
    //            description "Group address range for multicast data tunnels";
    //            type jt:ipprefix;
    //          }
    //        }
    //      }
    //    }
    //  }
    //  container multicast-snooping-options {
    //    description "Multicast snooping option configuration";
    //    uses juniper-multicast-snooping-options;
    //  }
    //  container igmp-snooping-options {
    //    description "IGMP snooping option configuration";
    //    uses juniper-igmp-snooping-options;
    //  }
    //  container mld-snooping-options {
    //    description "MLD snooping option configuration";
    //    uses juniper-mld-snooping-options;
    //  }
    //  container vlans {
    //    description "VLAN configuration";
    //    // uses apply-advanced;
    //    list vlan {
    //      key name;
    //      description "Virtual LAN";
    //      uses vlan-types-routing-instance;
    //    }
    //  }
   }
  //  grouping address-assignment-type {
  //    description "Address assignment configuration";
  //    // uses apply-advanced;
  //    container neighbor-discovery-router-advertisement {
  //      description "Designated NDRA pool for this instance";
  //      leaf ndra-name {
  //        description "Designated NDRA pool name";
  //        type string {
  //          length "1 .. 63";
  //        }
  //      }
  //    }
  //    leaf high-utilization {
  //      description "Generate an SNMP trap when address pool use surpasses this percentage";
  //      type union {
  //        type string {
  //          pattern "<.*>|$.*";
  //        }
  //        type uint16 {
  //          range "2 .. 99";
  //        }
  //      }
  //    }
  //    leaf abated-utilization {
  //      description "Generate an SNMP clear trap when address pool use falls below this percentage";
  //      type union {
  //        type string {
  //          pattern "<.*>|$.*";
  //        }
  //        type uint16 {
  //          range "1 .. 98";
  //        }
  //      }
  //    }
  //    leaf high-utilization-v6 {
  //      description "Generate an SNMP trap when address pool use surpasses this percentage";
  //      type union {
  //        type string {
  //          pattern "<.*>|$.*";
  //        }
  //        type uint16 {
  //          range "2 .. 99";
  //        }
  //      }
  //    }
  //    leaf abated-utilization-v6 {
  //      description "Generate an SNMP clear trap when address pool use falls below this percentage";
  //      type union {
  //        type string {
  //          pattern "<.*>|$.*";
  //        }
  //        type uint16 {
  //          range "1 .. 98";
  //        }
  //      }
  //    }
  //   //  list dynamic-pool {
  //   //    key name;
  //   //    ordered-by user;
  //   //    description "Dynamic address pool";
  //   //    leaf name {
  //   //      description "Dynamic address pool name";
  //   //      type string {
  //   //        length "1 .. 63";
  //   //      }
  //   //    }
  //   //    // uses apply-advanced;
  //   //    container family {
  //   //      presence "enable family";
  //   //      description "Address family";
  //   //      // uses apply-advanced;
  //   //      container inet6 {
  //   //        description "IPv6";
  //   //        // uses apply-advanced;
  //   //        leaf delegated-prefix-length {
  //   //          description "Delegated IPv6 network prefix length";
  //   //          type union {
  //   //            type string {
  //   //              pattern "<.*>|$.*";
  //   //            }
  //   //            type uint32 {
  //   //              range "1 .. 64";
  //   //            }
  //   //          }
  //   //        }
  //   //        leaf prefix-identifier {
  //   //          description "Prefix identifier to use for delegated prefix";
  //   //          type jt:ipv6addr;
  //   //        }
  //   //        leaf from-interface {
  //   //          description "Get prefix from interface name";
  //   //          type union {
  //   //            type jt:interface-name;
  //   //            type string {
  //   //              pattern "<.*>|$.*";
  //   //            }
  //   //          }
  //   //        }
  //   //        list range {
  //   //          key name;
  //   //          ordered-by user;
  //   //          description "IPv6 address range";
  //   //          leaf name {
  //   //            description "Range name";
  //   //            type string {
  //   //              length "1 .. 63";
  //   //            }
  //   //          }
  //   //          // uses apply-advanced;
  //   //          leaf masked-low {
  //   //            description "Lower limit of ipv6 address range";
  //   //            type jt:ipv6prefix-mandatory;
  //   //          }
  //   //          leaf masked-high {
  //   //            description "Upper limit of ipv6 address range";
  //   //            type jt:ipv6prefix-mandatory;
  //   //          }
  //   //          leaf prefix-length {
  //   //            description "IPv6 delegated prefix length";
  //   //            type union {
  //   //              type string {
  //   //                pattern "<.*>|$.*";
  //   //              }
  //   //              type uint32 {
  //   //                range "1 .. 64";
  //   //              }
  //   //            }
  //   //          }
  //   //        }
  //   //        container dhcp-attributes {
  //   //          description "DHCP options and match criteria";
  //   //          uses dynamic-dhcp-attribute-type;
  //   //        }
  //   //      }
  //   //    }
  //   //  }
  //   //  list pool {
  //   //    key name;
  //   //    ordered-by user;
  //   //    description "Address pool";
  //   //    leaf name {
  //   //      description "Address pool name";
  //   //      type string {
  //   //        length "1 .. 63";
  //   //      }
  //   //    }
  //   //    // uses apply-advanced;
  //   //    leaf active-drain {
  //   //      description "Notify client of pool active drain mode";
  //   //      type empty;
  //   //    }
  //   //    leaf hold-down {
  //   //      description "Place pool in passive drain mode";
  //   //      type empty;
  //   //    }
  //   //    leaf link {
  //   //      description "Address pool link name";
  //   //      type string {
  //   //        length "1 .. 63";
  //   //      }
  //   //    }
  //   //    container family {
  //   //      presence "enable family";
  //   //      description "Address family";
  //   //      choice family_type {
  //   //        case case_1 {
  //   //          container inet {
  //   //            presence "enable inet";
  //   //            description "IPv4";
  //   //            // uses apply-advanced;
  //   //            leaf network {
  //   //              description "Network address";
  //   //              type jt:ipv4prefix;
  //   //            }
  //   //            list range {
  //   //              key name;
  //   //              ordered-by user;
  //   //              description "Address range";
  //   //              leaf name {
  //   //                description "Range name";
  //   //                type string {
  //   //                  length "1 .. 63";
  //   //                }
  //   //              }
  //   //              // uses apply-advanced;
  //   //              leaf low {
  //   //                description "Lower limit of address range";
  //   //                type jt:ipv4addr;
  //   //              }
  //   //              leaf high {
  //   //                description "Upper limit of address range";
  //   //                type jt:ipv4addr;
  //   //              }
  //   //            }
  //   //            container dhcp-attributes {
  //   //              description "DHCP options and match criteria";
  //   //              uses dhcp-attribute-type;
  //   //            }
  //   //            container xauth-attributes {
  //   //              description "Configure xauth attributes";
  //   //              // uses apply-advanced;
  //   //              leaf primary-dns {
  //   //                description "Specify the primary-dns IP address";
  //   //                type jt:ipv4prefix;
  //   //              }
  //   //              leaf secondary-dns {
  //   //                description "Specify the secondary-dns IP address";
  //   //                type jt:ipv4prefix;
  //   //              }
  //   //              leaf primary-wins {
  //   //                description "Specify the primary-wins IP address";
  //   //                type jt:ipv4prefix;
  //   //              }
  //   //              leaf secondary-wins {
  //   //                description "Specify the secondary-wins IP address";
  //   //                type jt:ipv4prefix;
  //   //              }
  //   //            }
  //   //            list host {
  //   //              key name;
  //   //              ordered-by user;
  //   //              description "Hostname for static reservations";
  //   //              leaf name {
  //   //                description "Hostname";
  //   //                type string {
  //   //                  length "1 .. 256";
  //   //                }
  //   //              }
  //   //              // uses apply-advanced;
  //   //              leaf hardware-address {
  //   //                description "Hardware address";
  //   //                type jt:mac-addr;
  //   //              }
  //   //              leaf ip-address {
  //   //                description "Reserved address";
  //   //                type jt:ipv4addr;
  //   //              }
  //   //              choice host-identifier-type {
  //   //                case case_1 {
  //   //                  leaf user-name {
  //   //                    description "Set subscriber user name as host identifier";
  //   //                    type empty;
  //   //                  }
  //   //                }
  //   //              }
  //   //            }
  //   //            list excluded-address {
  //   //              key name;
  //   //              ordered-by user;
  //   //              description "Excluded Addresses";
  //   //              max-elements 20;
  //   //              leaf name {
  //   //                description "Excluded address";
  //   //                type jt:ipv4addr;
  //   //              }
  //   //              // uses apply-advanced;
  //   //            }
  //   //            list excluded-range {
  //   //              key name;
  //   //              ordered-by user;
  //   //              description "Excluded address range";
  //   //              max-elements 20;
  //   //              leaf name {
  //   //                description "Range name";
  //   //                type string {
  //   //                  length "1 .. 63";
  //   //                }
  //   //              }
  //   //              // uses apply-advanced;
  //   //              leaf low {
  //   //                description "Lower limit of excluded address range";
  //   //                type jt:ipv4addr;
  //   //              }
  //   //              leaf high {
  //   //                description "Upper limit of excluded address range";
  //   //                type jt:ipv4addr;
  //   //              }
  //   //            }
  //   //          }
  //   //        }
  //   //        case case_2 {
  //   //          container inet6 {
  //   //            presence "enable inet6";
  //   //            description "IPv6";
  //   //            // uses apply-advanced;
  //   //            leaf prefix {
  //   //              description "IPv6 network prefix";
  //   //              type jt:ipv6prefix-mandatory;
  //   //            }
  //   //            list range {
  //   //              key name;
  //   //              ordered-by user;
  //   //              description "IPv6 address range";
  //   //              leaf name {
  //   //                description "Range name";
  //   //                type string {
  //   //                  length "1 .. 63";
  //   //                }
  //   //              }
  //   //              // uses apply-advanced;
  //   //              leaf low {
  //   //                description "Lower limit of ipv6 address range";
  //   //                type jt:ipv6prefix-mandatory;
  //   //              }
  //   //              leaf high {
  //   //                description "Upper limit of ipv6 address range";
  //   //                type jt:ipv6prefix-mandatory;
  //   //              }
  //   //              leaf prefix-length {
  //   //                description "IPv6 delegated prefix length";
  //   //                type union {
  //   //                  type string {
  //   //                    pattern "<.*>|$.*";
  //   //                  }
  //   //                  type uint32 {
  //   //                    range "1 .. 128";
  //   //                  }
  //   //                }
  //   //              }
  //   //            }
  //   //            container dhcp-attributes {
  //   //              description "DHCP options and match criteria";
  //   //              uses dhcp-attribute-type;
  //   //            }
  //   //            container xauth-attributes {
  //   //              description "Configure xauth ipv6 attributes";
  //   //              // uses apply-advanced;
  //   //              leaf primary-dns-ipv6 {
  //   //                description "Specify the primary-dns IPv6 address";
  //   //                type jt:ipv6addr;
  //   //              }
  //   //              leaf secondary-dns-ipv6 {
  //   //                description "Specify the secondary-dns IPv6 address";
  //   //                type jt:ipv6addr;
  //   //              }
  //   //            }
  //   //            list host {
  //   //              key name;
  //   //              ordered-by user;
  //   //              description "Hostname for static reservations";
  //   //              leaf name {
  //   //                description "Hostname";
  //   //                type string {
  //   //                  length "1 .. 256";
  //   //                }
  //   //              }
  //   //              // uses apply-advanced;
  //   //              leaf hardware-address {
  //   //                description "Hardware address";
  //   //                type jt:mac-addr;
  //   //              }
  //   //              leaf ip-address {
  //   //                description "Reserved address";
  //   //                type jt:ipv6addr;
  //   //              }
  //   //              choice host-identifier-type {
  //   //                case case_1 {
  //   //                  leaf user-name {
  //   //                    description "Set subscriber user name as host identifier";
  //   //                    type empty;
  //   //                  }
  //   //                }
  //   //              }
  //   //            }
  //   //            list excluded-address {
  //   //              key name;
  //   //              ordered-by user;
  //   //              description "Excluded Addresses";
  //   //              max-elements 20;
  //   //              leaf name {
  //   //                description "Excluded address";
  //   //                type jt:ipv6addr;
  //   //              }
  //   //              // uses apply-advanced;
  //   //            }
  //   //            list excluded-range {
  //   //              key name;
  //   //              ordered-by user;
  //   //              description "Excluded address range";
  //   //              max-elements 20;
  //   //              leaf name {
  //   //                description "Range name";
  //   //                type string {
  //   //                  length "1 .. 63";
  //   //                }
  //   //              }
  //   //              // uses apply-advanced;
  //   //              leaf low {
  //   //                description "Lower limit of excluded address range";
  //   //                type jt:ipv6addr;
  //   //              }
  //   //              leaf high {
  //   //                description "Upper limit of excluded address range";
  //   //                type jt:ipv6addr;
  //   //              }
  //   //            }
  //   //          }
  //   //        }
  //   //      }
  //   //    }
  //   //  }
  //   //  list domain-profile {
  //   //    key name;
  //   //    ordered-by user;
  //   //    description "Address domain profile";
  //   //    leaf name {
  //   //      description "Pool domain profile name";
  //   //      type string {
  //   //        length "1 .. 63";
  //   //      }
  //   //    }
  //   //    // uses apply-advanced;
  //   //    container family {
  //   //      presence "enable family";
  //   //      description "Network family to which this configuration belongs";
  //   //      // uses apply-advanced;
  //   //      choice family_type {
  //   //        case case_1 {
  //   //          container inet {
  //   //            description "The IPv4 internet family";
  //   //            // uses apply-advanced;
  //   //            leaf preferred-prefix-length {
  //   //              description "Preferred prefix length";
  //   //              type union {
  //   //                type string {
  //   //                  pattern "<.*>|$.*";
  //   //                }
  //   //                type uint32 {
  //   //                  range "8 .. 30";
  //   //                }
  //   //              }
  //   //            }
  //   //            leaf source-partition-qualifier {
  //   //              description "Prefix source qualifier appended to location for partition name";
  //   //              type string {
  //   //                length "1 .. 63";
  //   //              }
  //   //            }
  //   //            container excluded-address {
  //   //              description "Excluded addresses from allocation";
  //   //              leaf-list last-octet {
  //   //                ordered-by user;
  //   //                description "Last octet of the excluded address";
  //   //                type union {
  //   //                  type string {
  //   //                    pattern "<.*>|$.*";
  //   //                  }
  //   //                  type uint8 {
  //   //                    range "0 .. 255";
  //   //                  }
  //   //                }
  //   //              }
  //   //            }
  //   //            container install-discard-routes {
  //   //              presence "enable install-discard-routes";
  //   //              description "Install discard route domain pool prefix";
  //   //              // uses apply-advanced;
  //   //              leaf tag {
  //   //                description "Route tag";
  //   //                type union {
  //   //                  type string {
  //   //                    pattern "<.*>|$.*";
  //   //                  }
  //   //                  type uint32 {
  //   //                    range "0 .. 4294967295";
  //   //                  }
  //   //                }
  //   //              }
  //   //              leaf backup-tag {
  //   //                description "Backup route tag";
  //   //                type union {
  //   //                  type string {
  //   //                    pattern "<.*>|$.*";
  //   //                  }
  //   //                  type uint32 {
  //   //                    range "0 .. 4294967295";
  //   //                  }
  //   //                }
  //   //              }
  //   //            }
  //   //            leaf dhcp-gateway-address-last-octet {
  //   //              description "DHCP host address component to be excluded and passed to DHCP";
  //   //              type union {
  //   //                type string {
  //   //                  pattern "<.*>|$.*";
  //   //                }
  //   //                type uint8 {
  //   //                  range "1 .. 8";
  //   //                }
  //   //              }
  //   //            }
  //   //            leaf protocol-attributes {
  //   //              description "Access protocol-attributes name";
  //   //              type string {
  //   //                length "1 .. 63";
  //   //              }
  //   //            }
  //   //          }
  //   //        }
  //   //        case case_2 {
  //   //          container inet6 {
  //   //            description "The IPv6 internet family";
  //   //            // uses apply-advanced;
  //   //            leaf partition-type {
  //   //              description "Partition type";
  //   //              type enumeration {
  //   //                enum "non-temporary-address" {
  //   //                  description "Address to advertise in DHCPv6";
  //   //                }
  //   //                enum "delegated-prefix" {
  //   //                  description "Prefix to advertise in DHCPv6";
  //   //                }
  //   //                enum "router-advertisement" {
  //   //                  description "Prefix for router advertisement";
  //   //                }
  //   //              }
  //   //            }
  //   //            leaf preferred-prefix-length {
  //   //              description "Preferred prefix length";
  //   //              type union {
  //   //                type string {
  //   //                  pattern "<.*>|$.*";
  //   //                }
  //   //                type uint32 {
  //   //                  range "8 .. 126";
  //   //                }
  //   //              }
  //   //            }
  //   //            leaf allocation-length {
  //   //              description "Per-allocation length";
  //   //              default "128";
  //   //              type union {
  //   //                type string {
  //   //                  pattern "<.*>|$.*";
  //   //                }
  //   //                type uint32 {
  //   //                  range "8 .. 128";
  //   //                }
  //   //              }
  //   //            }
  //   //            leaf source-partition-qualifier {
  //   //              description "Prefix source qualifier appended to location for partition name";
  //   //              type string {
  //   //                length "1 .. 63";
  //   //              }
  //   //            }
  //   //            container install-discard-routes {
  //   //              presence "enable install-discard-routes";
  //   //              description "Install discard route domain pool prefix";
  //   //              // uses apply-advanced;
  //   //              leaf tag {
  //   //                description "Route tag";
  //   //                type union {
  //   //                  type string {
  //   //                    pattern "<.*>|$.*";
  //   //                  }
  //   //                  type uint32 {
  //   //                    range "0 .. 4294967295";
  //   //                  }
  //   //                }
  //   //              }
  //   //              leaf backup-tag {
  //   //                description "Backup route tag";
  //   //                type union {
  //   //                  type string {
  //   //                    pattern "<.*>|$.*";
  //   //                  }
  //   //                  type uint32 {
  //   //                    range "0 .. 4294967295";
  //   //                  }
  //   //                }
  //   //              }
  //   //            }
  //   //            leaf protocol-attributes {
  //   //              description "Access protocol-attributes name";
  //   //              type string {
  //   //                length "1 .. 63";
  //   //              }
  //   //            }
  //   //          }
  //   //        }
  //   //      }
  //   //    }
  //   //  }
  //   //  container subscriber-group-default-tags {
  //   //    presence "enable subscriber-group-default-tags";
  //   //    description "Route tags to advertise for statically assigned subscriber addresses and prefixes";
  //   //    // uses apply-advanced;
  //   //    leaf tag {
  //   //      description "Route tag to advertise for the active user-plane of the subscriber group";
  //   //      type union {
  //   //        type string {
  //   //          pattern "<.*>|$.*";
  //   //        }
  //   //        type uint32 {
  //   //          range "0 .. 4294967295";
  //   //        }
  //   //      }
  //   //    }
  //   //    leaf backup-tag {
  //   //      description "Route tag to advertise for the backup user-plane of the subscriber group";
  //   //      type union {
  //   //        type string {
  //   //          pattern "<.*>|$.*";
  //   //        }
  //   //        type uint32 {
  //   //          range "0 .. 4294967295";
  //   //        }
  //   //      }
  //   //    }
  //   //  }
  //   //  list address-pools {
  //   //    key name;
  //   //    ordered-by user;
  //   //    description "Address pools for subscribers";
  //   //    max-elements 10000;
  //   //    uses sm-ippool-pool;
  //   //  }
  //  }
  //  grouping dhcp-attribute-type {
  //    // uses apply-advanced;
  //    container option-match {
  //      description "Match";
  //      // uses apply-advanced;
  //      container option-82 {
  //        // uses apply-advanced;
  //        list circuit-id {
  //          key name;
  //          ordered-by user;
  //          description "Circuit ID portion of the option 82";
  //          leaf name {
  //            type string;
  //          }
  //          leaf range {
  //            description "Range name";
  //            type string;
  //          }
  //        }
  //        list remote-id {
  //          key name;
  //          ordered-by user;
  //          description "Remote ID portion of the option 82";
  //          leaf name {
  //            type string;
  //          }
  //          leaf range {
  //            description "Range name";
  //            type string;
  //          }
  //        }
  //      }
  //    }
  //    leaf maximum-lease-time {
  //      description "Maximum lease time advertised to clients";
  //      units "seconds";
  //      type string;
  //    }
  //    leaf next-server {
  //      description "Next server that clients need to contact";
  //      type jt:ipv4addr;
  //    }
  //    leaf server-identifier {
  //      description "Server Identifier - IP address value";
  //      type jt:ipv4addr;
  //    }
  //    leaf grace-period {
  //      description "Grace period for leases";
  //      units "seconds";
  //      type union {
  //        type uint32;
  //        type string {
  //          pattern "<.*>|$.*";
  //        }
  //      }
  //    }
  //    leaf domain-name {
  //      description "Domain name advertised to clients";
  //      type string {
  //      }
  //    }
  //    list name-server {
  //      key name;
  //      ordered-by user;
  //      description "Domain name servers available to the client";
  //      leaf name {
  //        description "DNS server's IPv4 address";
  //        type jt:ipv4addr;
  //      }
  //      // uses apply-advanced;
  //    }
  //    list wins-server {
  //      key name;
  //      ordered-by user;
  //      description "WINS name servers";
  //      leaf name {
  //        description "WINS server's IPv4 address";
  //        type jt:ipv4addr;
  //      }
  //      // uses apply-advanced;
  //    }
  //    list router {
  //      key name;
  //      description "Routers advertised to clients";
  //      leaf name {
  //        description "Router's IPv4 address";
  //        type jt:ipv4addr;
  //      }
  //      // uses apply-advanced;
  //    }
  //    leaf boot-file {
  //      description "Boot filename advertised to clients";
  //      type string;
  //    }
  //    leaf boot-server {
  //      description "Boot server advertised to clients";
  //      type string {
  //      }
  //    }
  //    leaf tftp-server {
  //      description "TFTP server IP address advertised to clients";
  //      type jt:ipv4addr;
  //    }
  //    container sip-server {
  //      description "SIP servers to clients";
  //      // uses apply-advanced;
  //      list name {
  //        key name;
  //        description "SIP server domain name available to clients";
  //        leaf name {
  //          description "SIP server name";
  //          type string;
  //        }
  //        // uses apply-advanced;
  //      }
  //      list ip-address {
  //        key name;
  //        description "SIP servers list of IPv4 addresses available to the client";
  //        leaf name {
  //          description "SIP server's IPv4 address";
  //          type jt:ipv4addr;
  //        }
  //        // uses apply-advanced;
  //      }
  //    }
  //    leaf netbios-node-type {
  //      description "Type of NETBIOS node advertised to clients";
  //      type enumeration {
  //        enum "b-node" {
  //          description "Broadcast node";
  //        }
  //        enum "p-node" {
  //          description "Peer-to-peer node";
  //        }
  //        enum "m-node" {
  //          description "Mixed Node";
  //        }
  //        enum "h-node" {
  //          description "Hybrid node";
  //        }
  //      }
  //    }
  //    leaf sip-server-domain-name {
  //      description "SIP server domain name available to clients";
  //      type string {
  //      }
  //    }
  //    list sip-server-address {
  //      key name;
  //      ordered-by user;
  //      description "SIP Servers list of IPv6 addresses available to the client";
  //      leaf name {
  //        description "SIP Server's IPv6 address";
  //        type jt:ipv6addr;
  //      }
  //      // uses apply-advanced;
  //    }
  //    list dns-server {
  //      key name;
  //      ordered-by user;
  //      description "Domain name servers available to the client";
  //      leaf name {
  //        description "DNS server's IPv6 address";
  //        type jt:ipv6addr;
  //      }
  //      // uses apply-advanced;
  //    }
  //    leaf propagate-settings {
  //      description "Interface name for propagating TCP/IP Settings to pool";
  //      type string;
  //    }
  //    leaf-list propagate-ppp-settings {
  //      ordered-by user;
  //      description "PPP interface name for propagating DNS/WINS settings";
  //      type union {
  //        type jt:interface-name;
  //        type string {
  //          pattern "<.*>|$.*";
  //        }
  //      }
  //      max-elements 8;
  //    }
  //    list option {
  //      key name;
  //      ordered-by user;
  //      description "DHCP option";
  //      leaf name {
  //        description "DHCP option identifier code";
  //        type union {
  //          type uint32;
  //          type string {
  //            pattern "<.*>|$.*";
  //          }
  //        }
  //      }
  //      choice option-type-choice {
  //        case case_1 {
  //          leaf flag {
  //            description "Boolean flag value";
  //            type enumeration {
  //              enum "true" {
  //                description "True value";
  //              }
  //              enum "false" {
  //                description "False value";
  //              }
  //              enum "on" {
  //                description "On value";
  //              }
  //              enum "off" {
  //                description "Off value";
  //              }
  //            }
  //          }
  //        }
  //        case case_2 {
  //          leaf byte {
  //            description "Unsigned 8-bit value";
  //            type union {
  //              type uint8;
  //              type string {
  //                pattern "<.*>|$.*";
  //              }
  //            }
  //          }
  //        }
  //        case case_3 {
  //          leaf short {
  //            description "Signed 16-bit numeric value";
  //            type union {
  //              type int16;
  //              type string {
  //                pattern "<.*>|$.*";
  //              }
  //            }
  //          }
  //        }
  //        case case_4 {
  //          leaf unsigned-short {
  //            description "Unsigned 16-bit numeric value";
  //            type union {
  //              type uint16;
  //              type string {
  //                pattern "<.*>|$.*";
  //              }
  //            }
  //          }
  //        }
  //        case case_5 {
  //          leaf integer {
  //            description "Signed 32-bit numeric value";
  //            type union {
  //              type int32;
  //              type string {
  //                pattern "<.*>|$.*";
  //              }
  //            }
  //          }
  //        }
  //        case case_6 {
  //          leaf unsigned-integer {
  //            description "Unsigned 32-bit numeric value";
  //            type union {
  //              type uint32;
  //              type string {
  //                pattern "<.*>|$.*";
  //              }
  //            }
  //          }
  //        }
  //        case case_7 {
  //          leaf hex-string {
  //            description "Hexadecimal string";
  //            type string {
  //              length "1 .. 510";
  //            }
  //          }
  //        }
  //        case case_8 {
  //          leaf string {
  //            description "Character string value";
  //            type string {
  //              length "1 .. 254";
  //            }
  //          }
  //        }
  //        case case_9 {
  //          leaf ip-address {
  //            description "IP address value";
  //            type jt:ipv4addr;
  //          }
  //        }
  //        case case_10 {
  //          leaf ipv6-address {
  //            description "IPV6 address value";
  //            type jt:ipv6addr;
  //          }
  //        }
  //        case case_11 {
  //          container array {
  //            presence "enable array";
  //            description "Array of values";
  //            // uses apply-advanced;
  //            choice option-type-array-choice {
  //              case case_1 {
  //                leaf-list flag {
  //                  ordered-by user;
  //                  description "Array of boolean flag values";
  //                  type enumeration {
  //                    enum "true" {
  //                      description "True value";
  //                    }
  //                    enum "false" {
  //                      description "False value";
  //                    }
  //                    enum "on" {
  //                      description "On value";
  //                    }
  //                    enum "off" {
  //                      description "Off value";
  //                    }
  //                  }
  //                }
  //              }
  //              case case_2 {
  //                leaf-list byte {
  //                  ordered-by user;
  //                  description "Array of unsigned 8-bit values";
  //                  type union {
  //                    type uint8;
  //                    type string {
  //                      pattern "<.*>|$.*";
  //                    }
  //                  }
  //                }
  //              }
  //              case case_3 {
  //                leaf-list short {
  //                  ordered-by user;
  //                  description "Array of signed 16-bit numeric values";
  //                  type union {
  //                    type int16;
  //                    type string {
  //                      pattern "<.*>|$.*";
  //                    }
  //                  }
  //                }
  //              }
  //              case case_4 {
  //                leaf-list unsigned-short {
  //                  ordered-by user;
  //                  description "Array of 16-bit numeric values";
  //                  type union {
  //                    type uint16;
  //                    type string {
  //                      pattern "<.*>|$.*";
  //                    }
  //                  }
  //                }
  //              }
  //              case case_5 {
  //                leaf-list integer {
  //                  ordered-by user;
  //                  description "Array of signed 32-bit numeric values";
  //                  type union {
  //                    type int32;
  //                    type string {
  //                      pattern "<.*>|$.*";
  //                    }
  //                  }
  //                }
  //              }
  //              case case_6 {
  //                leaf-list unsigned-integer {
  //                  ordered-by user;
  //                  description "Array of unsigned 32-bit numeric values";
  //                  type union {
  //                    type uint32;
  //                    type string {
  //                      pattern "<.*>|$.*";
  //                    }
  //                  }
  //                }
  //              }
  //              case case_7 {
  //                leaf-list hex-string {
  //                  ordered-by user;
  //                  description "Hexadecimal string";
  //                  type string {
  //                    length "1 .. 510";
  //                  }
  //                }
  //              }
  //              case case_8 {
  //                leaf-list string {
  //                  ordered-by user;
  //                  description "Array of character string values";
  //                  type string {
  //                    length "1 .. 254";
  //                  }
  //                }
  //              }
  //              case case_9 {
  //                leaf-list ip-address {
  //                  ordered-by user;
  //                  description "Array of IP address values";
  //                  type jt:ipv4addr;
  //                }
  //              }
  //              case case_10 {
  //                leaf-list ipv6-address {
  //                  ordered-by user;
  //                  description "Array of IPv6 address values";
  //                  type jt:ipv6addr;
  //                }
  //              }
  //            }
  //          }
  //        }
  //      }
  //    }
  //    leaf valid-lifetime {
  //      description "Valid lifetime advertised to clients";
  //      units "seconds";
  //      type string;
  //    }
  //    leaf preferred-lifetime {
  //      description "Preferred lifetime advertised to clients";
  //      units "seconds";
  //      type string;
  //    }
  //    leaf t1-percentage {
  //      description "T1 time as percentage of preferred lifetime or max lease";
  //      units "percent";
  //      type union {
  //        type string {
  //          pattern "<.*>|$.*";
  //        }
  //        type uint32 {
  //          range "0 .. 100";
  //        }
  //      }
  //    }
  //    leaf t2-percentage {
  //      description "T2 time as percentage of preferred lifetime or max lease";
  //      units "percent";
  //      type union {
  //        type string {
  //          pattern "<.*>|$.*";
  //        }
  //        type uint32 {
  //          range "0 .. 100";
  //        }
  //      }
  //    }
  //    leaf exclude-prefix-len {
  //      description "Length of IPv6 prefix to be excluded from delegated prefix";
  //      type union {
  //        type string {
  //          pattern "<.*>|$.*";
  //        }
  //        type uint32 {
  //          range "1 .. 128";
  //        }
  //      }
  //    }
  //    leaf t1-renewal-time {
  //      description "T1 renewal time";
  //      units "seconds";
  //      type union {
  //        type uint32;
  //        type string {
  //          pattern "<.*>|$.*";
  //        }
  //      }
  //    }
  //    leaf t2-rebinding-time {
  //      description "T2 rebinding time";
  //      units "seconds";
  //      type union {
  //        type uint32;
  //        type string {
  //          pattern "<.*>|$.*";
  //        }
  //      }
  //    }
  //  }
  //  grouping dynamic-dhcp-attribute-type {
  //    // uses apply-advanced;
  //    leaf maximum-lease-time {
  //      description "Maximum lease time advertised to clients";
  //      units "seconds";
  //      type string;
  //    }
  //    leaf valid-lifetime {
  //      description "Preferred lifetime";
  //      units "seconds";
  //      type string;
  //    }
  //    leaf preferred-lifetime {
  //      description "Preferred lifetime";
  //      units "seconds";
  //      type string;
  //    }
  //    list dns-server {
  //      key name;
  //      ordered-by user;
  //      description "Domain name servers available to the client";
  //      leaf name {
  //        description "DNS server's IPv6 address";
  //        type jt:ipv6addr;
  //      }
  //      // uses apply-advanced;
  //    }
  //    leaf t1-percentage {
  //      description "T1 time as percentage of preferred lifetime advertised to clients";
  //      units "percent";
  //      type union {
  //        type string {
  //          pattern "<.*>|$.*";
  //        }
  //        type uint32 {
  //          range "0 .. 100";
  //        }
  //      }
  //    }
  //    leaf t2-percentage {
  //      description "T2 time as percentage of preferred lifetime advertised to clients";
  //      units "percent";
  //      type union {
  //        type string {
  //          pattern "<.*>|$.*";
  //        }
  //        type uint32 {
  //          range "0 .. 100";
  //        }
  //      }
  //    }
  //  }
  //  grouping jdhcp-local-server-type {
  //    // uses apply-advanced;
  //    container traceoptions {
  //      description "DHCP local server trace options";
  //      status deprecated;
  //      uses jdhcp-traceoptions-type;
  //    }
  //    container interface-traceoptions {
  //      description "DHCP local server interface trace options";
  //      status deprecated;
  //      uses jdhcp-interface-traceoptions-type;
  //    }
  //    container dhcpv6 {
  //      description "DHCPv6 configuration";
  //      uses dhcpv6-local-server-type;
  //    }
  //    list pool-match-order {
  //      key name;
  //      ordered-by user;
  //      description "Define order of attribute matching for pool selection";
  //      leaf name {
  //        description "Match type";
  //        type enumeration {
  //          enum "external-authority" {
  //            description "External authority handles address selection";
  //          }
  //          enum "ip-address-first" {
  //            description "IP address used first to select a pool";
  //          }
  //          enum "option-82" {
  //            description "Option 82 used in matching of pool";
  //          }
  //          enum "option-82-strict" {
  //            description "Option 82 used in strict matching of pool";
  //          }
  //        }
  //      }
  //      // uses apply-advanced;
  //    }
  //    leaf duplicate-clients-on-interface {
  //      description "Allow duplicate clients on different interfaces in a subnet";
  //      status deprecated;
  //      type empty;
  //    }
  //    container duplicate-clients-in-subnet {
  //      description "Allow duplicate clients in a subnet";
  //      uses jdhcp-duplicate-clients-in-subnet-type;
  //    }
  //    container forward-snooped-clients {
  //      description "Forward snooped (unicast) packets";
  //      choice interface-type {
  //        case case_1 {
  //          leaf configured-interfaces {
  //            description "Forward snooped (unicast) packets on configured interfaces";
  //            type empty;
  //          }
  //        }
  //        case case_2 {
  //          leaf non-configured-interfaces {
  //            description "Forward snooped (unicast) packets on non-configured interfaces";
  //            type empty;
  //          }
  //        }
  //        case case_3 {
  //          leaf all-interfaces {
  //            description "Forward snooped (unicast) packets on configured and non-configured interfaces";
  //            type empty;
  //          }
  //        }
  //      }
  //    }
  //    container authentication {
  //      description "DHCP authentication";
  //      uses authentication-type;
  //    }
  //    container liveness-detection {
  //      description "DHCP client liveness detection processing";
  //      uses dhcp-liveness-detection-type;
  //    }
  //    container reconfigure {
  //      description "DHCP reconfigure processing";
  //      presence "enable reconfigure";
  //      uses reconfigure-type;
  //    }
  //    container overrides {
  //      description "DHCP override processing";
  //      presence "enable overrides";
  //      uses override-local-server-type;
  //    }
  //    container dynamic-profile {
  //      description "Dynamic profile to use";
  //      uses dynamic-profile-type;
  //    }
  //    leaf service-profile {
  //      description "Dynamic profile to use for default service activation";
  //      type string {
  //        length "1 .. 128";
  //      }
  //    }
  //    leaf access-profile {
  //      description "Access profile to use for AAA services";
  //      type string {
  //        length "1 .. 128";
  //      }
  //    }
  //    container short-cycle-protection {
  //      description "Short cycle lockout configuration";
  //      leaf lockout-min-time {
  //        description "Short cycle lockout time in seconds";
  //        type union {
  //          type string {
  //            pattern "<.*>|$.*";
  //          }
  //          type uint32 {
  //            range "1 .. 86400";
  //          }
  //        }
  //      }
  //      leaf lockout-max-time {
  //        description "Short cycle lockout time in seconds";
  //        type union {
  //          type string {
  //            pattern "<.*>|$.*";
  //          }
  //          type uint32 {
  //            range "1 .. 86400";
  //          }
  //        }
  //      }
  //    }
  //    container route-suppression {
  //      description "Suppress access-internal and/or destination route addition";
  //      uses dhcp-route-suppression-type;
  //    }
  //    list group {
  //      key name;
  //      description "Define a DHCP local server group";
  //      uses dhcp-local-server-group;
  //    }
  //    list dual-stack-group {
  //      key name;
  //      description "Define a DHCP dual stack group";
  //      uses dhcp-local-server-dual-stack-group;
  //    }
  //    container lease-time-validation {
  //      presence "enable lease-time-validation";
  //      description "Configure lease time violation validation";
  //      // uses apply-advanced;
  //      leaf lease-time-threshold {
  //        description "Threshold for lease time violation seconds";
  //        units "seconds";
  //        type union {
  //          type string {
  //            pattern "<.*>|$.*";
  //          }
  //          type uint32 {
  //            range "60 .. 2147483647";
  //          }
  //        }
  //      }
  //      container violation-action {
  //        description "Lease time validation violation action";
  //        choice violation-action-choice {
  //          case case_1 {
  //            leaf strict {
  //              description "Reject discover and renew";
  //              type empty;
  //            }
  //          }
  //          case case_2 {
  //            leaf override-lease {
  //              description "Override assigned lease time with threshold";
  //              type empty;
  //            }
  //          }
  //        }
  //      }
  //    }
  //    choice requested-ip-check {
  //      case case_1 {
  //        leaf requested-ip-network-match {
  //          description "Subnet to match server's address for active and giaddr for passive clients";
  //          default "8";
  //          type union {
  //            type string {
  //              pattern "<.*>|$.*";
  //            }
  //            type uint32 {
  //              range "0 .. 31";
  //            }
  //          }
  //        }
  //      }
  //      case case_2 {
  //        leaf requested-ip-interface-match {
  //          description "Use incoming-interface's subnet to check";
  //          type empty;
  //        }
  //      }
  //    }
  //    leaf no-snoop {
  //      description "Do not snoop DHCP packets";
  //      type empty;
  //    }
  //    container persistent-storage {
  //      description "Trigger to enable flat file storage";
  //      leaf automatic {
  //        description "Trigger automatically";
  //        type empty;
  //      }
  //    }
  //    container allow-leasequery {
  //      description "Allow DHCP leasequery";
  //      presence "enable allow-leasequery";
  //      uses server-leasequery-type;
  //    }
  //    container remote-id-mismatch {
  //      description "DHCP client remote-id mismatch";
  //      presence "enable remote-id-mismatch";
  //      uses dhcp-remote-id-mismatch-type;
  //    }
  //    container reauthenticate {
  //      presence "enable reauthenticate";
  //      description "DHCP client reauthenticate processing";
  //      // uses apply-advanced;
  //      leaf lease-renewal {
  //        description "Reauthenticate on each renew, rebind, DISCOVER or SOLICIT";
  //        type empty;
  //      }
  //      leaf remote-id-mismatch {
  //        description "Reauthenticate on remote-id mismatch for renew, rebind and re-negotiation";
  //        type empty;
  //      }
  //      container actual-data-rate-change {
  //        description "Reauthenticate on data rate change";
  //        uses actual-data-rate-change-type;
  //      }
  //    }
  //    container allow-bulk-leasequery {
  //      description "Allow DHCP bulk leasequery";
  //      presence "enable allow-bulk-leasequery";
  //      uses server-bulk-leasequery-type;
  //    }
  //    container allow-active-leasequery {
  //      description "Allow DHCP active leasequery";
  //      presence "enable allow-active-leasequery";
  //      uses server-active-leasequery-type;
  //    }
  //    container active-leasequery {
  //      description "DHCPv4 active leasequery configuration";
  //      presence "enable active-leasequery";
  //      uses active-leasequery-v4-type;
  //    }
  //  }
  //  grouping active-leasequery-v4-type {
  //    description "Configure active leasequery";
  //    // uses apply-advanced;
  //    leaf topology-discover {
  //      description "Topology discovery";
  //      type empty;
  //    }
  //    list peer-address {
  //      key name;
  //      description "Server ip address";
  //      leaf name {
  //        description "Peer ip address";
  //        type jt:ipaddr;
  //      }
  //      // uses apply-advanced;
  //    }
  //    leaf timeout {
  //      description "Read/write timeout in seconds";
  //      default "120";
  //      units "seconds";
  //      type union {
  //        type string {
  //          pattern "<.*>|$.*";
  //        }
  //        type uint32 {
  //          range "10 .. 3600";
  //        }
  //      }
  //    }
  //    leaf idle-timeout {
  //      description "Idle timeout in seconds";
  //      default "60";
  //      units "seconds";
  //      type union {
  //        type string {
  //          pattern "<.*>|$.*";
  //        }
  //        type uint32 {
  //          range "10 .. 3600";
  //        }
  //      }
  //    }
  //  }
  //  grouping actual-data-rate-change-type {
  //    description "Reauthenticate on data rate change processing";
  //    // uses apply-advanced;
  //    container actual-data-rate-upstream {
  //      description "Actual data rate upstream";
  //      presence "enable actual-data-rate-upstream";
  //      uses actual-data-rate-type;
  //    }
  //    container actual-data-rate-downstream {
  //      description "Actual data rate downstream";
  //      presence "enable actual-data-rate-downstream";
  //      uses actual-data-rate-type;
  //    }
  //  }
  //  grouping actual-data-rate-type {
  //    description "Actual data rate type processing";
  //    // uses apply-advanced;
  //    leaf threshold {
  //      description "Threshold in kbps";
  //      type union {
  //        type uint32;
  //        type string {
  //          pattern "<.*>|$.*";
  //        }
  //      }
  //    }
  //  }
  //  grouping authentication-type {
  //    description "DHCP authentication";
  //    // uses apply-advanced;
  //    leaf password {
  //      description "Username password to use";
  //      type string {
  //        length "1 .. 64";
  //      }
  //    }
  //    container username-include {
  //      description "Add username options";
  //      // uses apply-advanced;
  //      leaf delimiter {
  //        description "Change delimiter/separator character";
  //        type string {
  //          length 1;
  //        }
  //      }
  //      leaf domain-name {
  //        description "Add domain name";
  //        type string {
  //          length "1 .. 64";
  //        }
  //      }
  //      leaf user-prefix {
  //        description "Add user defined prefix";
  //        type string {
  //          length "1 .. 64";
  //        }
  //      }
  //      leaf mac-address {
  //        description "Include MAC address";
  //        type empty;
  //      }
  //      container option-82 {
  //        presence "enable option-82";
  //        description "Include option 82";
  //        leaf circuit-id {
  //          description "Include option 82 circuit-id (sub option 1)";
  //          type empty;
  //        }
  //        leaf remote-id {
  //          description "Include option 82 remote-id (sub option 2)";
  //          type empty;
  //        }
  //      }
  //      leaf logical-system-name {
  //        description "Include logical system name";
  //        type empty;
  //      }
  //      leaf routing-instance-name {
  //        description "Include routing instance name";
  //        type empty;
  //      }
  //      container client-id {
  //        presence "enable client-id";
  //        description "Include client ID";
  //        leaf exclude-headers {
  //          description "Exclude all the headers";
  //          type empty;
  //        }
  //        leaf use-automatic-ascii-hex-encoding {
  //          description "Use automatic ascii hex username encoding";
  //          type empty;
  //        }
  //      }
  //      leaf option-60 {
  //        description "Include option 60";
  //        type empty;
  //      }
  //      leaf circuit-type {
  //        description "Include circuit type";
  //        type empty;
  //      }
  //      leaf interface-name {
  //        description "Include interface name";
  //        type empty;
  //      }
  //      leaf interface-description {
  //        description "Include interface description";
  //        type enumeration {
  //          enum "device" {
  //            description "Add the device interface description";
  //          }
  //          enum "logical" {
  //            description "Add the logical interface description";
  //          }
  //        }
  //      }
  //      leaf vlan-tags {
  //        description "Include the vlan tag(s)";
  //        type empty;
  //      }
  //    }
  //  }
  //  grouping dhcp-liveness-detection-type {
  //    description "DHCP client liveness detection processing";
  //    // uses apply-advanced;
  //    container failure-action {
  //      description "Liveness detection failure action options";
  //      uses dhcp-liveness-detection-failure-action-type;
  //    }
  //    container method {
  //      description "Liveness detection method options";
  //      // uses apply-advanced;
  //      choice method-choice {
  //        case case_1 {
  //          container bfd {
  //            description "Bidirectional Forwarding Detection (BFD) options";
  //            uses dhcp-bfd-liveness-detection-type;
  //          }
  //        }
  //        case case_2 {
  //          container layer2-liveness-detection {
  //            description "Address resolution options";
  //            uses dhcp-arp-nud-liveness-detection-type;
  //          }
  //        }
  //      }
  //    }
  //  }
  //  grouping dhcp-arp-nud-liveness-detection-type {
  //    description "Address Resolution detection options";
  //    // uses apply-advanced;
  //    leaf transmit-interval {
  //      description "Transmit interval for address resolution";
  //      default "300";
  //      units "seconds";
  //      type union {
  //        type string {
  //          pattern "<.*>|$.*";
  //        }
  //        type uint32 {
  //          range "300 .. 1800";
  //        }
  //      }
  //    }
  //    leaf max-consecutive-retries {
  //      description "Retry attempts";
  //      default "3";
  //      type union {
  //        type string {
  //          pattern "<.*>|$.*";
  //        }
  //        type uint32 {
  //          range "3 .. 6";
  //        }
  //      }
  //    }
  //  }
  //  grouping dhcp-bfd-liveness-detection-type {
  //    description "Bidirectional Forwarding Detection (BFD) options";
  //    // uses apply-advanced;
  //    leaf version {
  //      description "BFD protocol version number";
  //      default "automatic";
  //      type enumeration {
  //        enum "0" {
  //          description "BFD version 0 (deprecated)";
  //        }
  //        enum "1" {
  //          description "BFD version 1";
  //        }
  //        enum "automatic" {
  //          description "Choose BFD version automatically";
  //        }
  //      }
  //    }
  //    leaf minimum-interval {
  //      description "Minimum transmit and receive interval";
  //      units "milliseconds";
  //      type union {
  //        type string {
  //          pattern "<.*>|$.*";
  //        }
  //        type uint32 {
  //          range "30000 .. 255000";
  //        }
  //      }
  //    }
  //    leaf minimum-transmit-interval {
  //      description "Minimum transmit interval";
  //      status deprecated;
  //      units "milliseconds";
  //      type union {
  //        type string {
  //          pattern "<.*>|$.*";
  //        }
  //        type uint32 {
  //          range "30000 .. 255000";
  //        }
  //      }
  //    }
  //    leaf minimum-receive-interval {
  //      description "Minimum receive interval";
  //      units "milliseconds";
  //      type union {
  //        type string {
  //          pattern "<.*>|$.*";
  //        }
  //        type uint32 {
  //          range "30000 .. 255000";
  //        }
  //      }
  //    }
  //    leaf multiplier {
  //      description "Detection time multiplier";
  //      default "3";
  //      type union {
  //        type string {
  //          pattern "<.*>|$.*";
  //        }
  //        type uint32 {
  //          range "1 .. 255";
  //        }
  //      }
  //    }
  //    leaf inline-disable {
  //      description "Disable inline mode for this BFD session";
  //      type empty;
  //    }
  //    leaf pdu-size {
  //      description "BFD transport protocol payload size";
  //      default "24";
  //      type union {
  //        type string {
  //          pattern "<.*>|$.*";
  //        }
  //        type uint32 {
  //          range "24 .. 9000";
  //        }
  //      }
  //    }
  //    choice adaptation-choice {
  //      case case_1 {
  //        leaf no-adaptation {
  //          description "Disable adaptation";
  //          type empty;
  //        }
  //      }
  //    }
  //    container transmit-interval {
  //      description "Transmit-interval options";
  //      // uses apply-advanced;
  //      leaf minimum-interval {
  //        description "Minimum transmit interval";
  //        units "milliseconds";
  //        type union {
  //          type string {
  //            pattern "<.*>|$.*";
  //          }
  //          type uint32 {
  //            range "30000 .. 255000";
  //          }
  //        }
  //      }
  //      leaf threshold {
  //        description "High transmit interval triggering a trap";
  //        units "milliseconds";
  //        type union {
  //          type uint32;
  //          type string {
  //            pattern "<.*>|$.*";
  //          }
  //        }
  //      }
  //    }
  //    container detection-time {
  //      description "Detection-time options";
  //      // uses apply-advanced;
  //      leaf threshold {
  //        description "High detection-time triggering a trap";
  //        units "milliseconds";
  //        type union {
  //          type uint32;
  //          type string {
  //            pattern "<.*>|$.*";
  //          }
  //        }
  //      }
  //    }
  //    leaf session-mode {
  //      description "BFD single-hop or multihop session-mode";
  //      default "automatic";
  //      type enumeration {
  //        enum "automatic" {
  //          description "Choose session-mode automatically";
  //        }
  //        enum "single-hop" {
  //          description "Use single-hop";
  //        }
  //        enum "multihop" {
  //          description "Use multihop";
  //        }
  //      }
  //    }
  //    leaf holddown-interval {
  //      description "Time to hold the session-UP notification to the client";
  //      default "0";
  //      units "milliseconds";
  //      type union {
  //        type string {
  //          pattern "<.*>|$.*";
  //        }
  //        type uint32 {
  //          range "0 .. 255000";
  //        }
  //      }
  //    }
  //  }
  //  grouping dhcp-liveness-detection-failure-action-type {
  //    description "Liveness detection failure action options";
  //    // uses apply-advanced;
  //    choice failure-action-type {
  //      case case_1 {
  //        leaf clear-binding {
  //          description "Clear the client binding";
  //          type empty;
  //        }
  //      }
  //      case case_2 {
  //        leaf clear-binding-if-interface-up {
  //          description "Clear the client binding only if the incoming interface is up";
  //          type empty;
  //        }
  //      }
  //      case case_3 {
  //        leaf log-only {
  //          description "Maintain the client binding and log the failure event";
  //          type empty;
  //        }
  //      }
  //    }
  //  }
  //  grouping dhcp-local-server-dual-stack-group {
  //    description "DHCP dual stack groups";
  //    leaf name {
  //      description "Dual stack group name";
  //      type string {
  //        length "1 .. 64";
  //      }
  //    }
  //    // uses apply-advanced;
  //    container authentication {
  //      description "DHCP authentication";
  //      uses dual-stack-authentication-type;
  //    }
  //    leaf access-profile {
  //      description "Access profile to be used for jdhcpd";
  //      type string {
  //        length "1 .. 128";
  //      }
  //    }
  //    container dynamic-profile {
  //      description "Dynamic profile to use";
  //      uses dynamic-profile-type;
  //    }
  //    leaf service-profile {
  //      description "Dynamic profile to use for default service activation";
  //      type string {
  //        length "1 .. 128";
  //      }
  //    }
  //    leaf on-demand-address-allocation {
  //      description "Allocate addresses on demand";
  //      type empty;
  //    }
  //    container classification-key {
  //      description "Classification key for identifying dual stack household";
  //      uses classification-types;
  //    }
  //    leaf dual-stack-interface-client-limit {
  //      description "Limit the number of client allowed on an interface";
  //      type union {
  //        type string {
  //          pattern "<.*>|$.*";
  //        }
  //        type uint32 {
  //          range "1 .. 500000";
  //        }
  //      }
  //    }
  //    container protocol-master {
  //      description "Select family as protocol master";
  //      uses jdhcp-dual-stack-protocol-mstr-type;
  //    }
  //    container liveness-detection {
  //      description "DHCP client liveness detection processing";
  //      uses dhcp-liveness-detection-dualstack-type;
  //    }
  //    container reauthenticate {
  //      description "DHCP client reauthenticate processing";
  //      leaf lease-renewal {
  //        description "Reauthenticate on each renew, rebind, DISCOVER or SOLICIT";
  //        type empty;
  //      }
  //      leaf remote-id-mismatch {
  //        description "Reauthenticate on remote-id mismatch for renew, rebind and re-negotiation";
  //        type empty;
  //      }
  //    }
  //    container short-cycle-protection {
  //      description "Short cycle lockout configuration";
  //      leaf lockout-min-time {
  //        description "Short cycle lockout time in seconds";
  //        type union {
  //          type string {
  //            pattern "<.*>|$.*";
  //          }
  //          type uint32 {
  //            range "1 .. 86400";
  //          }
  //        }
  //      }
  //      leaf lockout-max-time {
  //        description "Short cycle lockout time in seconds";
  //        type union {
  //          type string {
  //            pattern "<.*>|$.*";
  //          }
  //          type uint32 {
  //            range "1 .. 86400";
  //          }
  //        }
  //      }
  //    }
  //  }
  //  grouping classification-types {
  //    description "Different mechanisms to identify a single household";
  //    // uses apply-advanced;
  //    leaf mac-address {
  //      description "MAC address of client";
  //      type empty;
  //    }
  //    leaf circuit-id {
  //      description "Circuit-id as key";
  //      type empty;
  //    }
  //    leaf remote-id {
  //      description "Remote-id as key";
  //      type empty;
  //    }
  //  }
  //  grouping dhcp-liveness-detection-dualstack-type {
  //    description "DHCP client liveness detection processing";
  //    // uses apply-advanced;
  //    container failure-action {
  //      description "Liveness detection failure action options";
  //      uses dhcp-liveness-detection-failure-action-type;
  //    }
  //    container method {
  //      description "Liveness detection method options";
  //      // uses apply-advanced;
  //      choice method-choice {
  //        case case_1 {
  //          container layer2-liveness-detection {
  //            description "Address resolution options";
  //            uses dhcp-arp-nud-liveness-detection-type;
  //          }
  //        }
  //      }
  //    }
  //  }
  //  grouping dhcp-local-server-group {
  //    description "DHCP groups";
  //    leaf name {
  //      description "Group name";
  //      type string {
  //        length "1 .. 64";
  //      }
  //    }
  //    // uses apply-advanced;
  //    container authentication {
  //      description "DHCP authentication";
  //      uses authentication-type;
  //    }
  //    container liveness-detection {
  //      description "DHCP client liveness detection processing";
  //      uses dhcp-liveness-detection-type;
  //    }
  //    container reconfigure {
  //      description "DHCP reconfigure processing";
  //      presence "enable reconfigure";
  //      uses reconfigure-type;
  //    }
  //    container overrides {
  //      description "DHCP override processing";
  //      presence "enable overrides";
  //      uses override-local-server-type;
  //    }
  //    container dynamic-profile {
  //      description "Dynamic profile to use";
  //      uses dynamic-profile-type;
  //    }
  //    leaf service-profile {
  //      description "Dynamic profile to use for default service activation";
  //      type string {
  //        length "1 .. 128";
  //      }
  //    }
  //    leaf access-profile {
  //      description "Access profile to use for AAA services";
  //      type string {
  //        length "1 .. 128";
  //      }
  //    }
  //    container short-cycle-protection {
  //      description "Short cycle lockout configuration";
  //      leaf lockout-min-time {
  //        description "Short cycle lockout time in seconds";
  //        type union {
  //          type string {
  //            pattern "<.*>|$.*";
  //          }
  //          type uint32 {
  //            range "1 .. 86400";
  //          }
  //        }
  //      }
  //      leaf lockout-max-time {
  //        description "Short cycle lockout time in seconds";
  //        type union {
  //          type string {
  //            pattern "<.*>|$.*";
  //          }
  //          type uint32 {
  //            range "1 .. 86400";
  //          }
  //        }
  //      }
  //    }
  //    container route-suppression {
  //      description "Suppress access-internal and/or destination route addition";
  //      uses dhcp-route-suppression-type;
  //    }
  //    list interface {
  //      key name;
  //      description "One or more interfaces";
  //      leaf name {
  //        description "Interface name";
  //        type union {
  //          type jt:interface-name;
  //          type string {
  //            pattern "<.*>|$.*";
  //          }
  //        }
  //      }
  //      // uses apply-advanced;
  //      leaf upto {
  //        description "Interface up to";
  //        type union {
  //          type jt:interface-name;
  //          type string {
  //            pattern "<.*>|$.*";
  //          }
  //        }
  //      }
  //      leaf exclude {
  //        description "Exclude this interface range";
  //        type empty;
  //      }
  //      leaf trace {
  //        description "Enable tracing for this interface";
  //        type empty;
  //      }
  //      container overrides {
  //        description "DHCP override processing";
  //        uses override-local-server-type;
  //      }
  //      container dynamic-profile {
  //        description "Dynamic profile to use";
  //        uses dynamic-profile-type;
  //      }
  //      leaf service-profile {
  //        description "Dynamic profile to use for default service activation";
  //        type string {
  //          length "1 .. 128";
  //        }
  //      }
  //      leaf access-profile {
  //        description "Access profile to use for AAA services";
  //        type string {
  //          length "1 .. 128";
  //        }
  //      }
  //      container short-cycle-protection {
  //        description "Short cycle lockout configuration";
  //        leaf lockout-min-time {
  //          description "Short cycle lockout time in seconds";
  //          type union {
  //            type string {
  //              pattern "<.*>|$.*";
  //            }
  //            type uint32 {
  //              range "1 .. 86400";
  //            }
  //          }
  //        }
  //        leaf lockout-max-time {
  //          description "Short cycle lockout time in seconds";
  //          type union {
  //            type string {
  //              pattern "<.*>|$.*";
  //            }
  //            type uint32 {
  //              range "1 .. 86400";
  //            }
  //          }
  //        }
  //      }
  //    }
  //    list interface-tag {
  //      key name;
  //      description "Interface tag configuration";
  //      leaf name {
  //        description "Interface tag name";
  //        type string {
  //          length "1 .. 64";
  //        }
  //      }
  //      // uses apply-advanced;
  //      container overrides {
  //        description "DHCP override processing";
  //        uses override-local-server-type;
  //      }
  //      container dynamic-profile {
  //        description "Dynamic profile to use";
  //        uses dynamic-profile-type;
  //      }
  //      leaf service-profile {
  //        description "Dynamic profile to use for default service activation";
  //        type string {
  //          length "1 .. 128";
  //        }
  //      }
  //      leaf access-profile {
  //        description "Access profile to use for AAA services";
  //        type string {
  //          length "1 .. 128";
  //        }
  //      }
  //      container short-cycle-protection {
  //        description "Short cycle lockout configuration";
  //        leaf lockout-min-time {
  //          description "Short cycle lockout time in seconds";
  //          type union {
  //            type string {
  //              pattern "<.*>|$.*";
  //            }
  //            type uint32 {
  //              range "1 .. 86400";
  //            }
  //          }
  //        }
  //        leaf lockout-max-time {
  //          description "Short cycle lockout time in seconds";
  //          type union {
  //            type string {
  //              pattern "<.*>|$.*";
  //            }
  //            type uint32 {
  //              range "1 .. 86400";
  //            }
  //          }
  //        }
  //      }
  //    }
  //    container lease-time-validation {
  //      presence "enable lease-time-validation";
  //      description "Configure lease time violation validation";
  //      // uses apply-advanced;
  //      leaf lease-time-threshold {
  //        description "Threshold for lease time violation seconds";
  //        units "seconds";
  //        type union {
  //          type string {
  //            pattern "<.*>|$.*";
  //          }
  //          type uint32 {
  //            range "60 .. 2147483647";
  //          }
  //        }
  //      }
  //      container violation-action {
  //        description "Lease time validation violation action";
  //        choice violation-action-choice {
  //          case case_1 {
  //            leaf strict {
  //              description "Reject discover and renew";
  //              type empty;
  //            }
  //          }
  //          case case_2 {
  //            leaf override-lease {
  //              description "Override assigned lease time with threshold";
  //              type empty;
  //            }
  //          }
  //        }
  //      }
  //    }
  //    container remote-id-mismatch {
  //      description "DHCP client remote-id mismatch";
  //      presence "enable remote-id-mismatch";
  //      uses dhcp-remote-id-mismatch-type;
  //    }
  //    container reauthenticate {
  //      presence "enable reauthenticate";
  //      description "DHCP client reauthenticate processing";
  //      // uses apply-advanced;
  //      leaf lease-renewal {
  //        description "Reauthenticate on each renew, rebind, DISCOVER or SOLICIT";
  //        type empty;
  //      }
  //      leaf remote-id-mismatch {
  //        description "Reauthenticate on remote-id mismatch for renew, rebind and re-negotiation";
  //        type empty;
  //      }
  //      container actual-data-rate-change {
  //        description "Reauthenticate on data rate change";
  //        uses actual-data-rate-change-type;
  //      }
  //    }
  //  }
  //  grouping dhcp-remote-id-mismatch-type {
  //    description "DHCP client remote-id-mismatch processing";
  //    // uses apply-advanced;
  //    leaf disconnect {
  //      description "Disconnect session on remote-id mismatch";
  //      type empty;
  //    }
  //  }
  //  grouping dhcp-route-suppression-type {
  //    // uses apply-advanced;
  //    choice dhcp-route-suppression-choice {
  //      case case_1 {
  //        leaf access-internal {
  //          description "Suppress access-internal and destination route addition";
  //          type empty;
  //        }
  //      }
  //      case case_2 {
  //        leaf destination {
  //          description "Suppress destination route addition";
  //          type empty;
  //        }
  //      }
  //    }
  //  }
  //  grouping dhcpv6-local-server-type {
  //    // uses apply-advanced;
  //    container authentication {
  //      description "DHCPv6 authentication";
  //      uses dhcpv6-authentication-type;
  //    }
  //    container liveness-detection {
  //      description "DHCPv6 client liveness detection processing";
  //      uses dhcpv6-liveness-detection-type;
  //    }
  //    container reconfigure {
  //      description "DHCPv6 reconfigure processing";
  //      presence "enable reconfigure";
  //      uses dhcpv6-reconfigure-type;
  //    }
  //    container dynamic-profile {
  //      description "Dynamic profile to use";
  //      uses dynamic-profile-type;
  //    }
  //    container forward-snooped-clients {
  //      description "Forward snooped (unicast) packets";
  //      choice interface-type {
  //        case case_1 {
  //          leaf configured-interfaces {
  //            description "Forward snooped (unicast) packets on configured interfaces";
  //            type empty;
  //          }
  //        }
  //        case case_2 {
  //          leaf non-configured-interfaces {
  //            description "Forward snooped (unicast) packets on non-configured interfaces";
  //            type empty;
  //          }
  //        }
  //        case case_3 {
  //          leaf all-interfaces {
  //            description "Forward snooped (unicast) packets on configured and non-configured interfaces";
  //            type empty;
  //          }
  //        }
  //      }
  //    }
  //    leaf service-profile {
  //      description "Dynamic profile to use for default service activation";
  //      type string {
  //        length "1 .. 128";
  //      }
  //    }
  //    leaf access-profile {
  //      description "Access profile to use for AAA services";
  //      type string {
  //        length "1 .. 128";
  //      }
  //    }
  //    container short-cycle-protection {
  //      description "Short cycle lockout configuration";
  //      leaf lockout-min-time {
  //        description "Short cycle lockout time in seconds";
  //        type union {
  //          type string {
  //            pattern "<.*>|$.*";
  //          }
  //          type uint32 {
  //            range "1 .. 86400";
  //          }
  //        }
  //      }
  //      leaf lockout-max-time {
  //        description "Short cycle lockout time in seconds";
  //        type union {
  //          type string {
  //            pattern "<.*>|$.*";
  //          }
  //          type uint32 {
  //            range "1 .. 86400";
  //          }
  //        }
  //      }
  //    }
  //    container overrides {
  //      description "DHCPv6 override processing";
  //      presence "enable overrides";
  //      uses dhcpv6-override-local-server-type;
  //    }
  //    container route-suppression {
  //      description "Suppress access-internal and/or access route addition";
  //      uses dhcpv6-route-suppression-type;
  //    }
  //    list group {
  //      key name;
  //      description "Define a DHCPv6 local server group";
  //      uses dhcpv6-local-server-group;
  //    }
  //    container lease-time-validation {
  //      presence "enable lease-time-validation";
  //      description "Configure lease time violation validation";
  //      // uses apply-advanced;
  //      leaf lease-time-threshold {
  //        description "Threshold for lease time violation seconds";
  //        units "seconds";
  //        type union {
  //          type string {
  //            pattern "<.*>|$.*";
  //          }
  //          type uint32 {
  //            range "60 .. 2147483647";
  //          }
  //        }
  //      }
  //      container violation-action {
  //        description "Lease time validation violation action";
  //        choice violation-action-choice {
  //          case case_1 {
  //            leaf strict {
  //              description "Reject solicit and renew";
  //              type empty;
  //            }
  //          }
  //          case case_2 {
  //            leaf override-lease {
  //              description "Override assigned lease time with threshold";
  //              type empty;
  //            }
  //          }
  //        }
  //      }
  //    }
  //    choice requested-ip-check {
  //      case case_1 {
  //        leaf requested-ip-network-match {
  //          description "Subnet to match server's address for active and link-address for passive clients";
  //          default "16";
  //          type union {
  //            type string {
  //              pattern "<.*>|$.*";
  //            }
  //            type uint32 {
  //              range "0 .. 127";
  //            }
  //          }
  //        }
  //      }
  //      case case_2 {
  //        leaf requested-ip-interface-match {
  //          description "Use incoming-interface's subnet to check";
  //          type empty;
  //        }
  //      }
  //    }
  //    leaf no-snoop {
  //      description "Do not snoop DHCPV6 packets";
  //      type empty;
  //    }
  //    container persistent-storage {
  //      description "Trigger to enable flat file storage";
  //      leaf automatic {
  //        description "Trigger automatically";
  //        type empty;
  //      }
  //    }
  //    container server-duid-type {
  //      description "Define the DUID type to be used as the Server ID. Type supported is DUID-LL";
  //      uses duid-type;
  //    }
  //    container remote-id-mismatch {
  //      description "DHCP client remote-id mismatch";
  //      presence "enable remote-id-mismatch";
  //      uses dhcp-remote-id-mismatch-type;
  //    }
  //    container reauthenticate {
  //      description "DHCP client reauthenticate processing";
  //      leaf lease-renewal {
  //        description "Reauthenticate on each renew, rebind, DISCOVER or SOLICIT";
  //        type empty;
  //      }
  //      leaf remote-id-mismatch {
  //        description "Reauthenticate on remote-id mismatch for renew, rebind and re-negotiation";
  //        type empty;
  //      }
  //    }
  //    container allow-leasequery {
  //      description "Allow DHCPv6 leasequery";
  //      presence "enable allow-leasequery";
  //      uses server-leasequery-type;
  //    }
  //    container allow-bulk-leasequery {
  //      description "Allow DHCPv6 bulk leasequery";
  //      presence "enable allow-bulk-leasequery";
  //      uses server-bulk-leasequery-type;
  //    }
  //    container allow-active-leasequery {
  //      description "Allow DHCPv6 active leasequery";
  //      presence "enable allow-active-leasequery";
  //      uses server-active-leasequery-type;
  //    }
  //    container duplicate-clients {
  //      description "Allow duplicate clients";
  //      uses dhcpv6-duplicate-clients-type;
  //    }
  //    container dynamic-server {
  //      description "DHCPv6 dynamic server configuration";
  //      uses dhcpv6-dynamic-server-type;
  //    }
  //    container active-leasequery {
  //      description "DHCPv6 active leasequery configuration";
  //      presence "enable active-leasequery";
  //      uses active-leasequery-v6-type;
  //    }
  //  }
  //  grouping active-leasequery-v6-type {
  //    description "Configure active leasequery";
  //    // uses apply-advanced;
  //    leaf topology-discover {
  //      description "Topology discovery";
  //      type empty;
  //    }
  //    leaf timeout {
  //      description "Read/write timeout in seconds";
  //      default "120";
  //      units "seconds";
  //      type union {
  //        type string {
  //          pattern "<.*>|$.*";
  //        }
  //        type uint32 {
  //          range "10 .. 3600";
  //        }
  //      }
  //    }
  //    leaf idle-timeout {
  //      description "Idle timeout in seconds";
  //      default "60";
  //      units "seconds";
  //      type union {
  //        type string {
  //          pattern "<.*>|$.*";
  //        }
  //        type uint32 {
  //          range "10 .. 3600";
  //        }
  //      }
  //    }
  //    list peer-address {
  //      key name;
  //      description "Peer ipv6 address";
  //      leaf name {
  //        description "Peer ipv6 address";
  //        type jt:ipv6addr;
  //      }
  //      // uses apply-advanced;
  //    }
  //  }
  //  grouping dhcpv6-authentication-type {
  //    description "DHCPv6 authentication";
  //    // uses apply-advanced;
  //    leaf password {
  //      description "Username password to use";
  //      type string {
  //        length "1 .. 64";
  //      }
  //    }
  //    container username-include {
  //      description "Add username options";
  //      // uses apply-advanced;
  //      leaf delimiter {
  //        description "Change delimiter/separator character";
  //        type string {
  //          length 1;
  //        }
  //      }
  //      leaf domain-name {
  //        description "Add domain name";
  //        type string {
  //          length "1 .. 64";
  //        }
  //      }
  //      leaf user-prefix {
  //        description "Add user defined prefix";
  //        type string {
  //          length "1 .. 64";
  //        }
  //      }
  //      leaf mac-address {
  //        description "Include MAC address";
  //        type empty;
  //      }
  //      container client-id {
  //        presence "enable client-id";
  //        description "Include client ID";
  //        leaf exclude-headers {
  //          description "Exclude all the headers";
  //          type empty;
  //        }
  //        leaf use-automatic-ascii-hex-encoding {
  //          description "Use automatic ascii hex username encoding";
  //          type empty;
  //        }
  //      }
  //      container relay-agent-remote-id {
  //        presence "enable relay-agent-remote-id";
  //        description "Include the relay agent remote ID";
  //        // uses apply-advanced;
  //        choice relay-agent-remote-id-choice {
  //          case case_1 {
  //            leaf enterprise-id {
  //              description "Only use enterprise-id portion of option-37";
  //              status deprecated;
  //              type empty;
  //            }
  //          }
  //          case case_2 {
  //            leaf remote-id {
  //              description "Only use remote-id portion of option-37";
  //              status deprecated;
  //              type empty;
  //            }
  //          }
  //        }
  //      }
  //      leaf logical-system-name {
  //        description "Include logical system name";
  //        type empty;
  //      }
  //      leaf routing-instance-name {
  //        description "Include routing instance name";
  //        type empty;
  //      }
  //      leaf relay-agent-subscriber-id {
  //        description "Include the relay agent subscriber ID";
  //        type empty;
  //      }
  //      leaf relay-agent-interface-id {
  //        description "Include the relay agent interface ID";
  //        type empty;
  //      }
  //      leaf circuit-type {
  //        description "Include circuit type";
  //        type empty;
  //      }
  //      leaf interface-name {
  //        description "Include interface name";
  //        type empty;
  //      }
  //      leaf interface-description {
  //        description "Include interface description";
  //        type enumeration {
  //          enum "device" {
  //            description "Add the device interface description";
  //          }
  //          enum "logical" {
  //            description "Add the logical interface description";
  //          }
  //        }
  //      }
  //      leaf vlan-tags {
  //        description "Include the vlan tag(s)";
  //        type empty;
  //      }
  //    }
  //  }
  //  grouping dhcpv6-duplicate-clients-type {
  //    description "Allow duplicate clients";
  //    choice distinguish-with {
  //      case case_1 {
  //        leaf incoming-interface {
  //          description "Allow duplicate clients on different underlying interfaces";
  //          type empty;
  //        }
  //      }
  //    }
  //  }
  //  grouping dhcpv6-dynamic-server-type {
  //    // uses apply-advanced;
  //    container overrides {
  //      description "DHCPv6 override processing";
  //      presence "enable overrides";
  //      uses dhcpv6-override-dynamic-server-type;
  //    }
  //    list group {
  //      key name;
  //      description "Define a DHCPv6 dynamic server group";
  //      uses dhcpv6-dynamic-server-group;
  //    }
  //  }
  //  grouping dhcpv6-dynamic-server-group {
  //    description "DHCP dynamic server groups";
  //    leaf name {
  //      description "Group name";
  //      type string {
  //        length "1 .. 64";
  //      }
  //    }
  //    // uses apply-advanced;
  //    leaf neighbor-discovery-router-advertisement {
  //      description "Designated NDRA pool for this group";
  //      type string {
  //        length "1 .. 64";
  //      }
  //    }
  //    container overrides {
  //      description "DHCP override processing";
  //      presence "enable overrides";
  //      uses dhcpv6-override-dynamic-server-type;
  //    }
  //    list interface {
  //      key name;
  //      description "One or more interfaces";
  //      leaf name {
  //        description "Interface name";
  //        type union {
  //          type jt:interface-name;
  //          type string {
  //            pattern "<.*>|$.*";
  //          }
  //        }
  //      }
  //      // uses apply-advanced;
  //      container overrides {
  //        description "DHCP override processing";
  //        uses dhcpv6-override-dynamic-server-type;
  //      }
  //    }
  //  }
  //  grouping dhcpv6-liveness-detection-type {
  //    description "DHCPv6 client liveness detection processing";
  //    // uses apply-advanced;
  //    container failure-action {
  //      description "Liveness detection failure action options";
  //      uses dhcp-liveness-detection-failure-action-type;
  //    }
  //    container method {
  //      description "Liveness detection method options";
  //      // uses apply-advanced;
  //      choice method-choice {
  //        case case_1 {
  //          container bfd {
  //            description "Bidirectional Forwarding Detection (BFD) options";
  //            uses dhcp-bfd-liveness-detection-type;
  //          }
  //        }
  //        case case_2 {
  //          container layer2-liveness-detection {
  //            description "Neighbor discovery options";
  //            uses dhcp-arp-nud-liveness-detection-type;
  //          }
  //        }
  //      }
  //    }
  //  }
  //  grouping dhcpv6-local-server-group {
  //    description "DHCP groups";
  //    leaf name {
  //      description "Group name";
  //      type string {
  //        length "1 .. 64";
  //      }
  //    }
  //    // uses apply-advanced;
  //    container authentication {
  //      description "DHCP authentication";
  //      uses dhcpv6-authentication-type;
  //    }
  //    container liveness-detection {
  //      description "DHCPv6 client liveness detection processing";
  //      uses dhcpv6-liveness-detection-type;
  //    }
  //    container reconfigure {
  //      description "DHCPv6 reconfigure processing";
  //      presence "enable reconfigure";
  //      uses dhcpv6-reconfigure-type;
  //    }
  //    container dynamic-profile {
  //      description "Dynamic profile to use";
  //      uses dynamic-profile-type;
  //    }
  //    leaf service-profile {
  //      description "Dynamic profile to use for default service activation";
  //      type string {
  //        length "1 .. 128";
  //      }
  //    }
  //    leaf access-profile {
  //      description "Access profile to use for AAA services";
  //      type string {
  //        length "1 .. 128";
  //      }
  //    }
  //    container short-cycle-protection {
  //      description "Short cycle lockout configuration";
  //      leaf lockout-min-time {
  //        description "Short cycle lockout time in seconds";
  //        type union {
  //          type string {
  //            pattern "<.*>|$.*";
  //          }
  //          type uint32 {
  //            range "1 .. 86400";
  //          }
  //        }
  //      }
  //      leaf lockout-max-time {
  //        description "Short cycle lockout time in seconds";
  //        type union {
  //          type string {
  //            pattern "<.*>|$.*";
  //          }
  //          type uint32 {
  //            range "1 .. 86400";
  //          }
  //        }
  //      }
  //    }
  //    container overrides {
  //      description "DHCP override processing";
  //      presence "enable overrides";
  //      uses dhcpv6-override-local-server-type;
  //    }
  //    container route-suppression {
  //      description "Suppress access-internal and/or access route addition";
  //      uses dhcpv6-route-suppression-type;
  //    }
  //    list interface {
  //      key name;
  //      description "One or more interfaces";
  //      leaf name {
  //        description "Interface name";
  //        type union {
  //          type jt:interface-name;
  //          type string {
  //            pattern "<.*>|$.*";
  //          }
  //        }
  //      }
  //      // uses apply-advanced;
  //      leaf upto {
  //        description "Interface up to";
  //        type union {
  //          type jt:interface-name;
  //          type string {
  //            pattern "<.*>|$.*";
  //          }
  //        }
  //      }
  //      leaf exclude {
  //        description "Exclude this interface range";
  //        type empty;
  //      }
  //      leaf trace {
  //        description "Enable tracing for this interface";
  //        type empty;
  //      }
  //      container overrides {
  //        description "DHCP override processing";
  //        uses dhcpv6-override-local-server-type;
  //      }
  //      container dynamic-profile {
  //        description "Dynamic profile to use";
  //        uses dynamic-profile-type;
  //      }
  //      leaf service-profile {
  //        description "Dynamic profile to use for default service activation";
  //        type string {
  //          length "1 .. 128";
  //        }
  //      }
  //      leaf access-profile {
  //        description "Access profile to use for AAA services";
  //        type string {
  //          length "1 .. 128";
  //        }
  //      }
  //      container short-cycle-protection {
  //        description "Short cycle lockout configuration";
  //        leaf lockout-min-time {
  //          description "Short cycle lockout time in seconds";
  //          type union {
  //            type string {
  //              pattern "<.*>|$.*";
  //            }
  //            type uint32 {
  //              range "1 .. 86400";
  //            }
  //          }
  //        }
  //        leaf lockout-max-time {
  //          description "Short cycle lockout time in seconds";
  //          type union {
  //            type string {
  //              pattern "<.*>|$.*";
  //            }
  //            type uint32 {
  //              range "1 .. 86400";
  //            }
  //          }
  //        }
  //      }
  //    }
  //    list interface-tag {
  //      key name;
  //      description "Interface tag configuration";
  //      leaf name {
  //        description "Interface tag name";
  //        type string {
  //          length "1 .. 64";
  //        }
  //      }
  //      // uses apply-advanced;
  //      container overrides {
  //        description "DHCP override processing";
  //        uses dhcpv6-override-local-server-type;
  //      }
  //      container dynamic-profile {
  //        description "Dynamic profile to use";
  //        uses dynamic-profile-type;
  //      }
  //      leaf service-profile {
  //        description "Dynamic profile to use for default service activation";
  //        type string {
  //          length "1 .. 128";
  //        }
  //      }
  //      leaf access-profile {
  //        description "Access profile to use for AAA services";
  //        type string {
  //          length "1 .. 128";
  //        }
  //      }
  //      container short-cycle-protection {
  //        description "Short cycle lockout configuration";
  //        leaf lockout-min-time {
  //          description "Short cycle lockout time in seconds";
  //          type union {
  //            type string {
  //              pattern "<.*>|$.*";
  //            }
  //            type uint32 {
  //              range "1 .. 86400";
  //            }
  //          }
  //        }
  //        leaf lockout-max-time {
  //          description "Short cycle lockout time in seconds";
  //          type union {
  //            type string {
  //              pattern "<.*>|$.*";
  //            }
  //            type uint32 {
  //              range "1 .. 86400";
  //            }
  //          }
  //        }
  //      }
  //    }
  //    container lease-time-validation {
  //      presence "enable lease-time-validation";
  //      description "Configure lease time violation validation";
  //      // uses apply-advanced;
  //      leaf lease-time-threshold {
  //        description "Threshold for lease time violation seconds";
  //        units "seconds";
  //        type union {
  //          type string {
  //            pattern "<.*>|$.*";
  //          }
  //          type uint32 {
  //            range "60 .. 2147483647";
  //          }
  //        }
  //      }
  //      container violation-action {
  //        description "Lease time validation violation action";
  //        choice violation-action-choice {
  //          case case_1 {
  //            leaf strict {
  //              description "Reject solicit and renew";
  //              type empty;
  //            }
  //          }
  //          case case_2 {
  //            leaf override-lease {
  //              description "Override assigned lease time with threshold";
  //              type empty;
  //            }
  //          }
  //        }
  //      }
  //    }
  //    container remote-id-mismatch {
  //      description "DHCP client remote-id mismatch";
  //      presence "enable remote-id-mismatch";
  //      uses dhcp-remote-id-mismatch-type;
  //    }
  //    container reauthenticate {
  //      description "DHCP client reauthenticate processing";
  //      leaf lease-renewal {
  //        description "Reauthenticate on each renew, rebind, DISCOVER or SOLICIT";
  //        type empty;
  //      }
  //      leaf remote-id-mismatch {
  //        description "Reauthenticate on remote-id mismatch for renew, rebind and re-negotiation";
  //        type empty;
  //      }
  //    }
  //  }
  //  grouping dhcpv6-override-dynamic-server-type {
  //    description "DHCP override processing";
  //    // uses apply-advanced;
  //    leaf interface-client-limit {
  //      description "Limit the number of clients allowed on an interface";
  //      type union {
  //        type string {
  //          pattern "<.*>|$.*";
  //        }
  //        type uint32 {
  //          range "1 .. 500000";
  //        }
  //      }
  //    }
  //    leaf rapid-commit {
  //      description "Enable rapid commit processing";
  //      type empty;
  //    }
  //    container process-inform {
  //      presence "enable process-inform";
  //      description "Process INFORMATION request PDUs";
  //      // uses apply-advanced;
  //      leaf pool {
  //        description "Pool name for family inet6";
  //        type string {
  //          length "1 .. 64";
  //        }
  //      }
  //    }
  //    leaf delegated-pool {
  //      description "Delegated pool name for inet6";
  //      type string {
  //        length "1 .. 64";
  //      }
  //    }
  //    leaf ia-na-pool {
  //      description "IA_NA pool name for inet6";
  //      type string {
  //        length "1 .. 64";
  //      }
  //    }
  //  }
  //  grouping dhcpv6-override-local-server-type {
  //    description "DHCP override processing";
  //    // uses apply-advanced;
  //    leaf interface-client-limit {
  //      description "Limit the number of clients allowed on an interface";
  //      type union {
  //        type string {
  //          pattern "<.*>|$.*";
  //        }
  //        type uint32 {
  //          range "1 .. 500000";
  //        }
  //      }
  //    }
  //    leaf rapid-commit {
  //      description "Enable rapid commit processing";
  //      type empty;
  //    }
  //    container client-negotiation-match {
  //      description "Use secondary match criteria for SOLICIT PDU";
  //      choice match-with {
  //        case case_1 {
  //          leaf incoming-interface {
  //            description "Use incoming interface";
  //            type empty;
  //          }
  //        }
  //      }
  //    }
  //    container process-inform {
  //      presence "enable process-inform";
  //      description "Process INFORMATION request PDUs";
  //      // uses apply-advanced;
  //      leaf pool {
  //        description "Pool name for family inet6";
  //        type string {
  //          length "1 .. 64";
  //        }
  //      }
  //    }
  //    container delay-advertise {
  //      description "Filter options for dhcp-server";
  //      presence "enable delay-advertise";
  //      uses dhcpv6-filter-option;
  //    }
  //    leaf delegated-pool {
  //      description "Delegated pool name for inet6";
  //      type string {
  //        length "1 .. 64";
  //      }
  //    }
  //    leaf multi-address-embedded-option-response {
  //      description "If the client requests multiple addresses place the options in each address";
  //      type empty;
  //    }
  //    leaf always-process-option-request-option {
  //      description "Always process option even after address allocation failure";
  //      type empty;
  //    }
  //    leaf delete-binding-on-renegotiation {
  //      description "Delete binding on renegotiation";
  //      type empty;
  //    }
  //    leaf top-level-status-code {
  //      description "A top level status code option rather than encapsulated in IA for NoAddrsAvail in Advertise PDUs";
  //      type empty;
  //    }
  //    leaf always-add-option-dns-server {
  //      description "Add option-23, DNS recursive name server in Advertise and Reply";
  //      type empty;
  //    }
  //    leaf asymmetric-lease-time {
  //      description "Use a reduced lease time for the client. In seconds";
  //      units "seconds";
  //      type union {
  //        type string {
  //          pattern "<.*>|$.*";
  //        }
  //        type uint32 {
  //          range "600 .. 86400";
  //        }
  //      }
  //    }
  //    leaf asymmetric-prefix-lease-time {
  //      description "Use a reduced prefix lease time for the client. In seconds";
  //      units "seconds";
  //      type union {
  //        type string {
  //          pattern "<.*>|$.*";
  //        }
  //        type uint32 {
  //          range "600 .. 86400";
  //        }
  //      }
  //    }
  //    leaf protocol-attributes {
  //      description "DHCPv6 attributes to use as defined under access protocol-attributes";
  //      type string {
  //        length "1 .. 64";
  //      }
  //    }
  //    leaf dual-stack {
  //      description "Dual stack group to use";
  //      type string {
  //        length "1 .. 64";
  //      }
  //    }
  //  }
  //  grouping dhcpv6-filter-option {
  //    description "Generic DHCPv6 filter processing";
  //    // uses apply-advanced;
  //    leaf delay-time {
  //      description "Time delay between solicit and advertise";
  //      default "3";
  //      units "seconds";
  //      type union {
  //        type string {
  //          pattern "<.*>|$.*";
  //        }
  //        type uint32 {
  //          range "1 .. 30";
  //        }
  //      }
  //    }
  //    container based-on {
  //      description "Option number";
  //      // uses apply-advanced;
  //      container option-18 {
  //        presence "enable option-18";
  //        description "Option 18";
  //        // uses apply-advanced;
  //        container equals {
  //          description "Generic option equals";
  //          uses server-v6-option-ascii-hex;
  //        }
  //        container not-equals {
  //          description "Generic option not equals";
  //          uses server-v6-option-ascii-hex;
  //        }
  //        container starts-with {
  //          description "Generic option starts-with";
  //          uses server-v6-option-ascii-hex;
  //        }
  //      }
  //      container option-37 {
  //        presence "enable option-37";
  //        description "Option 37";
  //        // uses apply-advanced;
  //        container equals {
  //          description "Generic option equals";
  //          uses server-v6-option-ascii-hex;
  //        }
  //        container not-equals {
  //          description "Generic option not equals";
  //          uses server-v6-option-ascii-hex;
  //        }
  //        container starts-with {
  //          description "Generic option starts-with";
  //          uses server-v6-option-ascii-hex;
  //        }
  //      }
  //      container option-15 {
  //        presence "enable option-15";
  //        description "Option 15";
  //        // uses apply-advanced;
  //        container equals {
  //          description "Generic option equals";
  //          uses server-v6-option-ascii-hex;
  //        }
  //        container not-equals {
  //          description "Generic option not equals";
  //          uses server-v6-option-ascii-hex;
  //        }
  //        container starts-with {
  //          description "Generic option starts-with";
  //          uses server-v6-option-ascii-hex;
  //        }
  //      }
  //      container option-16 {
  //        presence "enable option-16";
  //        description "Option 16";
  //        // uses apply-advanced;
  //        container equals {
  //          description "Generic option equals";
  //          uses server-v6-option-ascii-hex;
  //        }
  //        container not-equals {
  //          description "Generic option not equals";
  //          uses server-v6-option-ascii-hex;
  //        }
  //        container starts-with {
  //          description "Generic option starts-with";
  //          uses server-v6-option-ascii-hex;
  //        }
  //      }
  //    }
  //  }
  //  grouping dhcpv6-reconfigure-type {
  //    description "DHCPv6 reconfigure processing";
  //    // uses apply-advanced;
  //    leaf strict {
  //      description "Only allow packets containing Reconfigure Accept Option";
  //      type empty;
  //    }
  //    leaf clear-on-abort {
  //      description "Delete client on reconfiguration abort";
  //      type empty;
  //    }
  //    leaf attempts {
  //      description "Number of reconfigure attempts before aborting";
  //      type union {
  //        type string {
  //          pattern "<.*>|$.*";
  //        }
  //        type uint32 {
  //          range "1 .. 10";
  //        }
  //      }
  //    }
  //    leaf timeout {
  //      description "Initial timeout value for retry";
  //      type union {
  //        type string {
  //          pattern "<.*>|$.*";
  //        }
  //        type uint32 {
  //          range "1 .. 10";
  //        }
  //      }
  //    }
  //    leaf token {
  //      description "Reconfigure token";
  //      type string {
  //        length "1 .. 244";
  //      }
  //    }
  //    container trigger {
  //      description "DHCP reconfigure trigger";
  //      uses reconfigure-trigger-type;
  //    }
  //    leaf support-option-pd-exclude {
  //      description "Request prefix exclude option in reconfigure message";
  //      type empty;
  //    }
  //  }
  //  grouping dhcpv6-route-suppression-type {
  //    description "Suppress access-internal and/or access route addition";
  //    leaf access {
  //      description "Suppress access route addition";
  //      type empty;
  //    }
  //    leaf access-internal {
  //      description "Suppress access-internal route addition";
  //      type empty;
  //    }
  //  }
  //  grouping dual-stack-authentication-type {
  //    description "DHCP dual stack authentication";
  //    // uses apply-advanced;
  //    leaf password {
  //      description "Username password to use";
  //      type string {
  //        length "1 .. 64";
  //      }
  //    }
  //    container username-include {
  //      description "Add username options";
  //      // uses apply-advanced;
  //      leaf delimiter {
  //        description "Change delimiter/separator character";
  //        type string {
  //          length 1;
  //        }
  //      }
  //      leaf domain-name {
  //        description "Add domain name";
  //        type string {
  //          length "1 .. 64";
  //        }
  //      }
  //      leaf user-prefix {
  //        description "Add user defined prefix";
  //        type string {
  //          length "1 .. 64";
  //        }
  //      }
  //      leaf mac-address {
  //        description "Include MAC address";
  //        type empty;
  //      }
  //      container client-id {
  //        presence "enable client-id";
  //        description "Include client ID";
  //        leaf exclude-headers {
  //          description "Exclude all the headers";
  //          type empty;
  //        }
  //        leaf use-automatic-ascii-hex-encoding {
  //          description "Use automatic ascii hex username encoding";
  //          type empty;
  //        }
  //      }
  //      leaf relay-agent-remote-id {
  //        description "Include the relay agent remote ID";
  //        type empty;
  //      }
  //      leaf logical-system-name {
  //        description "Include logical system name";
  //        type empty;
  //      }
  //      leaf routing-instance-name {
  //        description "Include routing instance name";
  //        type empty;
  //      }
  //      leaf relay-agent-interface-id {
  //        description "Include the relay agent interface ID";
  //        type empty;
  //      }
  //      leaf interface-name {
  //        description "Include interface name";
  //        type empty;
  //      }
  //      leaf interface-description {
  //        description "Include interface description";
  //        type enumeration {
  //          enum "device" {
  //            description "Add the device interface description";
  //          }
  //          enum "logical" {
  //            description "Add the logical interface description";
  //          }
  //        }
  //      }
  //      leaf circuit-type {
  //        description "Include circuit type";
  //        type empty;
  //      }
  //      leaf vlan-tags {
  //        description "Include the vlan tag(s)";
  //        type empty;
  //      }
  //    }
  //  }
  //  grouping duid-type {
  //    // uses apply-advanced;
  //    leaf duid_ll {
  //      description "Link Layer Address based DUID ";
  //      type empty;
  //    }
  //  }
  //  grouping dynamic-profile-type {
  //    description "Dynamic profile to use";
  //    // uses apply-advanced;
  //    leaf dynamic-profile {
  //      description "Dynamic profile to use";
  //      type string {
  //        length "1 .. 80";
  //      }
  //    }
  //    choice dynamic-profile-type-choice {
  //      case case_1 {
  //        leaf use-primary {
  //          description "Dynamic profile to use on the primary interface";
  //          type string {
  //            length "1 .. 80";
  //          }
  //        }
  //      }
  //      case case_2 {
  //        container aggregate-clients {
  //          presence "enable aggregate-clients";
  //          description "Aggregate client profiles";
  //          // uses apply-advanced;
  //          choice aggregate-type {
  //            case case_1 {
  //              leaf merge {
  //                description "Merge the client dynamic profiles";
  //                type empty;
  //              }
  //            }
  //            case case_2 {
  //              leaf replace {
  //                description "Replace client dynamic profiles";
  //                type empty;
  //              }
  //            }
  //          }
  //        }
  //      }
  //    }
  //  }
  //  grouping jdhcp-dual-stack-protocol-mstr-type {
  //    description "Select family as protocol master";
  //    choice addr-fam {
  //      case case_1 {
  //        leaf inet {
  //          description "INET family has protocol master behavior";
  //          type empty;
  //        }
  //      }
  //      case case_2 {
  //        leaf inet6 {
  //          description "INET6 family has protocol master behavior";
  //          type empty;
  //        }
  //      }
  //    }
  //  }
  //  grouping jdhcp-duplicate-clients-in-subnet-type {
  //    description "Allow duplicate clients in a subnet";
  //    choice distinguish-with {
  //      case case_1 {
  //        leaf incoming-interface {
  //          description "Allow duplicate clients on different interfaces in a subnet";
  //          type empty;
  //        }
  //      }
  //      case case_2 {
  //        leaf option-82 {
  //          description "Allow duplicate clients using different option-82 options in a subnet";
  //          type empty;
  //        }
  //      }
  //    }
  //  }
  //  grouping jdhcp-interface-traceoptions-type {
  //    description "Interface trace options for DHCP";
  //    // uses apply-advanced;
  //    leaf no-remote-trace {
  //      description "Disable remote tracing";
  //      type empty;
  //    }
  //    container file {
  //      description "Trace file information";
  //      leaf filename {
  //        description "Name of file in which to write trace information";
  //        type string {
  //          length "1 .. 1024";
  //        }
  //      }
  //      leaf size {
  //        description "Maximum trace file size";
  //        type string;
  //      }
  //      leaf files {
  //        description "Maximum number of trace files";
  //        default "3";
  //        type union {
  //          type string {
  //            pattern "<.*>|$.*";
  //          }
  //          type uint32 {
  //            range "2 .. 1000";
  //          }
  //        }
  //      }
  //      choice world-readable-choice {
  //        leaf world-readable {
  //          description "Allow any user to read the log file";
  //          type empty;
  //        }
  //        leaf no-world-readable {
  //          description "Don't allow any user to read the log file";
  //          type empty;
  //        }
  //      }
  //      leaf match {
  //        description "Regular expression for lines to be logged";
  //        type jt:regular-expression;
  //      }
  //    }
  //    list flag {
  //      key name;
  //      ordered-by user;
  //      description "Interface trace categories";
  //      leaf name {
  //        type enumeration {
  //          enum "state" {
  //            description "State-transition operations";
  //          }
  //          enum "packet" {
  //            description "Packet-decoding operations";
  //          }
  //          enum "flow" {
  //            description "Flow-decoding operations";
  //          }
  //          enum "packet-option" {
  //            description "DHCP option-decoding operations";
  //          }
  //          enum "dhcpv6-state" {
  //            description "State-transition operations for dhcpv6";
  //          }
  //          enum "dhcpv6-packet" {
  //            description "Packet-decoding operations for dhcpv6";
  //          }
  //          enum "dhcpv6-packet-option" {
  //            description "DHCP option-decoding operations for dhcpv6";
  //          }
  //          enum "all" {
  //            description "All operations";
  //          }
  //        }
  //      }
  //    }
  //  }
  //  grouping jdhcp-proxy-client-type {
  //    // uses apply-advanced;
  //    list dhcpv4-profiles {
  //      key name;
  //      ordered-by user;
  //      description "DHCPv4 proxy client profile configuration";
  //      uses dhcpv4-profile;
  //    }
  //    list dhcpv6-profiles {
  //      key name;
  //      ordered-by user;
  //      description "DHCPv6 proxy client profile configuration";
  //      uses dhcpv6-profile;
  //    }
  //    container traceoptions {
  //      description "DHCP proxy-client trace options";
  //      uses jdhcp-traceoptions-type;
  //    }
  //  }
  //  grouping dhcpv4-profile {
  //    description "DHCPv4 proxy client configuration";
  //    leaf name {
  //      description "DHCP proxy client profile name";
  //      type string {
  //        length "1 .. 63";
  //      }
  //    }
  //    // uses apply-advanced;
  //    leaf pool-name {
  //      description "This pool name will be sent to sever in subnet-name-suboption(3) of subnet allocation option(220). It is optional. It shall be sent only if configured.";
  //      type string {
  //        length "1 .. 63";
  //      }
  //    }
  //    leaf lease-time {
  //      description "Default least time requested in seconds. If DHCP client does not get the lease time from DHCP server, it will use this default lease time as the lease time. By default, the value of lease-time is zero";
  //      type union {
  //        type string {
  //          pattern "<.*>|$.*";
  //        }
  //        type uint16 {
  //          range "60 .. 1000";
  //        }
  //      }
  //    }
  //    leaf retransmission-attempt {
  //      description "Number of attempts to retransmit the DHCP client protocol message";
  //      default "4";
  //      type union {
  //        type string {
  //          pattern "<.*>|$.*";
  //        }
  //        type uint16 {
  //          range "0 .. 1000";
  //        }
  //      }
  //    }
  //    leaf retransmission-interval {
  //      description "Number of seconds between successive retransmissions of DHCP client protocols messages";
  //      default "4";
  //      type union {
  //        type string {
  //          pattern "<.*>|$.*";
  //        }
  //        type uint16 {
  //          range "4 .. 64";
  //        }
  //      }
  //    }
  //    leaf dead-server-retry-interval {
  //      description "Number of seconds before reconnecting to a server which was marked as down in previous attempts";
  //      default "300";
  //      type union {
  //        type string {
  //          pattern "<.*>|$.*";
  //        }
  //        type uint16 {
  //          range "300 .. 3600";
  //        }
  //      }
  //    }
  //    leaf dhcp-server-selection-algorithm {
  //      description "DHCP server selection algorithm to be used";
  //      default "round-robin";
  //      type enumeration {
  //        enum "highest-priority-server" {
  //          description "System will try the highest priority server first";
  //        }
  //        enum "round-robin" {
  //          description "System will use round-robin method to select the server";
  //        }
  //      }
  //    }
  //    leaf dead-server-successive-retry-attempt {
  //      description "Number of successive retry attempts before declaring an unresponsive server as dead";
  //      default "10";
  //      type union {
  //        type string {
  //          pattern "<.*>|$.*";
  //        }
  //        type uint16 {
  //          range "5 .. 1000";
  //        }
  //      }
  //    }
  //    leaf bind-interface {
  //      description "Primary IPv4 address of bind-interface is source of DHCP packets";
  //      type union {
  //        type jt:interface-unit;
  //        type string {
  //          pattern "<.*>|$.*";
  //        }
  //      }
  //    }
  //    list servers {
  //      key name;
  //      description "DHCP server";
  //      max-elements 5;
  //      leaf name {
  //        description "DHCP server IPv4 address";
  //        type jt:ipv4addr;
  //      }
  //      // uses apply-advanced;
  //      leaf priority {
  //        description "Server priority";
  //        default "3";
  //        type union {
  //          type string {
  //            pattern "<.*>|$.*";
  //          }
  //          type uint8 {
  //            range "1 .. 5";
  //          }
  //        }
  //      }
  //    }
  //  }
  //  grouping dhcpv6-profile {
  //    description "DHCPv6 proxy client configuration";
  //    leaf name {
  //      description "DHCP proxy client profile name";
  //      type string {
  //        length "1 .. 63";
  //      }
  //    }
  //    // uses apply-advanced;
  //    leaf pool-name {
  //      description "This pool name will be sent to sever in subnet-name-suboption(3) of subnet allocation option(220). It is optional. It shall be sent only if configured.";
  //      type string {
  //        length "1 .. 63";
  //      }
  //    }
  //    leaf lease-time {
  //      description "Default least time requested in seconds. If DHCP client does not get the lease time from DHCP server, it will use this default lease time as the lease time. By default, the value of lease-time is zero";
  //      type union {
  //        type string {
  //          pattern "<.*>|$.*";
  //        }
  //        type uint16 {
  //          range "60 .. 1000";
  //        }
  //      }
  //    }
  //    leaf retransmission-attempt {
  //      description "Number of attempts to retransmit the DHCP client protocol message";
  //      default "4";
  //      type union {
  //        type string {
  //          pattern "<.*>|$.*";
  //        }
  //        type uint16 {
  //          range "0 .. 1000";
  //        }
  //      }
  //    }
  //    leaf retransmission-interval {
  //      description "Number of seconds between successive retransmissions of DHCP client protocols messages";
  //      default "4";
  //      type union {
  //        type string {
  //          pattern "<.*>|$.*";
  //        }
  //        type uint16 {
  //          range "4 .. 64";
  //        }
  //      }
  //    }
  //    leaf bind-interface {
  //      description "Source interface of DHCP control packets";
  //      type union {
  //        type jt:interface-unit;
  //        type string {
  //          pattern "<.*>|$.*";
  //        }
  //      }
  //    }
  //  }
  //  grouping jdhcp-traceoptions-type {
  //    description "Trace options for DHCP";
  //    // uses apply-advanced;
  //    leaf no-remote-trace {
  //      description "Disable remote tracing";
  //      type empty;
  //    }
  //    container file {
  //      description "Trace file information";
  //      leaf filename {
  //        description "Name of file in which to write trace information";
  //        type string {
  //          length "1 .. 1024";
  //        }
  //      }
  //      leaf size {
  //        description "Maximum trace file size";
  //        type string;
  //      }
  //      leaf files {
  //        description "Maximum number of trace files";
  //        default "3";
  //        type union {
  //          type string {
  //            pattern "<.*>|$.*";
  //          }
  //          type uint32 {
  //            range "2 .. 1000";
  //          }
  //        }
  //      }
  //      choice world-readable-choice {
  //        leaf world-readable {
  //          description "Allow any user to read the log file";
  //          type empty;
  //        }
  //        leaf no-world-readable {
  //          description "Don't allow any user to read the log file";
  //          type empty;
  //        }
  //      }
  //      leaf match {
  //        description "Regular expression for lines to be logged";
  //        type jt:regular-expression;
  //      }
  //    }
  //    list flag {
  //      key name;
  //      ordered-by user;
  //      description "DHCP operations to include in debugging trace";
  //      leaf name {
  //        type enumeration {
  //          enum "state" {
  //            description "State-transition operations";
  //          }
  //          enum "packet" {
  //            description "Packet-decoding operations";
  //          }
  //          enum "flow" {
  //            description "Flow-decoding operations";
  //          }
  //          enum "packet-option" {
  //            description "DHCP option-decoding operations";
  //          }
  //          enum "dhcpv6-state" {
  //            description "State-transition operations for dhcpv6";
  //          }
  //          enum "dhcpv6-packet" {
  //            description "Packet-decoding operations for dhcpv6";
  //          }
  //          enum "dhcpv6-packet-option" {
  //            description "DHCP option-decoding operations for dhcpv6";
  //          }
  //          enum "all" {
  //            description "All operations";
  //          }
  //          enum "database" {
  //            description "Database operations";
  //          }
  //          enum "persistent" {
  //            description "Persitent file operations";
  //          }
  //          enum "lockout-db" {
  //            description "Lockout database operations";
  //          }
  //          enum "interface" {
  //            description "Interface operations";
  //          }
  //          enum "rtsock" {
  //            description "Routing socket operations";
  //          }
  //          enum "flow-notify" {
  //            description "Flow notification operations";
  //          }
  //          enum "io" {
  //            description "I/O operations";
  //          }
  //          enum "ha" {
  //            description "High Availability-related operations";
  //          }
  //          enum "ui" {
  //            description "User Interface operations";
  //          }
  //          enum "general" {
  //            description "Miscellaneous operations";
  //          }
  //          enum "fwd" {
  //            description "Firewall process operations";
  //          }
  //          enum "rpd" {
  //            description "Routing Protocol process operations";
  //          }
  //          enum "auth" {
  //            description "Authentication operations";
  //          }
  //          enum "profile" {
  //            description "Profile operations";
  //          }
  //          enum "session-db" {
  //            description "Session database operations";
  //          }
  //          enum "performance" {
  //            description "Performance measurement operations";
  //          }
  //          enum "statistics" {
  //            description "Baseline statistics operations";
  //          }
  //          enum "dhcpv6-io" {
  //            description "I/O operations for dhcpv6";
  //          }
  //          enum "dhcpv6-rpd" {
  //            description "Routing Protocol process operations for dhcpv6";
  //          }
  //          enum "dhcpv6-session-db" {
  //            description "Session database operations for dhcpv6";
  //          }
  //          enum "dhcpv6-general" {
  //            description "Miscellaneous operations for dhcpv6";
  //          }
  //          enum "liveness-detection" {
  //            description "Liveness detection operations";
  //          }
  //          enum "security-persistence" {
  //            description "Liveness detection operations";
  //          }
  //          enum "mclag" {
  //            description "Multichassis LAG";
  //          }
  //          enum "ra-guard" {
  //            description "DHCP RA guard option for dhcpv6";
  //          }
  //          enum "era" {
  //            description "DHCP ERA logging option dhcp";
  //          }
  //          enum "telemetry" {
  //            description "Telemetry operation";
  //          }
  //        }
  //      }
  //    }
  //  }
  //  grouping jsscd-static-subscribers-type {
  //    // uses apply-advanced;
  //    container access-profile {
  //      description "Access profile reference";
  //      uses jsscd-access-profile-type;
  //    }
  //    container dynamic-profile {
  //      description "Dynamic profile reference";
  //      uses jsscd-dynamic-profile-type;
  //    }
  //    container service-profile {
  //      description "Dynamic profile to use for default service activation";
  //      uses jsscd-service-profile-type;
  //    }
  //    container authentication {
  //      description "Static Subscriber Client authentication";
  //      uses jsscd-authentication-type;
  //    }
  //    list group {
  //      key name;
  //      ordered-by user;
  //      description "Static Subscriber Client group configuration";
  //      uses jsscd-group-type;
  //    }
  //    leaf auto-login {
  //      description "Auto login the operator logged-out static subscribers";
  //      type empty;
  //    }
  //    leaf baseline-stats {
  //      description "Baseline the statistics for static subscribers";
  //      type empty;
  //    }
  //    list interface {
  //      key name;
  //      description "One or more interfaces";
  //      leaf name {
  //        description "Interface name";
  //        type union {
  //          type jt:interface-unit;
  //          type string {
  //            pattern "<.*>|$.*";
  //          }
  //        }
  //      }
  //      // uses apply-advanced;
  //      container subscriber-ip-address {
  //        description "Assigned IP address to report externally";
  //        // uses apply-advanced;
  //        leaf address {
  //          description "IPv4 address";
  //          type jt:ipv4addr;
  //        }
  //      }
  //      container subscriber-ipv6-address {
  //        description "Assigned IPv6 address to report externally";
  //        // uses apply-advanced;
  //        leaf address {
  //          description "IPv6 Address or Prefix";
  //          type jt:ipv6prefix;
  //        }
  //      }
  //    }
  //  }
  //  grouping jsscd-access-profile-type {
  //    description "Access profile for static subscribers";
  //    // uses apply-advanced;
  //    leaf access-profile-name {
  //      description "Profile name";
  //      type string;
  //    }
  //  }
  //  grouping jsscd-authentication-type {
  //    description "Static Subscriber Client authentication";
  //    // uses apply-advanced;
  //    leaf password {
  //      description "Username password to use";
  //      type jt:unreadable;
  //    }
  //    container username-include {
  //      description "Add username options";
  //      // uses apply-advanced;
  //      leaf delimiter {
  //        description "Change delimiter/separator character";
  //        type string {
  //          length 1;
  //        }
  //      }
  //      leaf domain-name {
  //        description "Add domain name";
  //        type string {
  //          length "1 .. 64";
  //        }
  //      }
  //      leaf user-prefix {
  //        description "Add user defined prefix";
  //        type string {
  //          length "1 .. 64";
  //        }
  //      }
  //      leaf interface {
  //        description "Include interface name";
  //        type empty;
  //      }
  //      leaf logical-system-name {
  //        description "Include logical system name";
  //        type empty;
  //      }
  //      leaf routing-instance-name {
  //        description "Include routing instance name";
  //        type empty;
  //      }
  //      leaf vlan-tags {
  //        description "Include vlan tag(s)";
  //        type empty;
  //      }
  //    }
  //  }
  //  grouping jsscd-dynamic-profile-type {
  //    description "Dynamic profile to use";
  //    // uses apply-advanced;
  //    leaf dynamic-profile-name {
  //      description "Dynamic profile to use";
  //      type string {
  //        length "1 .. 80";
  //      }
  //    }
  //    container aggregate-clients {
  //      presence "enable aggregate-clients";
  //      description "Aggregate client profiles";
  //      // uses apply-advanced;
  //      choice aggregate-type {
  //        case case_1 {
  //          leaf merge {
  //            description "Merge the client dynamic profiles";
  //            type empty;
  //          }
  //        }
  //        case case_2 {
  //          leaf replace {
  //            description "Replace client dynamic profiles";
  //            type empty;
  //          }
  //        }
  //      }
  //    }
  //  }
  //  grouping jsscd-group-type {
  //    leaf name {
  //      description "Group name";
  //      type string {
  //        length "1 .. 64";
  //      }
  //    }
  //    // uses apply-advanced;
  //    container service-profile {
  //      description "Dynamic profile to use for default service activation";
  //      uses jsscd-service-profile-type;
  //    }
  //    container access-profile {
  //      description "Access profile reference";
  //      uses jsscd-access-profile-type;
  //    }
  //    container dynamic-profile {
  //      description "Dynamic profile reference";
  //      uses jsscd-dynamic-profile-type;
  //    }
  //    container authentication {
  //      description "Static Subscriber Client authentication";
  //      uses jsscd-authentication-type;
  //    }
  //    list interface {
  //      key name;
  //      description "One or more interfaces";
  //      leaf name {
  //        description "Interface name";
  //        type union {
  //          type jt:interface-unit;
  //          type string {
  //            pattern "<.*>|$.*";
  //          }
  //        }
  //      }
  //      leaf upto {
  //        description "Interface up to";
  //        type union {
  //          type jt:interface-unit;
  //          type string {
  //            pattern "<.*>|$.*";
  //          }
  //        }
  //      }
  //      leaf exclude {
  //        description "Exclude this interface range";
  //        type empty;
  //      }
  //    }
  //    leaf auto-login {
  //      description "Auto login the operator logged-out static subscribers";
  //      type empty;
  //    }
  //  }
  //  grouping jsscd-service-profile-type {
  //    description "Service profile for static subscribers";
  //    // uses apply-advanced;
  //    leaf service-profile-name {
  //      description "Service profile name";
  //      type string {
  //        length "1 .. 80";
  //      }
  //    }
  //  }
  //  grouping juniper-bridge-domains {
  //    description "Bridge domains";
  //    leaf name {
  //      description "Bridge domain name";
  //      type string {
  //      }
  //    }
  //    // uses apply-advanced;
  //    leaf description {
  //      description "Text description of bridge domain";
  //      type string {
  //      }
  //    }
  //    leaf domain-type {
  //      description "Type of bridge domain";
  //      type enumeration {
  //        enum "bridge" {
  //          description "Forwarding instance";
  //        }
  //      }
  //    }
  //    choice vlan_choice {
  //      case case_1 {
  //        leaf vlan-id {
  //          description "IEEE 802.1q VLAN identifier for bridging domain";
  //          type string;
  //        }
  //      }
  //      case case_2 {
  //        container vlan-tags {
  //          presence "enable vlan-tags";
  //          description "IEEE 802.1q VLAN tags for bridging domain";
  //          leaf outer {
  //            description "[tpid.]vlan-id, tpid format is 0xNNNN and is optional";
  //            type string {
  //            }
  //          }
  //          leaf inner {
  //            description "[tpid.]vlan-id, tpid format is 0xNNNN and is optional";
  //            type string {
  //            }
  //          }
  //        }
  //      }
  //      case case_3 {
  //        leaf-list vlan-id-list {
  //          description "Create bridge-domain for each of the vlan-id specified in the vlan-id-list";
  //          type jt:vlan-range;
  //        }
  //      }
  //    }
  //    leaf-list isid-list {
  //      ordered-by user;
  //      description "Create bridge-domain for isid (Valid isid:256..16777214)";
  //      type string;
  //    }
  //    leaf vlan-id-scope-local {
  //      description "Enable the scope of vlan-id local to avoid transmitting vlan tagged packets";
  //      type empty;
  //    }
  //    leaf service-id {
  //      description "Service id required if bridge-domain is of type MC-AE and vlan-id all or vlan-id none or vlan-tags";
  //      type union {
  //        type string {
  //          pattern "<.*>|$.*";
  //        }
  //        type uint32 {
  //          range "1 .. 65535";
  //        }
  //      }
  //    }
  //    leaf domain-id {
  //      description "Domain-id for auto derived Route Target";
  //      type union {
  //        type string {
  //          pattern "<.*>|$.*";
  //        }
  //        type uint32 {
  //          range "1 .. 15";
  //        }
  //      }
  //    }
  //    leaf no-local-switching {
  //      description "Disable local switching within CE-facing interfaces";
  //      type empty;
  //    }
  //    leaf mcae-mac-synchronize {
  //      description "Enable IRB MAC synchronization in this bridge domain";
  //      type empty;
  //    }
  //    leaf mcae-mac-flush {
  //      description "Enable MCAE MAC flush in a/s mode for a bridge domain on MCAE link up";
  //      type empty;
  //    }
  //    leaf no-irb-layer-2-copy {
  //      description "Disable transmission of layer-2 copy of packets of irb routing-interface";
  //      type empty;
  //    }
  //    leaf enable-mac-move-action {
  //      description "Enable blocking action due to mac-move in this Bridge Domain";
  //      type empty;
  //    }
  //    list interface {
  //      key name;
  //      ordered-by user;
  //      description "Interface name for this bridge domain";
  //      leaf name {
  //        type string;
  //      }
  //      // uses apply-advanced;
  //      leaf protect-interface {
  //        description "Name of protect interface";
  //        type union {
  //          type jt:interface-name;
  //          type string {
  //            pattern "<.*>|$.*";
  //          }
  //        }
  //      }
  //    }
  //    leaf routing-interface {
  //      description "Routing interface name for this bridge-domain";
  //      type union {
  //        type jt:interface-unit;
  //        type string {
  //          pattern "<.*>|$.*";
  //        }
  //      }
  //    }
  //    container forwarding-options {
  //      description "Forwarding options configuration";
  //      uses juniper-bridge-forwarding-options;
  //    }
  //    container bridge-options {
  //      description "Bridge domain configuration";
  //      uses juniper-protocols-bd;
  //    }
  //   //  container protocols {
  //   //    presence "enable protocols";
  //   //    // uses apply-advanced;
  //   //    container igmp-snooping {
  //   //      description "IGMP snooping configuration";
  //   //      presence "enable igmp-snooping";
  //   //      uses juniper-bd-protocols-igmp-snooping;
  //   //    }
  //   //    container mld-snooping {
  //   //      description "MLD snooping configuration";
  //   //      presence "enable mld-snooping";
  //   //      uses juniper-bd-protocols-mld-snooping;
  //   //    }
  //   //  }
  //   //  container vxlan {
  //   //    description "VXLAN options";
  //   //    // uses apply-advanced;
  //   //    leaf ovsdb-managed {
  //   //      description "Bridge-domain is managed remotely via VXLAN OVSDB Controller";
  //   //      type empty;
  //   //    }
  //   //    leaf vni {
  //   //      description "VXLAN identifier";
  //   //      type union {
  //   //        type string {
  //   //          pattern "<.*>|$.*";
  //   //        }
  //   //        type uint32 {
  //   //          range "0 .. 16777214";
  //   //        }
  //   //      }
  //   //    }
  //   //    leaf translation-vni {
  //   //      description "Translated VXLAN identifier";
  //   //      type union {
  //   //        type string {
  //   //          pattern "<.*>|$.*";
  //   //        }
  //   //        type uint32 {
  //   //          range "1 .. 16777214";
  //   //        }
  //   //      }
  //   //    }
  //   //    leaf multicast-group {
  //   //      description "Multicast group registered for VXLAN segment";
  //   //      type jt:ipv4addr;
  //   //    }
  //   //    leaf encapsulate-inner-vlan {
  //   //      description "Retain inner VLAN in the packet";
  //   //      type empty;
  //   //    }
  //   //    leaf decapsulate-accept-inner-vlan {
  //   //      description "Accept VXLAN packets with inner VLAN";
  //   //      type empty;
  //   //    }
  //   //    leaf unreachable-vtep-aging-timer {
  //   //      description "Unreachable VXLAN tunnel endpoint removal timer";
  //   //      units "seconds";
  //   //      type union {
  //   //        type string {
  //   //          pattern "<.*>|$.*";
  //   //        }
  //   //        type uint16 {
  //   //          range "300 .. 1800";
  //   //        }
  //   //      }
  //   //    }
  //   //    leaf destination-udp-port {
  //   //      description "VXLAN destination UDP port";
  //   //      default "4789";
  //   //      type union {
  //   //        type string {
  //   //          pattern "<.*>|$.*";
  //   //        }
  //   //        type uint16 {
  //   //          range "4789 .. 65535";
  //   //        }
  //   //      }
  //   //    }
  //   //    leaf ingress-node-replication {
  //   //      description "Enable ingress node replication";
  //   //      type empty;
  //   //    }
  //   //    leaf-list static-remote-vtep-list {
  //   //      description "Configure bridge domain specific static remote VXLAN tunnel endpoints";
  //   //      type jt:ipaddr;
  //   //      max-elements 1024;
  //   //    }
  //   //  }
  //    leaf isolated-vlan {
  //      description "Isolated VLAN ID for private vlan bridge domain";
  //      type union {
  //        type string {
  //          pattern "<.*>|$.*";
  //        }
  //        type uint32 {
  //          range "1 .. 4094";
  //        }
  //      }
  //    }
  //    leaf-list community-vlans {
  //      description "List of Community VLANs for private vlan bridge domain";
  //      type jt:vlan-range;
  //    }
  //    container proxy-mac {
  //      description "Proxy MAC settings";
  //      // uses apply-advanced;
  //      leaf irb {
  //        description "Reply with virtual-gateway MAC or IRB MAC";
  //        type empty;
  //      }
  //      leaf proxy-mac-address {
  //        description "Reply with configured MAC for all requests";
  //        type jt:mac-unicast;
  //      }
  //    }
  //    container multicast-snooping-options {
  //      description "Multicast snooping option configuration";
  //      uses juniper-multicast-snooping-options;
  //    }
  //  }
  //  grouping juniper-bd-protocols-igmp-snooping {
  //    description "IGMP snooping options";
  //    // uses apply-advanced;
  //    container traceoptions {
  //      description "Trace options for IGMP Snooping";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "packets" {
  //              description "Trace all IGMP packets";
  //            }
  //            enum "query" {
  //              description "Trace IGMP membership query messages";
  //            }
  //            enum "report" {
  //              description "Trace membership report messages";
  //            }
  //            enum "leave" {
  //              description "Trace leave group messages (IGMPv2 only)";
  //            }
  //            enum "group" {
  //              description "Trace group operations";
  //            }
  //            enum "client-notification" {
  //              description "Trace notifications";
  //            }
  //            enum "host-notification" {
  //              description "Trace host notifications";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    leaf query-interval {
  //      description "When to send host query messages";
  //      default "125";
  //      units "seconds";
  //      type union {
  //        type string {
  //          pattern "<.*>|$.*";
  //        }
  //        type uint32 {
  //          range "1 .. 1024";
  //        }
  //      }
  //    }
  //    container l2-querier {
  //      description "Enable L2 querier mode";
  //      // uses apply-advanced;
  //      leaf source-address {
  //        description "Source IP address to use for L2 querier";
  //        type jt:ipv4addr;
  //      }
  //    }
  //    leaf query-response-interval {
  //      description "How long to wait for a host query response";
  //      default "10";
  //      units "seconds";
  //      type string {
  //      }
  //    }
  //    leaf query-last-member-interval {
  //      description "When to send group query messages";
  //      default "1";
  //      units "seconds";
  //      type string {
  //      }
  //    }
  //    leaf robust-count {
  //      description "Expected packet loss on a subnet";
  //      default "2";
  //      type union {
  //        type string {
  //          pattern "<.*>|$.*";
  //        }
  //        type uint32 {
  //          range "2 .. 10";
  //        }
  //      }
  //    }
  //    leaf learn-pim-router {
  //      description "Learn PIM router interfaces from PIM hellos";
  //      type empty;
  //    }
  //    leaf immediate-leave {
  //      description "Enable immediate group leave on interfaces";
  //      type empty;
  //    }
  //    leaf evpn-ssm-reports-only {
  //      description "Accept and process only <s,g> reports of SSM groups";
  //      type empty;
  //    }
  //    leaf version {
  //      description "Set IGMP snooping version number";
  //      type union {
  //        type string {
  //          pattern "<.*>|$.*";
  //        }
  //        type uint8 {
  //          range "2 .. 3";
  //        }
  //      }
  //    }
  //    container proxy {
  //      presence "enable proxy";
  //      description "Enable proxy mode";
  //      // uses apply-advanced;
  //      leaf source-address {
  //        description "Source IP address to use for proxy";
  //        type jt:ipv4addr;
  //      }
  //      leaf irb {
  //        description "Proxy IGMP reports to IRB";
  //        type empty;
  //      }
  //    }
  //    list interface {
  //      key name;
  //      ordered-by user;
  //      description "Interface options for IGMP";
  //      leaf name {
  //        description "Interface name";
  //        type union {
  //          type jt:interface-name;
  //          type string {
  //            pattern "<.*>|$.*";
  //          }
  //        }
  //      }
  //      // uses apply-advanced;
  //      leaf multicast-router-interface {
  //        description "Enabling multicast-router-interface on the interface";
  //        type empty;
  //      }
  //      leaf immediate-leave {
  //        description "Enable immediate group leave on interfaces";
  //        type empty;
  //      }
  //      leaf host-only-interface {
  //        description "Enable interfaces to be treated as host-side interfaces";
  //        type empty;
  //      }
  //      leaf group-limit {
  //        description "Maximum number of (source,group) per interface";
  //        type union {
  //          type string {
  //            pattern "<.*>|$.*";
  //          }
  //          type uint16 {
  //            range "1 .. 65535";
  //          }
  //        }
  //      }
  //      container static {
  //        description "Static group or source membership";
  //        // uses apply-advanced;
  //        list group {
  //          key name;
  //          ordered-by user;
  //          description "IP multicast group address";
  //          leaf name {
  //            description "IP multicast group address";
  //            type jt:ipv4addr;
  //          }
  //          // uses apply-advanced;
  //          list source {
  //            key name;
  //            ordered-by user;
  //            description "IP multicast source address";
  //            leaf name {
  //              description "Source address of IP multicast data";
  //              type jt:ipv4addr;
  //            }
  //            // uses apply-advanced;
  //          }
  //        }
  //      }
  //    }
  //    list pseudowire-remote-address {
  //      key name;
  //      ordered-by user;
  //      description "Pseudowire interface options for IGMP";
  //      leaf name {
  //        description "Pseudowire endpoint address";
  //        type jt:ipv4addr;
  //      }
  //      // uses apply-advanced;
  //      leaf multicast-router-interface {
  //        description "Enabling multicast-router-interface on the interface";
  //        type empty;
  //      }
  //      leaf immediate-leave {
  //        description "Enable immediate group leave on interfaces";
  //        type empty;
  //      }
  //    }
  //    list vlan {
  //      key name;
  //      ordered-by user;
  //      description "Vlan options";
  //      leaf name {
  //        description "VLAN name";
  //        type string;
  //      }
  //      // uses apply-advanced;
  //      leaf query-interval {
  //        description "When to send host query messages";
  //        units "seconds";
  //        type union {
  //          type string {
  //            pattern "<.*>|$.*";
  //          }
  //          type uint32 {
  //            range "1 .. 1024";
  //          }
  //        }
  //      }
  //      leaf query-response-interval {
  //        description "How long to wait for a host query response";
  //        units "seconds";
  //        type string {
  //        }
  //      }
  //      leaf query-last-member-interval {
  //        description "When to send group query messages";
  //        units "seconds";
  //        type string {
  //        }
  //      }
  //      leaf robust-count {
  //        description "Expected packet loss on a subnet";
  //        type union {
  //          type string {
  //            pattern "<.*>|$.*";
  //          }
  //          type uint32 {
  //            range "2 .. 10";
  //          }
  //        }
  //      }
  //      leaf immediate-leave {
  //        description "Enable immediate group leave on interfaces";
  //        type empty;
  //      }
  //      container proxy {
  //        presence "enable proxy";
  //        description "Enable proxy mode";
  //        // uses apply-advanced;
  //        leaf source-address {
  //          description "Source IP address to use for proxy";
  //          type jt:ipv4addr;
  //        }
  //      }
  //      container l2-querier {
  //        description "Enable L2 querier mode";
  //        // uses apply-advanced;
  //        leaf source-address {
  //          description "Source IP address to use for L2 querier";
  //          type jt:ipv4addr;
  //        }
  //      }
  //      leaf evpn-ssm-reports-only {
  //        description "Accept and process only <s,g> reports of SSM groups";
  //        type empty;
  //      }
  //      list interface {
  //        key name;
  //        ordered-by user;
  //        description "Interface options for IGMP";
  //        leaf name {
  //          description "Interface name";
  //          type union {
  //            type jt:interface-name;
  //            type string {
  //              pattern "<.*>|$.*";
  //            }
  //          }
  //        }
  //        // uses apply-advanced;
  //        leaf multicast-router-interface {
  //          description "Enabling multicast-router-interface on the interface";
  //          type empty;
  //        }
  //        leaf immediate-leave {
  //          description "Enable immediate group leave on interfaces";
  //          type empty;
  //        }
  //        leaf host-only-interface {
  //          description "Enable interfaces to be treated as host-side interfaces";
  //          type empty;
  //        }
  //        leaf group-limit {
  //          description "Maximum number of (source,group) per interface";
  //          type union {
  //            type string {
  //              pattern "<.*>|$.*";
  //            }
  //            type uint16 {
  //              range "1 .. 65535";
  //            }
  //          }
  //        }
  //        container static {
  //          description "Static group or source membership";
  //          // uses apply-advanced;
  //          list group {
  //            key name;
  //            ordered-by user;
  //            description "IP multicast group address";
  //            leaf name {
  //              description "IP multicast group address";
  //              type jt:ipv4addr;
  //            }
  //            // uses apply-advanced;
  //            list source {
  //              key name;
  //              ordered-by user;
  //              description "IP multicast source address";
  //              leaf name {
  //                description "Source address of IP multicast data";
  //                type jt:ipv4addr;
  //              }
  //              // uses apply-advanced;
  //            }
  //          }
  //        }
  //      }
  //      list pseudowire-remote-address {
  //        key name;
  //        ordered-by user;
  //        description "Pseudowire interface options for IGMP";
  //        leaf name {
  //          description "Pseudowire endpoint address";
  //          type jt:ipv4addr;
  //        }
  //        // uses apply-advanced;
  //        leaf multicast-router-interface {
  //          description "Enabling multicast-router-interface on the interface";
  //          type empty;
  //        }
  //        leaf immediate-leave {
  //          description "Enable immediate group leave on interfaces";
  //          type empty;
  //        }
  //      }
  //      list qualified-vlan {
  //        key name;
  //        ordered-by user;
  //        description "VLAN options for qualified-learning";
  //        leaf name {
  //          description "VLAN ID of the learning-domain";
  //          type union {
  //            type string {
  //              pattern "<.*>|$.*";
  //            }
  //            type uint32 {
  //              range "0 .. 1023";
  //            }
  //          }
  //        }
  //        // uses apply-advanced;
  //        leaf query-interval {
  //          description "When to send host query messages";
  //          units "seconds";
  //          type union {
  //            type string {
  //              pattern "<.*>|$.*";
  //            }
  //            type uint32 {
  //              range "1 .. 1024";
  //            }
  //          }
  //        }
  //        leaf query-response-interval {
  //          description "How long to wait for a host query response";
  //          units "seconds";
  //          type string {
  //          }
  //        }
  //        leaf query-last-member-interval {
  //          description "When to send group query messages";
  //          units "seconds";
  //          type string {
  //          }
  //        }
  //        leaf robust-count {
  //          description "Expected packet loss on a subnet";
  //          type union {
  //            type string {
  //              pattern "<.*>|$.*";
  //            }
  //            type uint32 {
  //              range "2 .. 10";
  //            }
  //          }
  //        }
  //        leaf immediate-leave {
  //          description "Enable immediate group leave on interfaces";
  //          type empty;
  //        }
  //        container proxy {
  //          presence "enable proxy";
  //          description "Enable proxy mode";
  //          // uses apply-advanced;
  //          leaf source-address {
  //            description "Source IP address to use for proxy";
  //            type jt:ipv4addr;
  //          }
  //        }
  //        leaf evpn-ssm-reports-only {
  //          description "Accept and process only <s,g> reports of SSM groups";
  //          type empty;
  //        }
  //        list interface {
  //          key name;
  //          ordered-by user;
  //          description "Interface options for IGMP";
  //          leaf name {
  //            description "Interface name";
  //            type union {
  //              type jt:interface-name;
  //              type string {
  //                pattern "<.*>|$.*";
  //              }
  //            }
  //          }
  //          // uses apply-advanced;
  //          leaf multicast-router-interface {
  //            description "Enabling multicast-router-interface on the interface";
  //            type empty;
  //          }
  //          leaf immediate-leave {
  //            description "Enable immediate group leave on interfaces";
  //            type empty;
  //          }
  //          leaf host-only-interface {
  //            description "Enable interfaces to be treated as host-side interfaces";
  //            type empty;
  //          }
  //          leaf group-limit {
  //            description "Maximum number of (source,group) per interface";
  //            type union {
  //              type string {
  //                pattern "<.*>|$.*";
  //              }
  //              type uint16 {
  //                range "1 .. 65535";
  //              }
  //            }
  //          }
  //          container static {
  //            description "Static group or source membership";
  //            // uses apply-advanced;
  //            list group {
  //              key name;
  //              ordered-by user;
  //              description "IP multicast group address";
  //              leaf name {
  //                description "IP multicast group address";
  //                type jt:ipv4addr;
  //              }
  //              // uses apply-advanced;
  //              list source {
  //                key name;
  //                ordered-by user;
  //                description "IP multicast source address";
  //                leaf name {
  //                  description "Source address of IP multicast data";
  //                  type jt:ipv4addr;
  //                }
  //                // uses apply-advanced;
  //              }
  //            }
  //          }
  //        }
  //        list pseudowire-remote-address {
  //          key name;
  //          ordered-by user;
  //          description "Pseudowire interface options for IGMP";
  //          leaf name {
  //            description "Pseudowire endpoint address";
  //            type jt:ipv4addr;
  //          }
  //          // uses apply-advanced;
  //          leaf multicast-router-interface {
  //            description "Enabling multicast-router-interface on the interface";
  //            type empty;
  //          }
  //          leaf immediate-leave {
  //            description "Enable immediate group leave on interfaces";
  //            type empty;
  //          }
  //        }
  //      }
  //      leaf version {
  //        description "Set IGMP snooping version number";
  //        type union {
  //          type string {
  //            pattern "<.*>|$.*";
  //          }
  //          type uint8 {
  //            range "2 .. 3";
  //          }
  //        }
  //      }
  //    }
  //  }
  //  grouping juniper-bd-protocols-mld-snooping {
  //    description "MLD snooping options";
  //    // uses apply-advanced;
  //    container traceoptions {
  //      description "Trace options for MLD Snooping";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "packets" {
  //              description "Trace all MLD packets";
  //            }
  //            enum "query" {
  //              description "Trace MLD membership query messages";
  //            }
  //            enum "report" {
  //              description "Trace membership report messages";
  //            }
  //            enum "leave" {
  //              description "Trace leave group messages (MLDv2 only)";
  //            }
  //            enum "group" {
  //              description "Trace group operations";
  //            }
  //            enum "client-notification" {
  //              description "Trace notifications";
  //            }
  //            enum "host-notification" {
  //              description "Trace host notifications";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    leaf query-interval {
  //      description "When to send host query messages";
  //      default "125";
  //      units "seconds";
  //      type union {
  //        type string {
  //          pattern "<.*>|$.*";
  //        }
  //        type uint32 {
  //          range "1 .. 1024";
  //        }
  //      }
  //    }
  //    container l2-querier {
  //      description "Enable L2 querier mode";
  //      // uses apply-advanced;
  //      leaf source-address {
  //        description "Source IP address to use for L2 querier";
  //        type jt:ipv6addr;
  //      }
  //    }
  //    leaf query-response-interval {
  //      description "How long to wait for a host query response";
  //      default "10";
  //      units "seconds";
  //      type string {
  //      }
  //    }
  //    leaf query-last-member-interval {
  //      description "When to send group query messages";
  //      default "1";
  //      units "seconds";
  //      type string {
  //      }
  //    }
  //    leaf robust-count {
  //      description "Expected packet loss on a subnet";
  //      default "2";
  //      type union {
  //        type string {
  //          pattern "<.*>|$.*";
  //        }
  //        type uint32 {
  //          range "2 .. 10";
  //        }
  //      }
  //    }
  //    leaf immediate-leave {
  //      description "Enable immediate group leave on interfaces";
  //      type empty;
  //    }
  //    leaf evpn-ssm-reports-only {
  //      description "Accept and process only <s,g> reports of SSM groups";
  //      type empty;
  //    }
  //    leaf version {
  //      description "Set MLD snooping version number";
  //      type union {
  //        type string {
  //          pattern "<.*>|$.*";
  //        }
  //        type uint8 {
  //          range "1 .. 2";
  //        }
  //      }
  //    }
  //    container proxy {
  //      description "Enable proxy mode";
  //      // uses apply-advanced;
  //      leaf source-address {
  //        description "Source IP address to use for proxy";
  //        type jt:ipv6addr;
  //      }
  //      leaf irb {
  //        description "Proxy IGMP reports to IRB";
  //        type empty;
  //      }
  //    }
  //    list interface {
  //      key name;
  //      ordered-by user;
  //      description "Interface options for MLD";
  //      leaf name {
  //        description "Interface name";
  //        type union {
  //          type jt:interface-name;
  //          type string {
  //            pattern "<.*>|$.*";
  //          }
  //        }
  //      }
  //      // uses apply-advanced;
  //      leaf multicast-router-interface {
  //        description "Enabling multicast-router-interface on the interface";
  //        type empty;
  //      }
  //      leaf immediate-leave {
  //        description "Enable immediate group leave on interfaces";
  //        type empty;
  //      }
  //      leaf host-only-interface {
  //        description "Enable interfaces to be treated as host-side interfaces";
  //        type empty;
  //      }
  //      leaf group-limit {
  //        description "Maximum number of (source,group) per interface";
  //        type union {
  //          type string {
  //            pattern "<.*>|$.*";
  //          }
  //          type uint16 {
  //            range "1 .. 65535";
  //          }
  //        }
  //      }
  //      container static {
  //        description "Static group or source membership";
  //        // uses apply-advanced;
  //        list group {
  //          key name;
  //          ordered-by user;
  //          description "IP multicast group address";
  //          leaf name {
  //            description "IP multicast group address";
  //            type jt:ipv6addr;
  //          }
  //          // uses apply-advanced;
  //          list source {
  //            key name;
  //            ordered-by user;
  //            description "IP multicast source address";
  //            leaf name {
  //              description "Source address of IP multicast data";
  //              type jt:ipv6addr;
  //            }
  //            // uses apply-advanced;
  //          }
  //        }
  //      }
  //    }
  //    list pseudowire-remote-address {
  //      key name;
  //      ordered-by user;
  //      description "Pseudowire interface options for MLD";
  //      leaf name {
  //        description "Pseudowire endpoint address";
  //        type jt:ipv4addr;
  //      }
  //      // uses apply-advanced;
  //      leaf multicast-router-interface {
  //        description "Enabling multicast-router-interface on the interface";
  //        type empty;
  //      }
  //      leaf immediate-leave {
  //        description "Enable immediate group leave on interfaces";
  //        type empty;
  //      }
  //    }
  //    list vlan {
  //      key name;
  //      ordered-by user;
  //      description "Vlan options";
  //      leaf name {
  //        description "Vlan of the bridge-domain";
  //        type string;
  //      }
  //      // uses apply-advanced;
  //      leaf query-interval {
  //        description "When to send host query messages";
  //        units "seconds";
  //        type union {
  //          type string {
  //            pattern "<.*>|$.*";
  //          }
  //          type uint32 {
  //            range "1 .. 1024";
  //          }
  //        }
  //      }
  //      leaf query-response-interval {
  //        description "How long to wait for a host query response";
  //        units "seconds";
  //        type string {
  //        }
  //      }
  //      leaf query-last-member-interval {
  //        description "When to send group query messages";
  //        units "seconds";
  //        type string {
  //        }
  //      }
  //      leaf robust-count {
  //        description "Expected packet loss on a subnet";
  //        type union {
  //          type string {
  //            pattern "<.*>|$.*";
  //          }
  //          type uint32 {
  //            range "2 .. 10";
  //          }
  //        }
  //      }
  //      leaf immediate-leave {
  //        description "Enable immediate group leave on interfaces";
  //        type empty;
  //      }
  //      container proxy {
  //        description "Enable proxy mode";
  //        // uses apply-advanced;
  //        leaf source-address {
  //          description "Source IP address to use for proxy";
  //          type jt:ipv6addr;
  //        }
  //      }
  //      container l2-querier {
  //        description "Enable L2 querier mode";
  //        // uses apply-advanced;
  //        leaf source-address {
  //          description "Source IP address to use for L2 querier";
  //          type jt:ipv6addr;
  //        }
  //      }
  //      leaf evpn-ssm-reports-only {
  //        description "Accept and process only <s,g> reports of SSM groups";
  //        type empty;
  //      }
  //      list interface {
  //        key name;
  //        ordered-by user;
  //        description "Interface options for MLD";
  //        leaf name {
  //          description "Interface name";
  //          type union {
  //            type jt:interface-name;
  //            type string {
  //              pattern "<.*>|$.*";
  //            }
  //          }
  //        }
  //        // uses apply-advanced;
  //        leaf multicast-router-interface {
  //          description "Enabling multicast-router-interface on the interface";
  //          type empty;
  //        }
  //        leaf immediate-leave {
  //          description "Enable immediate group leave on interfaces";
  //          type empty;
  //        }
  //        leaf host-only-interface {
  //          description "Enable interfaces to be treated as host-side interfaces";
  //          type empty;
  //        }
  //        leaf group-limit {
  //          description "Maximum number of (source,group) per interface";
  //          type union {
  //            type string {
  //              pattern "<.*>|$.*";
  //            }
  //            type uint16 {
  //              range "1 .. 65535";
  //            }
  //          }
  //        }
  //        container static {
  //          description "Static group or source membership";
  //          // uses apply-advanced;
  //          list group {
  //            key name;
  //            ordered-by user;
  //            description "IP multicast group address";
  //            leaf name {
  //              description "IP multicast group address";
  //              type jt:ipv6addr;
  //            }
  //            // uses apply-advanced;
  //            list source {
  //              key name;
  //              ordered-by user;
  //              description "IP multicast source address";
  //              leaf name {
  //                description "Source address of IP multicast data";
  //                type jt:ipv6addr;
  //              }
  //              // uses apply-advanced;
  //            }
  //          }
  //        }
  //      }
  //      list pseudowire-remote-address {
  //        key name;
  //        ordered-by user;
  //        description "Pseudowire interface options for MLD";
  //        leaf name {
  //          description "Pseudowire endpoint address";
  //          type jt:ipv4addr;
  //        }
  //        // uses apply-advanced;
  //        leaf multicast-router-interface {
  //          description "Enabling multicast-router-interface on the interface";
  //          type empty;
  //        }
  //        leaf immediate-leave {
  //          description "Enable immediate group leave on interfaces";
  //          type empty;
  //        }
  //      }
  //      list qualified-vlan {
  //        key name;
  //        ordered-by user;
  //        description "VLAN options for qualified-learning";
  //        leaf name {
  //          description "VLAN ID of the learning-domain";
  //          type union {
  //            type string {
  //              pattern "<.*>|$.*";
  //            }
  //            type uint32 {
  //              range "0 .. 1023";
  //            }
  //          }
  //        }
  //        // uses apply-advanced;
  //        leaf query-interval {
  //          description "When to send host query messages";
  //          units "seconds";
  //          type union {
  //            type string {
  //              pattern "<.*>|$.*";
  //            }
  //            type uint32 {
  //              range "1 .. 1024";
  //            }
  //          }
  //        }
  //        leaf query-response-interval {
  //          description "How long to wait for a host query response";
  //          units "seconds";
  //          type string {
  //          }
  //        }
  //        leaf query-last-member-interval {
  //          description "When to send group query messages";
  //          units "seconds";
  //          type string {
  //          }
  //        }
  //        leaf robust-count {
  //          description "Expected packet loss on a subnet";
  //          type union {
  //            type string {
  //              pattern "<.*>|$.*";
  //            }
  //            type uint32 {
  //              range "2 .. 10";
  //            }
  //          }
  //        }
  //        leaf immediate-leave {
  //          description "Enable immediate group leave on interfaces";
  //          type empty;
  //        }
  //        container proxy {
  //          description "Enable proxy mode";
  //          // uses apply-advanced;
  //          leaf source-address {
  //            description "Source IP address to use for proxy";
  //            type jt:ipv6addr;
  //          }
  //        }
  //        leaf evpn-ssm-reports-only {
  //          description "Accept and process only <s,g> reports of SSM groups";
  //          type empty;
  //        }
  //        list interface {
  //          key name;
  //          ordered-by user;
  //          description "Interface options for MLD";
  //          leaf name {
  //            description "Interface name";
  //            type union {
  //              type jt:interface-name;
  //              type string {
  //                pattern "<.*>|$.*";
  //              }
  //            }
  //          }
  //          // uses apply-advanced;
  //          leaf multicast-router-interface {
  //            description "Enabling multicast-router-interface on the interface";
  //            type empty;
  //          }
  //          leaf immediate-leave {
  //            description "Enable immediate group leave on interfaces";
  //            type empty;
  //          }
  //          leaf host-only-interface {
  //            description "Enable interfaces to be treated as host-side interfaces";
  //            type empty;
  //          }
  //          leaf group-limit {
  //            description "Maximum number of (source,group) per interface";
  //            type union {
  //              type string {
  //                pattern "<.*>|$.*";
  //              }
  //              type uint16 {
  //                range "1 .. 65535";
  //              }
  //            }
  //          }
  //          container static {
  //            description "Static group or source membership";
  //            // uses apply-advanced;
  //            list group {
  //              key name;
  //              ordered-by user;
  //              description "IP multicast group address";
  //              leaf name {
  //                description "IP multicast group address";
  //                type jt:ipv6addr;
  //              }
  //              // uses apply-advanced;
  //              list source {
  //                key name;
  //                ordered-by user;
  //                description "IP multicast source address";
  //                leaf name {
  //                  description "Source address of IP multicast data";
  //                  type jt:ipv6addr;
  //                }
  //                // uses apply-advanced;
  //              }
  //            }
  //          }
  //        }
  //        list pseudowire-remote-address {
  //          key name;
  //          ordered-by user;
  //          description "Pseudowire interface options for MLD";
  //          leaf name {
  //            description "Pseudowire endpoint address";
  //            type jt:ipv4addr;
  //          }
  //          // uses apply-advanced;
  //          leaf multicast-router-interface {
  //            description "Enabling multicast-router-interface on the interface";
  //            type empty;
  //          }
  //          leaf immediate-leave {
  //            description "Enable immediate group leave on interfaces";
  //            type empty;
  //          }
  //        }
  //      }
  //      leaf version {
  //        description "Set MLD snooping version number";
  //        type union {
  //          type string {
  //            pattern "<.*>|$.*";
  //          }
  //          type uint8 {
  //            range "1 .. 2";
  //          }
  //        }
  //      }
  //    }
  //  }
  //  grouping juniper-bridge-forwarding-options {
  //    // uses apply-advanced;
  //    container filter {
  //      description "Filtering for bridge forwarding table";
  //      // uses apply-advanced;
  //      leaf input {
  //        description "Name of input filter to apply for forwarded packets";
  //        type string;
  //      }
  //      leaf output {
  //        description "Name of output filter to apply for forwarded packets";
  //        type string;
  //      }
  //    }
  //    container flood {
  //      description "Filtering for bridge flood table";
  //      // uses apply-advanced;
  //      leaf input {
  //        description "Name of input filter to apply for bridge flood packets";
  //        type string;
  //      }
  //    }
  //    container dhcp-relay {
  //      description "Dynamic Host Configuration Protocol relay configuration";
  //      status deprecated;
  //      uses jdhcp-relay-type;
  //    }
  //    container dhcp-security {
  //      description "Dynamic ARP Inspection configuration";
  //      presence "enable dhcp-security";
  //      uses jdhcp-security-type;
  //    }
  //  }
  //  grouping jdhcp-relay-type {
  //    description "Dynamic Host Configuration Protocol relay configuration";
  //    // uses apply-advanced;
  //    container traceoptions {
  //      description "DHCP relay trace options";
  //      status deprecated;
  //      uses jdhcp-traceoptions-type;
  //    }
  //    container persistent-storage {
  //      description "Trigger to enable flat file storage";
  //      leaf automatic {
  //        description "Trigger automatically";
  //        type empty;
  //      }
  //    }
  //    leaf duplicate-clients-on-interface {
  //      description "Allow duplicate clients on different interfaces in a subnet";
  //      status deprecated;
  //      type empty;
  //    }
  //    container duplicate-clients-in-subnet {
  //      description "Allow duplicate clients in a subnet";
  //      uses jdhcp-duplicate-clients-in-subnet-type;
  //    }
  //    container interface-traceoptions {
  //      description "DHCP relay interface trace options";
  //      status deprecated;
  //      uses jdhcp-interface-traceoptions-type;
  //    }
  //    container dhcpv6 {
  //      description "DHCPv6 configuration";
  //      uses dhcpv6-relay-type;
  //    }
  //    leaf arp-inspection {
  //      description "Enable Dynamic ARP Inspection";
  //      type empty;
  //    }
  //    container forward-snooped-clients {
  //      description "Forward snooped (unicast) packets";
  //      choice interface-type {
  //        case case_1 {
  //          leaf configured-interfaces {
  //            description "Forward snooped (unicast) packets on configured interfaces";
  //            type empty;
  //          }
  //        }
  //        case case_2 {
  //          leaf non-configured-interfaces {
  //            description "Forward snooped (unicast) packets on non-configured interfaces";
  //            type empty;
  //          }
  //        }
  //        case case_3 {
  //          leaf all-interfaces {
  //            description "Forward snooped (unicast) packets on configured and non-configured interfaces";
  //            type empty;
  //          }
  //        }
  //      }
  //    }
  //    container authentication {
  //      description "DHCP authentication";
  //      uses authentication-type;
  //    }
  //    container liveness-detection {
  //      description "DHCP client liveness detection processing";
  //      uses dhcp-liveness-detection-type;
  //    }
  //    container dynamic-profile {
  //      description "Dynamic profile to use";
  //      uses dynamic-profile-type;
  //    }
  //    leaf service-profile {
  //      description "Dynamic profile to use for default service activation";
  //      type string {
  //        length "1 .. 128";
  //      }
  //    }
  //    leaf access-profile {
  //      description "Access profile to use for AAA services";
  //      type string {
  //        length "1 .. 128";
  //      }
  //    }
  //    container short-cycle-protection {
  //      description "Short cycle lockout configuration";
  //      leaf lockout-min-time {
  //        description "Short cycle lockout time in seconds";
  //        type union {
  //          type string {
  //            pattern "<.*>|$.*";
  //          }
  //          type uint32 {
  //            range "1 .. 86400";
  //          }
  //        }
  //      }
  //      leaf lockout-max-time {
  //        description "Short cycle lockout time in seconds";
  //        type union {
  //          type string {
  //            pattern "<.*>|$.*";
  //          }
  //          type uint32 {
  //            range "1 .. 86400";
  //          }
  //        }
  //      }
  //    }
  //    container overrides {
  //      description "DHCP override processing";
  //      presence "enable overrides";
  //      uses override-type;
  //    }
  //    container relay-option {
  //      description "DHCP option processing";
  //      presence "enable relay-option";
  //      uses dhcp-generic-v4-option;
  //    }
  //    container server-match {
  //      description "Server match processing";
  //      // uses apply-advanced;
  //      container default-action {
  //        description "Server match default action";
  //        presence "enable default-action";
  //        uses server-match-action-choice;
  //      }
  //      list address {
  //        key name;
  //        description "Server address";
  //        leaf name {
  //          description "Server address for matching";
  //          type jt:ipv4prefix;
  //        }
  //        // uses apply-advanced;
  //        choice server-match-action-choice {
  //          case case_1 {
  //            leaf forward-only {
  //              description "Forward without subscriber services when a match is made";
  //              type empty;
  //            }
  //          }
  //          case case_2 {
  //            leaf create-relay-entry {
  //              description "Create relay entry and allow subscriber services";
  //              type empty;
  //            }
  //          }
  //        }
  //      }
  //    }
  //    container relay-option-60 {
  //      description "DHCP option-60 processing";
  //      presence "enable relay-option-60";
  //      status deprecated;
  //      uses relay-option-60-type-top;
  //    }
  //    container relay-option-82 {
  //      description "DHCP option-82 processing";
  //      presence "enable relay-option-82";
  //      uses relay-option-82-type;
  //    }
  //    container forward-only {
  //      description "Forward DHCP packets without creating binding";
  //      presence "enable forward-only";
  //      uses forward-only-to-rc-type;
  //    }
  //    leaf description {
  //      description "Text description of servers";
  //      type string;
  //    }
  //    leaf maximum-hop-count {
  //      description "Maximum number of hops per packet";
  //      type union {
  //        type string {
  //          pattern "<.*>|$.*";
  //        }
  //        type uint32 {
  //          range "1 .. 16";
  //        }
  //      }
  //    }
  //    leaf minimum-wait-time {
  //      description "Minimum number of seconds before requests are forwarded";
  //      type union {
  //        type string {
  //          pattern "<.*>|$.*";
  //        }
  //        type uint32 {
  //          range "0 .. 30000";
  //        }
  //      }
  //    }
  //    leaf client-response-ttl {
  //      description "IP time-to-live value to set in responses to client";
  //      type union {
  //        type string {
  //          pattern "<.*>|$.*";
  //        }
  //        type uint32 {
  //          range "1 .. 255";
  //        }
  //      }
  //    }
  //    leaf source-ip-change {
  //      description "Use address of egress interface as source ip";
  //      type empty;
  //    }
  //    leaf forward-only-replies {
  //      description "Forward-only replies from server to appropriate logical-system:routing-instance based on options";
  //      type empty;
  //    }
  //    container server-group {
  //      description "Define a DHCP server group";
  //      uses server-group-type;
  //    }
  //    container active-server-group {
  //      description "Name of DHCP server group";
  //      uses dhcpv4-gbl-active-sg-type;
  //    }
  //    container route-suppression {
  //      description "Suppress access-internal and/or destination route addition";
  //      uses dhcp-route-suppression-type;
  //    }
  //    list group {
  //      key name;
  //      description "Define a DHCP group";
  //      uses dhcp-group;
  //    }
  //    list dual-stack-group {
  //      key name;
  //      description "Define a DHCP dual stack group";
  //      uses dhcp-dual-stack-group;
  //    }
  //    leaf no-snoop {
  //      description "Do not snoop DHCP packets";
  //      type empty;
  //    }
  //    leaf server-response-time {
  //      description "Number of seconds in a period of activity between the last server response and an unaswered request";
  //      default "0";
  //      type union {
  //        type uint32;
  //        type string {
  //          pattern "<.*>|$.*";
  //        }
  //      }
  //    }
  //    container lease-time-validation {
  //      presence "enable lease-time-validation";
  //      description "Configure lease time violation validation";
  //      // uses apply-advanced;
  //      leaf lease-time-threshold {
  //        description "Threshold for lease time violation in seconds";
  //        units "seconds";
  //        type union {
  //          type string {
  //            pattern "<.*>|$.*";
  //          }
  //          type uint32 {
  //            range "60 .. 2147483647";
  //          }
  //        }
  //      }
  //      container violation-action {
  //        description "Lease time validation violation action";
  //        leaf drop {
  //          description "Drop dhcpv4 offer and ack packets";
  //          type empty;
  //        }
  //      }
  //    }
  //    container leasequery {
  //      description "DHCP leasequery configuration";
  //      presence "enable leasequery";
  //      uses relay-leasequery-type;
  //    }
  //    container bulk-leasequery {
  //      description "DHCP bulk leasequery configuration";
  //      presence "enable bulk-leasequery";
  //      uses relay-bulk-leasequery-v4-type;
  //    }
  //    container active-leasequery {
  //      description "DHCPv4 active leasequery configuration";
  //      presence "enable active-leasequery";
  //      uses active-leasequery-v4-type;
  //    }
  //    container remote-id-mismatch {
  //      description "DHCP client remote-id mismatch";
  //      presence "enable remote-id-mismatch";
  //      uses dhcp-remote-id-mismatch-type;
  //    }
  //  }
  //  grouping dhcp-dual-stack-group {
  //    description "DHCP dual stack groups";
  //    leaf name {
  //      description "Dual stack group name";
  //      type string {
  //        length "1 .. 64";
  //      }
  //    }
  //    // uses apply-advanced;
  //    container authentication {
  //      description "DHCP authentication";
  //      uses dual-stack-authentication-type;
  //    }
  //    leaf service-profile {
  //      description "Dynamic profile to use for default service activation";
  //      type string {
  //        length "1 .. 128";
  //      }
  //    }
  //    leaf access-profile {
  //      description "Access profile to be used for jdhcpd";
  //      type string {
  //        length "1 .. 128";
  //      }
  //    }
  //    container dynamic-profile {
  //      description "Dynamic profile to use";
  //      uses dynamic-profile-type;
  //    }
  //    container liveness-detection {
  //      description "DHCP client liveness detection processing";
  //      uses dhcp-liveness-detection-dualstack-type;
  //    }
  //    container relay-agent-interface-id {
  //      description "Interface-id option processing";
  //      presence "enable relay-agent-interface-id";
  //      uses v6-relay-option-interface-id-type;
  //    }
  //    container relay-agent-remote-id {
  //      description "Remote-id option processing";
  //      presence "enable relay-agent-remote-id";
  //      uses v6-relay-option-remote-id-type;
  //    }
  //    container classification-key {
  //      description "Classification key for identifying dual stack household";
  //      uses classification-types;
  //    }
  //    leaf dual-stack-interface-client-limit {
  //      description "Limit the number of client allowed on an interface";
  //      type union {
  //        type string {
  //          pattern "<.*>|$.*";
  //        }
  //        type uint32 {
  //          range "1 .. 500000";
  //        }
  //      }
  //    }
  //    container protocol-master {
  //      description "Select family as protocol master";
  //      uses jdhcp-dual-stack-protocol-mstr-type;
  //    }
  //    container short-cycle-protection {
  //      description "Short cycle lockout configuration";
  //      leaf lockout-min-time {
  //        description "Short cycle lockout time in seconds";
  //        type union {
  //          type string {
  //            pattern "<.*>|$.*";
  //          }
  //          type uint32 {
  //            range "1 .. 86400";
  //          }
  //        }
  //      }
  //      leaf lockout-max-time {
  //        description "Short cycle lockout time in seconds";
  //        type union {
  //          type string {
  //            pattern "<.*>|$.*";
  //          }
  //          type uint32 {
  //            range "1 .. 86400";
  //          }
  //        }
  //      }
  //    }
  //  }
  //  grouping dhcp-generic-v4-option {
  //    description "Generic DHCP options processing";
  //    // uses apply-advanced;
  //    leaf option-number {
  //      description "Option number";
  //      status deprecated;
  //      type enumeration {
  //        enum "60" {
  //          description "Option 60";
  //          status deprecated;
  //        }
  //        enum "77" {
  //          description "Option 77";
  //          status deprecated;
  //        }
  //      }
  //    }
  //    container equals {
  //      description "Generic option equals";
  //      status deprecated;
  //      uses relay-v4-option-ascii-hex;
  //    }
  //    container default-action {
  //      description "Generic option default action";
  //      status deprecated;
  //      uses dhcp-v4-option-default-action;
  //    }
  //    container starts-with {
  //      description "Generic option starts with";
  //      status deprecated;
  //      uses relay-v4-option-ascii-hex;
  //    }
  //    container option-60 {
  //      description "Add option 60 processing";
  //      presence "enable option-60";
  //      uses dhcp-generic-v4-option-type;
  //    }
  //    container option-77 {
  //      description "Add option 77 processing";
  //      presence "enable option-77";
  //      uses dhcp-generic-v4-option-type;
  //    }
  //    list option-order {
  //      key name;
  //      ordered-by user;
  //      description "Options precedence order";
  //      leaf name {
  //        description "Option number";
  //        type enumeration {
  //          enum "60" {
  //            description "Option 60";
  //          }
  //          enum "77" {
  //            description "Option 77";
  //          }
  //        }
  //      }
  //      // uses apply-advanced;
  //    }
  //  }
  //  grouping dhcp-generic-v4-option-type {
  //    // uses apply-advanced;
  //    container equals {
  //      description "Generic option equals";
  //      uses relay-v4-option-ascii-hex;
  //    }
  //    container default-action {
  //      description "Generic option default action";
  //      uses dhcp-v4-option-default-action;
  //    }
  //    container starts-with {
  //      description "Generic option starts with";
  //      uses relay-v4-option-ascii-hex;
  //    }
  //  }
  //  grouping dhcp-group {
  //    description "DHCP groups";
  //    leaf name {
  //      description "Group name";
  //      type string {
  //        length "1 .. 64";
  //      }
  //    }
  //    // uses apply-advanced;
  //    container active-server-group {
  //      description "Name of DHCP server group";
  //      uses dhcpv4-gp-active-sg-type;
  //    }
  //    container authentication {
  //      description "DHCP authentication";
  //      uses authentication-type;
  //    }
  //    container liveness-detection {
  //      description "DHCP client liveness detection processing";
  //      uses dhcp-liveness-detection-type;
  //    }
  //    container dynamic-profile {
  //      description "Dynamic profile to use";
  //      uses dynamic-profile-type;
  //    }
  //    leaf service-profile {
  //      description "Dynamic profile to use for default service activation";
  //      type string {
  //        length "1 .. 128";
  //      }
  //    }
  //    leaf access-profile {
  //      description "Access profile to use for AAA services";
  //      type string {
  //        length "1 .. 128";
  //      }
  //    }
  //    container overrides {
  //      description "DHCP override processing";
  //      presence "enable overrides";
  //      uses override-type;
  //    }
  //    container short-cycle-protection {
  //      description "Short cycle lockout configuration";
  //      leaf lockout-min-time {
  //        description "Short cycle lockout time in seconds";
  //        type union {
  //          type string {
  //            pattern "<.*>|$.*";
  //          }
  //          type uint32 {
  //            range "1 .. 86400";
  //          }
  //        }
  //      }
  //      leaf lockout-max-time {
  //        description "Short cycle lockout time in seconds";
  //        type union {
  //          type string {
  //            pattern "<.*>|$.*";
  //          }
  //          type uint32 {
  //            range "1 .. 86400";
  //          }
  //        }
  //      }
  //    }
  //    container server-match {
  //      description "Server match processing";
  //      // uses apply-advanced;
  //      container default-action {
  //        description "Server match default action";
  //        presence "enable default-action";
  //        uses server-match-action-choice;
  //      }
  //      list address {
  //        key name;
  //        description "Server address";
  //        leaf name {
  //          description "Server address for matching";
  //          type jt:ipv4prefix;
  //        }
  //        // uses apply-advanced;
  //        choice server-match-action-choice {
  //          case case_1 {
  //            leaf forward-only {
  //              description "Forward without subscriber services when a match is made";
  //              type empty;
  //            }
  //          }
  //          case case_2 {
  //            leaf create-relay-entry {
  //              description "Create relay entry and allow subscriber services";
  //              type empty;
  //            }
  //          }
  //        }
  //      }
  //    }
  //    container relay-option {
  //      description "DHCP option processing";
  //      presence "enable relay-option";
  //      uses dhcp-generic-v4-option;
  //    }
  //    container relay-option-60 {
  //      description "DHCP option-60 processing";
  //      presence "enable relay-option-60";
  //      status deprecated;
  //      uses relay-option-60-type-group;
  //    }
  //    container relay-option-82 {
  //      description "DHCP option-82 processing";
  //      presence "enable relay-option-82";
  //      uses relay-option-82-type;
  //    }
  //    container forward-only {
  //      description "Forward DHCP packets without creating binding";
  //      presence "enable forward-only";
  //      uses forward-only-to-rc-type;
  //    }
  //    container route-suppression {
  //      description "Suppress access-internal and/or destination route addition";
  //      uses dhcp-route-suppression-type;
  //    }
  //    leaf description {
  //      description "Text description of servers";
  //      type string;
  //    }
  //    leaf maximum-hop-count {
  //      description "Maximum number of hops per packet";
  //      type union {
  //        type string {
  //          pattern "<.*>|$.*";
  //        }
  //        type uint32 {
  //          range "1 .. 16";
  //        }
  //      }
  //    }
  //    leaf minimum-wait-time {
  //      description "Minimum number of seconds before requests are forwarded";
  //      type union {
  //        type string {
  //          pattern "<.*>|$.*";
  //        }
  //        type uint32 {
  //          range "0 .. 30000";
  //        }
  //      }
  //    }
  //    leaf client-response-ttl {
  //      description "IP time-to-live value to set in responses to client";
  //      type union {
  //        type string {
  //          pattern "<.*>|$.*";
  //        }
  //        type uint32 {
  //          range "1 .. 255";
  //        }
  //      }
  //    }
  //    leaf source-ip-change {
  //      description "Use address of egress interface as source ip";
  //      type empty;
  //    }
  //    list interface {
  //      key name;
  //      description "One or more interfaces";
  //      leaf name {
  //        description "Interface name";
  //        type union {
  //          type jt:interface-name;
  //          type string {
  //            pattern "<.*>|$.*";
  //          }
  //        }
  //      }
  //      // uses apply-advanced;
  //      leaf upto {
  //        description "Interface up to";
  //        type union {
  //          type jt:interface-name;
  //          type string {
  //            pattern "<.*>|$.*";
  //          }
  //        }
  //      }
  //      leaf exclude {
  //        description "Exclude this interface range";
  //        type empty;
  //      }
  //      leaf trace {
  //        description "Enable tracing for this interface";
  //        type empty;
  //      }
  //      container overrides {
  //        description "DHCP override processing";
  //        uses override-type;
  //      }
  //      container dynamic-profile {
  //        description "Dynamic profile to use";
  //        uses dynamic-profile-type;
  //      }
  //      leaf service-profile {
  //        description "Dynamic profile to use for default service activation";
  //        type string {
  //          length "1 .. 128";
  //        }
  //      }
  //      leaf access-profile {
  //        description "Access profile to use for AAA services";
  //        type string {
  //          length "1 .. 128";
  //        }
  //      }
  //      container short-cycle-protection {
  //        description "Short cycle lockout configuration";
  //        leaf lockout-min-time {
  //          description "Short cycle lockout time in seconds";
  //          type union {
  //            type string {
  //              pattern "<.*>|$.*";
  //            }
  //            type uint32 {
  //              range "1 .. 86400";
  //            }
  //          }
  //        }
  //        leaf lockout-max-time {
  //          description "Short cycle lockout time in seconds";
  //          type union {
  //            type string {
  //              pattern "<.*>|$.*";
  //            }
  //            type uint32 {
  //              range "1 .. 86400";
  //            }
  //          }
  //        }
  //      }
  //    }
  //    list interface-tag {
  //      key name;
  //      description "Interfae tag configuration";
  //      leaf name {
  //        description "Interface tag name";
  //        type string {
  //          length "1 .. 64";
  //        }
  //      }
  //      // uses apply-advanced;
  //      container overrides {
  //        description "DHCP override processing";
  //        uses override-type;
  //      }
  //      container dynamic-profile {
  //        description "Dynamic profile to use";
  //        uses dynamic-profile-type;
  //      }
  //      leaf service-profile {
  //        description "Dynamic profile to use for default service activation";
  //        type string {
  //          length "1 .. 128";
  //        }
  //      }
  //      leaf access-profile {
  //        description "Access profile to use for AAA services";
  //        type string {
  //          length "1 .. 128";
  //        }
  //      }
  //      container short-cycle-protection {
  //        description "Short cycle lockout configuration";
  //        leaf lockout-min-time {
  //          description "Short cycle lockout time in seconds";
  //          type union {
  //            type string {
  //              pattern "<.*>|$.*";
  //            }
  //            type uint32 {
  //              range "1 .. 86400";
  //            }
  //          }
  //        }
  //        leaf lockout-max-time {
  //          description "Short cycle lockout time in seconds";
  //          type union {
  //            type string {
  //              pattern "<.*>|$.*";
  //            }
  //            type uint32 {
  //              range "1 .. 86400";
  //            }
  //          }
  //        }
  //      }
  //    }
  //    container remote-id-mismatch {
  //      description "DHCP client remote-id mismatch";
  //      presence "enable remote-id-mismatch";
  //      uses dhcp-remote-id-mismatch-type;
  //    }
  //    container lease-time-validation {
  //      presence "enable lease-time-validation";
  //      description "Configure lease time violation validation";
  //      // uses apply-advanced;
  //      leaf lease-time-threshold {
  //        description "Threshold for lease time violation in seconds";
  //        units "seconds";
  //        type union {
  //          type string {
  //            pattern "<.*>|$.*";
  //          }
  //          type uint32 {
  //            range "60 .. 2147483647";
  //          }
  //        }
  //      }
  //      container violation-action {
  //        description "Lease time validation violation action";
  //        leaf drop {
  //          description "Drop dhcpv4 offer and ack packets";
  //          type empty;
  //        }
  //      }
  //    }
  //  }
  //  grouping dhcp-v4-option-default-action {
  //    description "Default action";
  //    // uses apply-advanced;
  //    choice server-group-choice {
  //      case case_1 {
  //        leaf relay-server-group {
  //          description "Name of DHCP relay server group when match is made";
  //          type string {
  //            length "1 .. 64";
  //          }
  //        }
  //      }
  //      case case_2 {
  //        leaf local-server-group {
  //          description "Name of DHCP local server group when match is made";
  //          type string {
  //            length "1 .. 64";
  //          }
  //        }
  //      }
  //      case case_3 {
  //        leaf drop {
  //          description "Discard when a match is made";
  //          type empty;
  //        }
  //      }
  //      case case_4 {
  //        leaf forward-only {
  //          description "Forward without subscriber services when a match is made";
  //          type empty;
  //        }
  //      }
  //    }
  //  }
  //  grouping dhcpv4-gbl-active-sg-type {
  //    leaf active-server-group {
  //      description "Name of DHCP server group";
  //      type string {
  //        length "1 .. 64";
  //      }
  //    }
  //    leaf allow-server-change {
  //      description "Accept DHCP-ACK from any server in this group";
  //      type empty;
  //    }
  //  }
  //  grouping dhcpv4-gp-active-sg-type {
  //    leaf active-server-group {
  //      description "Name of DHCP server group";
  //      type string {
  //        length "1 .. 64";
  //      }
  //    }
  //    leaf allow-server-change {
  //      description "Accept DHCP-ACK from any server in this group";
  //      type empty;
  //    }
  //  }
  //  grouping dhcpv6-relay-type {
  //    description "DHCPv6 relay configuration";
  //    // uses apply-advanced;
  //    container authentication {
  //      description "DHCPv6 authentication";
  //      uses dhcpv6-authentication-type;
  //    }
  //    container persistent-storage {
  //      description "Trigger to enable flat file storage";
  //      leaf automatic {
  //        description "Trigger automatically";
  //        type empty;
  //      }
  //    }
  //    container liveness-detection {
  //      description "DHCPv6 client liveness detection processing";
  //      uses dhcpv6-liveness-detection-type;
  //    }
  //    container dynamic-profile {
  //      description "Dynamic profile to use";
  //      uses dynamic-profile-type;
  //    }
  //    leaf service-profile {
  //      description "Dynamic profile to use for default service activation";
  //      type string {
  //        length "1 .. 128";
  //      }
  //    }
  //    leaf access-profile {
  //      description "Access profile to use for AAA services";
  //      type string {
  //        length "1 .. 128";
  //      }
  //    }
  //    container short-cycle-protection {
  //      description "Short cycle lockout configuration";
  //      leaf lockout-min-time {
  //        description "Short cycle lockout time in seconds";
  //        type union {
  //          type string {
  //            pattern "<.*>|$.*";
  //          }
  //          type uint32 {
  //            range "1 .. 86400";
  //          }
  //        }
  //      }
  //      leaf lockout-max-time {
  //        description "Short cycle lockout time in seconds";
  //        type union {
  //          type string {
  //            pattern "<.*>|$.*";
  //          }
  //          type uint32 {
  //            range "1 .. 86400";
  //          }
  //        }
  //      }
  //    }
  //    container overrides {
  //      description "DHCPv6 override processing";
  //      presence "enable overrides";
  //      uses dhcpv6-override-relay-type;
  //    }
  //    container relay-option {
  //      description "DHCPv6 option processing";
  //      presence "enable relay-option";
  //      uses dhcp-generic-v6-option;
  //    }
  //    leaf exclude-relay-agent-identifier {
  //      description "Exclude relay agent identifier from packets to server";
  //      type empty;
  //    }
  //    container server-match {
  //      description "Server match processing";
  //      // uses apply-advanced;
  //      container default-action {
  //        description "Server match default action";
  //        uses server-match-action-choice;
  //      }
  //      container duid {
  //        description "Match duid processing";
  //        // uses apply-advanced;
  //        container equals {
  //          description "Duid equals";
  //          uses server-match-v6-ascii-hex;
  //        }
  //        container starts-with {
  //          description "Duid starts with";
  //          uses server-match-v6-ascii-hex;
  //        }
  //      }
  //      list address {
  //        key name;
  //        description "Server ipv6 address";
  //        leaf name {
  //          description "Server ipv6 address for matching";
  //          type jt:ipv6prefix;
  //        }
  //        // uses apply-advanced;
  //        choice server-match-action-choice {
  //          case case_1 {
  //            leaf forward-only {
  //              description "Forward without subscriber services when a match is made";
  //              type empty;
  //            }
  //          }
  //          case case_2 {
  //            leaf create-relay-entry {
  //              description "Create relay entry and allow subscriber services";
  //              type empty;
  //            }
  //          }
  //        }
  //      }
  //    }
  //    leaf relay-agent-option-79 {
  //      description "Add the client MAC address to the Relay Forward header.";
  //      type empty;
  //    }
  //    container vendor-specific-information {
  //      description "DHCPv6 option 17 vendor-specific processing";
  //      uses jdhcp-vendor-specific-type;
  //    }
  //    container forward-only {
  //      description "Forward DHCPv6 packets without creating binding";
  //      presence "enable forward-only";
  //      uses forward-only-to-rc-type;
  //    }
  //    leaf forward-only-replies {
  //      description "Forward-only replies from server to appropriate logical-system:routing-instance based on options";
  //      type empty;
  //    }
  //    container forward-snooped-clients {
  //      description "Forward snooped (unicast) packets";
  //      choice interface-type {
  //        case case_1 {
  //          leaf configured-interfaces {
  //            description "Forward snooped (unicast) packets on configured interfaces";
  //            type empty;
  //          }
  //        }
  //        case case_2 {
  //          leaf non-configured-interfaces {
  //            description "Forward snooped (unicast) packets on non-configured interfaces";
  //            type empty;
  //          }
  //        }
  //        case case_3 {
  //          leaf all-interfaces {
  //            description "Forward snooped (unicast) packets on configured and non-configured interfaces";
  //            type empty;
  //          }
  //        }
  //      }
  //    }
  //    container route-suppression {
  //      description "Suppress access-internal and/or access route addition";
  //      uses dhcpv6-route-suppression-type;
  //    }
  //    list group {
  //      key name;
  //      description "Define a DHCPv6 relay group";
  //      uses dhcpv6-relay-group;
  //    }
  //    container relay-agent-interface-id {
  //      description "DHCPv6 interface-id option processing";
  //      presence "enable relay-agent-interface-id";
  //      uses v6-relay-option-interface-id-type;
  //    }
  //    container relay-agent-remote-id {
  //      description "DHCPv6 remote-id option processing";
  //      presence "enable relay-agent-remote-id";
  //      uses v6-relay-option-remote-id-type;
  //    }
  //    container server-group {
  //      description "Define a DHCPv6 server group";
  //      uses v6-server-group-type;
  //    }
  //    container active-server-group {
  //      description "Name of DHCPv6 server group";
  //      uses dhcpv6-gbl-active-sg-type;
  //    }
  //    leaf server-response-time {
  //      description "Number of seconds in a period of activity between the last server response and an unaswered request";
  //      default "0";
  //      type union {
  //        type uint32;
  //        type string {
  //          pattern "<.*>|$.*";
  //        }
  //      }
  //    }
  //    container lease-time-validation {
  //      presence "enable lease-time-validation";
  //      description "Configure lease time violation validation";
  //      // uses apply-advanced;
  //      leaf lease-time-threshold {
  //        description "Threshold for lease time violation in seconds";
  //        units "seconds";
  //        type union {
  //          type string {
  //            pattern "<.*>|$.*";
  //          }
  //          type uint32 {
  //            range "60 .. 2147483647";
  //          }
  //        }
  //      }
  //      container violation-action {
  //        description "Lease time validation violation action";
  //        leaf drop {
  //          description "Drop dhcpv6 advertise and reply packets";
  //          type empty;
  //        }
  //      }
  //    }
  //    leaf no-snoop {
  //      description "Do not snoop DHCPV6 packets";
  //      type empty;
  //    }
  //    container leasequery {
  //      description "DHCPv6 leasequery configuration";
  //      presence "enable leasequery";
  //      uses relay-leasequery-type;
  //    }
  //    container bulk-leasequery {
  //      description "DHCPv6 bulk leasequery configuration";
  //      presence "enable bulk-leasequery";
  //      uses relay-bulk-leasequery-v6-type;
  //    }
  //    container active-leasequery {
  //      description "DHCPv6 active leasequery configuration";
  //      presence "enable active-leasequery";
  //      uses active-leasequery-v6-type;
  //    }
  //    container remote-id-mismatch {
  //      description "DHCP client remote-id mismatch";
  //      presence "enable remote-id-mismatch";
  //      uses dhcp-remote-id-mismatch-type;
  //    }
  //    container duplicate-clients {
  //      description "Allow duplicate clients";
  //      uses dhcpv6-duplicate-clients-type;
  //    }
  //  }
  //  grouping dhcp-generic-v6-option {
  //    description "Generic DHCPv6 options processing";
  //    // uses apply-advanced;
  //    leaf option-number {
  //      description "Option number";
  //      status deprecated;
  //      type enumeration {
  //        enum "15" {
  //          description "Option 15";
  //          status deprecated;
  //        }
  //        enum "16" {
  //          description "Option 16";
  //          status deprecated;
  //        }
  //      }
  //    }
  //    container equals {
  //      description "Generic option equals";
  //      status deprecated;
  //      uses relay-v6-option-ascii-hex;
  //    }
  //    container default-action {
  //      description "Generic option default action";
  //      status deprecated;
  //      uses dhcp-v6-option-default-action;
  //    }
  //    container starts-with {
  //      description "Generic option starts with";
  //      status deprecated;
  //      uses relay-v6-option-ascii-hex;
  //    }
  //    container option-15 {
  //      description "Add option 15 processing";
  //      presence "enable option-15";
  //      uses dhcp-generic-v6-option-type;
  //    }
  //    container option-16 {
  //      description "Add option 16 processing";
  //      presence "enable option-16";
  //      uses dhcp-generic-v6-option-type;
  //    }
  //    list option-order {
  //      key name;
  //      ordered-by user;
  //      description "Options precedence order";
  //      leaf name {
  //        description "Option number";
  //        type enumeration {
  //          enum "15" {
  //            description "Option 15";
  //          }
  //          enum "16" {
  //            description "Option 16";
  //          }
  //        }
  //      }
  //      // uses apply-advanced;
  //    }
  //  }
  //  grouping dhcp-generic-v6-option-type {
  //    // uses apply-advanced;
  //    container equals {
  //      description "Generic option equals";
  //      uses relay-v6-option-ascii-hex;
  //    }
  //    container default-action {
  //      description "Generic option default action";
  //      uses dhcp-v6-option-default-action;
  //    }
  //    container starts-with {
  //      description "Generic option starts with";
  //      uses relay-v6-option-ascii-hex;
  //    }
  //  }
  //  grouping dhcp-v6-option-default-action {
  //    description "Default action";
  //    // uses apply-advanced;
  //    choice server-group-choice {
  //      case case_1 {
  //        leaf relay-server-group {
  //          description "Name of DHCP relay server group when match is made";
  //          type string {
  //            length "1 .. 64";
  //          }
  //        }
  //      }
  //      case case_2 {
  //        leaf drop {
  //          description "Discard when a match is made";
  //          type empty;
  //        }
  //      }
  //      case case_3 {
  //        leaf forward-only {
  //          description "Forward without subscriber services when a match is made";
  //          type empty;
  //        }
  //      }
  //    }
  //  }
  //  grouping dhcpv6-gbl-active-sg-type {
  //    // uses apply-advanced;
  //    leaf active-server-group {
  //      description "Name of DHCPv6 server group";
  //      type string {
  //        length "1 .. 64";
  //      }
  //    }
  //  }
  //  grouping dhcpv6-override-relay-type {
  //    description "DHCPv6 relay override processing";
  //    // uses apply-advanced;
  //    choice allow-snooped-clients-choice {
  //      leaf allow-snooped-clients {
  //        description "Allow client creation from snooped PDUs";
  //        type empty;
  //      }
  //      leaf no-allow-snooped-clients {
  //        description "Don't allow client creation from snooped PDUs";
  //        type empty;
  //      }
  //    }
  //    leaf delay-authentication {
  //      description "Delay subscriber authentication in DHCP protocol processing until request packet";
  //      type empty;
  //    }
  //    leaf interface-client-limit {
  //      description "Limit the number of clients allowed on an interface";
  //      type union {
  //        type string {
  //          pattern "<.*>|$.*";
  //        }
  //        type uint32 {
  //          range "1 .. 500000";
  //        }
  //      }
  //    }
  //    leaf dual-stack {
  //      description "Dual stack group to use.";
  //      type string {
  //        length "1 .. 64";
  //      }
  //    }
  //    leaf no-bind-on-request {
  //      description "Do not bind if stray DHCPv6 RENEW, REBIND is received";
  //      type empty;
  //    }
  //    container client-negotiation-match {
  //      description "Use secondary match criteria for SOLICIT PDU";
  //      choice match-with {
  //        case case_1 {
  //          leaf incoming-interface {
  //            description "Use incoming interface";
  //            type empty;
  //          }
  //        }
  //      }
  //    }
  //    leaf send-release-on-delete {
  //      description "Always send RELEASE to the server when a binding is deleted";
  //      type empty;
  //    }
  //    leaf always-process-option-request-option {
  //      description "Always process option even after address allocation failure";
  //      type empty;
  //    }
  //    leaf relay-source {
  //      description "Interface for relay source";
  //      type union {
  //        type jt:interface-name;
  //        type string {
  //          pattern "<.*>|$.*";
  //        }
  //      }
  //    }
  //    leaf delete-binding-on-renegotiation {
  //      description "Delete binding on renegotiation";
  //      type empty;
  //    }
  //    leaf asymmetric-lease-time {
  //      description "Use a reduced lease time for the client. In seconds";
  //      units "seconds";
  //      type union {
  //        type string {
  //          pattern "<.*>|$.*";
  //        }
  //        type uint32 {
  //          range "600 .. 86400";
  //        }
  //      }
  //    }
  //    leaf asymmetric-prefix-lease-time {
  //      description "Use a reduced prefix lease time for the client. In seconds";
  //      units "seconds";
  //      type union {
  //        type string {
  //          pattern "<.*>|$.*";
  //        }
  //        type uint32 {
  //          range "600 .. 86400";
  //        }
  //      }
  //    }
  //  }
  //  grouping dhcpv6-relay-group {
  //    description "DHCPv6 groups";
  //    leaf name {
  //      description "Group name";
  //      type string {
  //        length "1 .. 64";
  //      }
  //    }
  //    // uses apply-advanced;
  //    container active-server-group {
  //      description "Name of DHCPv6 server group";
  //      uses dhcpv6-gp-active-sg-type;
  //    }
  //    list dual-stack-group {
  //      key name;
  //      description "Define a DHCP dual stack group";
  //      uses dhcp-dual-stack-group;
  //    }
  //    container authentication {
  //      description "DHCPv6 authentication";
  //      uses dhcpv6-authentication-type;
  //    }
  //    container liveness-detection {
  //      description "DHCPv6 client liveness detection processing";
  //      uses dhcpv6-liveness-detection-type;
  //    }
  //    container dynamic-profile {
  //      description "Dynamic profile to use";
  //      uses dynamic-profile-type;
  //    }
  //    leaf service-profile {
  //      description "Dynamic profile to use for default service activation";
  //      type string {
  //        length "1 .. 128";
  //      }
  //    }
  //    leaf access-profile {
  //      description "Access profile to use for AAA services";
  //      type string {
  //        length "1 .. 128";
  //      }
  //    }
  //    container short-cycle-protection {
  //      description "Short cycle lockout configuration";
  //      leaf lockout-min-time {
  //        description "Short cycle lockout time in seconds";
  //        type union {
  //          type string {
  //            pattern "<.*>|$.*";
  //          }
  //          type uint32 {
  //            range "1 .. 86400";
  //          }
  //        }
  //      }
  //      leaf lockout-max-time {
  //        description "Short cycle lockout time in seconds";
  //        type union {
  //          type string {
  //            pattern "<.*>|$.*";
  //          }
  //          type uint32 {
  //            range "1 .. 86400";
  //          }
  //        }
  //      }
  //    }
  //    container overrides {
  //      description "DHCPv6 override processing";
  //      presence "enable overrides";
  //      uses dhcpv6-override-relay-type;
  //    }
  //    container relay-option {
  //      description "DHCPv6 option processing";
  //      presence "enable relay-option";
  //      uses dhcp-generic-v6-option;
  //    }
  //    container vendor-specific-information {
  //      description "DHCPv6 option 17 vendor-specific processing";
  //      uses jdhcp-vendor-specific-type;
  //    }
  //    container forward-only {
  //      description "Forward DHCPv6 packets without creating binding";
  //      presence "enable forward-only";
  //      uses forward-only-to-rc-type;
  //    }
  //    container relay-agent-interface-id {
  //      description "DHCPv6 interface-id option processing";
  //      presence "enable relay-agent-interface-id";
  //      uses v6-relay-option-interface-id-type;
  //    }
  //    container relay-agent-remote-id {
  //      description "DHCPv6 remote-id option processing";
  //      presence "enable relay-agent-remote-id";
  //      uses v6-relay-option-remote-id-type;
  //    }
  //    container route-suppression {
  //      description "Suppress access-internal and/or access route addition";
  //      uses dhcpv6-route-suppression-type;
  //    }
  //    leaf relay-agent-option-79 {
  //      description "Add the client MAC address to the Relay Forward header.";
  //      type empty;
  //    }
  //    list interface {
  //      key name;
  //      description "One or more interfaces";
  //      leaf name {
  //        description "Interface name";
  //        type union {
  //          type jt:interface-name;
  //          type string {
  //            pattern "<.*>|$.*";
  //          }
  //        }
  //      }
  //      // uses apply-advanced;
  //      leaf upto {
  //        description "Interface up to";
  //        type union {
  //          type jt:interface-name;
  //          type string {
  //            pattern "<.*>|$.*";
  //          }
  //        }
  //      }
  //      leaf exclude {
  //        description "Exclude this interface range";
  //        type empty;
  //      }
  //      leaf trace {
  //        description "Enable tracing for this interface";
  //        type empty;
  //      }
  //      container overrides {
  //        description "DHCPv6 override processing";
  //        uses dhcpv6-override-relay-type;
  //      }
  //      container dynamic-profile {
  //        description "Dynamic profile to use";
  //        uses dynamic-profile-type;
  //      }
  //      leaf service-profile {
  //        description "Dynamic profile to use for default service activation";
  //        type string {
  //          length "1 .. 128";
  //        }
  //      }
  //      leaf access-profile {
  //        description "Access profile to use for AAA services";
  //        type string {
  //          length "1 .. 128";
  //        }
  //      }
  //      container short-cycle-protection {
  //        description "Short cycle lockout configuration";
  //        leaf lockout-min-time {
  //          description "Short cycle lockout time in seconds";
  //          type union {
  //            type string {
  //              pattern "<.*>|$.*";
  //            }
  //            type uint32 {
  //              range "1 .. 86400";
  //            }
  //          }
  //        }
  //        leaf lockout-max-time {
  //          description "Short cycle lockout time in seconds";
  //          type union {
  //            type string {
  //              pattern "<.*>|$.*";
  //            }
  //            type uint32 {
  //              range "1 .. 86400";
  //            }
  //          }
  //        }
  //      }
  //    }
  //    list interface-tag {
  //      key name;
  //      description "Interface tag configurations";
  //      leaf name {
  //        description "Interface tag name";
  //        type string {
  //          length "1 .. 64";
  //        }
  //      }
  //      // uses apply-advanced;
  //      container overrides {
  //        description "DHCPv6 override processing";
  //        uses dhcpv6-override-relay-type;
  //      }
  //      container dynamic-profile {
  //        description "Dynamic profile to use";
  //        uses dynamic-profile-type;
  //      }
  //      leaf service-profile {
  //        description "Dynamic profile to use for default service activation";
  //        type string {
  //          length "1 .. 128";
  //        }
  //      }
  //      leaf access-profile {
  //        description "Access profile to use for AAA services";
  //        type string {
  //          length "1 .. 128";
  //        }
  //      }
  //      container short-cycle-protection {
  //        description "Short cycle lockout configuration";
  //        leaf lockout-min-time {
  //          description "Short cycle lockout time in seconds";
  //          type union {
  //            type string {
  //              pattern "<.*>|$.*";
  //            }
  //            type uint32 {
  //              range "1 .. 86400";
  //            }
  //          }
  //        }
  //        leaf lockout-max-time {
  //          description "Short cycle lockout time in seconds";
  //          type union {
  //            type string {
  //              pattern "<.*>|$.*";
  //            }
  //            type uint32 {
  //              range "1 .. 86400";
  //            }
  //          }
  //        }
  //      }
  //    }
  //    container lease-time-validation {
  //      presence "enable lease-time-validation";
  //      description "Configure lease time violation validation";
  //      // uses apply-advanced;
  //      leaf lease-time-threshold {
  //        description "Threshold for lease time violation in seconds";
  //        units "seconds";
  //        type union {
  //          type string {
  //            pattern "<.*>|$.*";
  //          }
  //          type uint32 {
  //            range "60 .. 2147483647";
  //          }
  //        }
  //      }
  //      container violation-action {
  //        description "Lease time validation violation action";
  //        leaf drop {
  //          description "Drop dhcpv6 advertise and reply packets";
  //          type empty;
  //        }
  //      }
  //    }
  //    container remote-id-mismatch {
  //      description "DHCP client remote-id mismatch";
  //      presence "enable remote-id-mismatch";
  //      uses dhcp-remote-id-mismatch-type;
  //    }
  //    container server-match {
  //      description "Server match processing";
  //      // uses apply-advanced;
  //      container default-action {
  //        description "Server match default action";
  //        uses server-match-action-choice;
  //      }
  //      container duid {
  //        description "Match duid processing";
  //        // uses apply-advanced;
  //        container equals {
  //          description "Duid equals";
  //          uses server-match-v6-ascii-hex;
  //        }
  //        container starts-with {
  //          description "Duid starts with";
  //          uses server-match-v6-ascii-hex;
  //        }
  //      }
  //      list address {
  //        key name;
  //        description "Server ipv6 address";
  //        leaf name {
  //          description "Server ipv6 address for matching";
  //          type jt:ipv6prefix;
  //        }
  //        // uses apply-advanced;
  //        choice server-match-action-choice {
  //          case case_1 {
  //            leaf forward-only {
  //              description "Forward without subscriber services when a match is made";
  //              type empty;
  //            }
  //          }
  //          case case_2 {
  //            leaf create-relay-entry {
  //              description "Create relay entry and allow subscriber services";
  //              type empty;
  //            }
  //          }
  //        }
  //      }
  //    }
  //  }
  //  grouping dhcpv6-gp-active-sg-type {
  //    // uses apply-advanced;
  //    leaf active-server-group {
  //      description "Name of DHCPv6 server group";
  //      type string {
  //        length "1 .. 64";
  //      }
  //    }
  //  }
  //  grouping forward-only-to-rc-type {
  //    description "Forward DHCP packets without creating binding";
  //    // uses apply-advanced;
  //    leaf logical-system {
  //      default "current";
  //      type string;
  //    }
  //    leaf routing-instance {
  //      default "current";
  //      type string;
  //    }
  //  }
  //  grouping jdhcp-security-type {
  //    description "DHCP access security configuration";
  //    // uses apply-advanced;
  //    leaf no-dhcp-snooping {
  //      description "Disable dhcp snooping";
  //      type empty;
  //    }
  //    leaf arp-inspection {
  //      description "Enable dynamic ARP inspection";
  //      type empty;
  //    }
  //    leaf ip-source-guard {
  //      description "Enable IP source guard";
  //      type empty;
  //    }
  //    leaf no-dhcpv6-snooping {
  //      description "Disable DHCPv6 snooping";
  //      type empty;
  //    }
  //    leaf neighbor-discovery-inspection {
  //      description "Enable neighbor discovery inspection";
  //      type empty;
  //    }
  //    leaf ipv6-source-guard {
  //      description "Enable IPv6 source guard";
  //      type empty;
  //    }
  //    leaf light-weight-dhcpv6-relay {
  //      description "Enable light weight dhcpv6 relay";
  //      type empty;
  //    }
  //    list group {
  //      key name;
  //      description "Define a DHCP security group for overriding defaults";
  //      uses ds-group;
  //    }
  //    container option-82 {
  //      description "DHCP option-82 processing for snooped packets";
  //      presence "enable option-82";
  //      uses security-option-82-type;
  //    }
  //    container dhcpv6-options {
  //      description "DHCPv6 option processing for snooped packets";
  //      presence "enable dhcpv6-options";
  //      uses security-dhcpv6-options-type;
  //    }
  //    leaf mine-dhcp-client-options {
  //      description "Start storing incoming DHCP client options";
  //      type empty;
  //    }
  //    leaf mine-dhcpv6-client-options {
  //      description "Start storing incoming DHCPv6 client options";
  //      type empty;
  //    }
  //  }
  //  grouping ds-group {
  //    description "DHCP security groups";
  //    leaf name {
  //      description "Group name";
  //      type string {
  //        length "1 .. 64";
  //      }
  //    }
  //    // uses apply-advanced;
  //    container overrides {
  //      description "DHCP override processing";
  //      presence "enable overrides";
  //      uses ds-override-type;
  //    }
  //    list interface {
  //      key name;
  //      description "One or more interfaces";
  //      leaf name {
  //        description "Interface name";
  //        type union {
  //          type jt:interface-name;
  //          type string {
  //            pattern "<.*>|$.*";
  //          }
  //        }
  //      }
  //      // uses apply-advanced;
  //      list static-ip {
  //        key name;
  //        ordered-by user;
  //        description "Static IP address configuration";
  //        uses ip-mac-static;
  //      }
  //      list static-ipv6 {
  //        key name;
  //        ordered-by user;
  //        description "Static IPv6 address configuration";
  //        uses ipv6-mac-static;
  //      }
  //    }
  //  }
  //  grouping ds-override-type {
  //    description "Dynamic ARP Inspection override processing";
  //    // uses apply-advanced;
  //    leaf trusted {
  //      description "Make this trusted group of interfaces";
  //      type empty;
  //    }
  //    leaf untrusted {
  //      description "Make this untrusted group of interfaces";
  //      type empty;
  //    }
  //    leaf no-option82 {
  //      description "Make this group of interfaces not to add option82";
  //      type empty;
  //    }
  //    leaf no-option37 {
  //      description "Make this group of interfaces not to add option37";
  //      type empty;
  //    }
  //    leaf no-option18 {
  //      description "Make this group of interfaces not to add option18";
  //      type empty;
  //    }
  //    leaf no-option16 {
  //      description "Make this group of interfaces not to add option16";
  //      type empty;
  //    }
  //    leaf no-option79 {
  //      description "Make this group of interfaces not to add option79";
  //      type empty;
  //    }
  //    leaf no-dhcpv6-options {
  //      description "Make this group of interfaces not to add any DHCPv6 options";
  //      type empty;
  //    }
  //  }
  //  grouping ip-mac-static {
  //    leaf name {
  //      description "IP address";
  //      type jt:ipaddr;
  //    }
  //    leaf mac {
  //      description "MAC address";
  //      type jt:mac-addr;
  //    }
  //  }
  //  grouping ipv6-mac-static {
  //    leaf name {
  //      description "IP address";
  //      type jt:ipv6addr;
  //    }
  //    leaf mac {
  //      description "MAC address";
  //      type jt:mac-addr;
  //    }
  //  }
  //  grouping jdhcp-vendor-specific-type {
  //    description "Add vendor-specific option processing";
  //    // uses apply-advanced;
  //    leaf host-name {
  //      description "Add router host name";
  //      type empty;
  //    }
  //    leaf location {
  //      description "Add location information expressed as interface name format";
  //      type empty;
  //    }
  //  }
  //  grouping juniper-forwarding-options {
  //    // uses apply-advanced;
  //    list storm-control-profiles {
  //      key name;
  //      description "Storm control profile for this instance";
  //      leaf name {
  //        description "Storm control profile name";
  //        type string {
  //          length "1 .. 127";
  //        }
  //      }
  //      // uses apply-advanced;
  //      container all {
  //        presence "enable all";
  //        description "For all BUM traffic";
  //        // uses apply-advanced;
  //        choice bandwidth {
  //          case case_1 {
  //            leaf bandwidth-percentage {
  //              description "Percentage of link bandwidth";
  //              type union {
  //                type string {
  //                  pattern "<.*>|$.*";
  //                }
  //                type uint32 {
  //                  range "1 .. 100";
  //                }
  //              }
  //            }
  //          }
  //          case case_2 {
  //            leaf bandwidth-level {
  //              description "Link bandwidth";
  //              units "kbps";
  //              type union {
  //                type string {
  //                  pattern "<.*>|$.*";
  //                }
  //                type uint32;
  //              }
  //            }
  //          }
  //        }
  //        leaf burst-size {
  //          description "Burst size";
  //          units "bytes";
  //          type union {
  //            type string {
  //              pattern "<.*>|$.*";
  //            }
  //            type uint32;
  //          }
  //        }
  //        leaf no-broadcast {
  //          description "Disable broadcast storm control";
  //          type empty;
  //        }
  //        leaf no-unknown-unicast {
  //          description "Disable unknown unicast storm control";
  //          type empty;
  //        }
  //        choice no-multicast-choices {
  //          case case_1 {
  //            leaf no-multicast {
  //              description "Disable multicast storm control";
  //              type empty;
  //            }
  //          }
  //          case case_2 {
  //            leaf no-registered-multicast {
  //              description "Disable registered multicast storm control";
  //              type empty;
  //            }
  //          }
  //          case case_3 {
  //            leaf no-unregistered-multicast {
  //              description "Disable unregistered multicast storm control";
  //              type empty;
  //            }
  //          }
  //        }
  //      }
  //      leaf action-shutdown {
  //        description "Disable port for excessive storm control errors";
  //        type empty;
  //      }
  //    }
  //    leaf tunnel-termination {
  //      description "Enable tunnel termination for all interfaces";
  //      type empty;
  //    }
  //    container tunnels {
  //      presence "enable tunnels";
  //      description "Tunnel port profile";
  //      // uses apply-advanced;
  //      container udp {
  //        presence "enable udp";
  //        // uses apply-advanced;
  //        container payload-port-profile {
  //          presence "enable payload-port-profile";
  //          description "Tunnel payload port profile udp, only 1 can exist";
  //          // uses apply-advanced;
  //          leaf profile-name {
  //            description "Payload port profile name";
  //            type string;
  //          }
  //          leaf inet {
  //            description "Tunnel port profile udp inet port";
  //            type union {
  //              type string {
  //                pattern "<.*>|$.*";
  //              }
  //              type uint32 {
  //                range "1 .. 65535";
  //              }
  //            }
  //          }
  //          leaf inet6 {
  //            description "Tunnel port profile udp inet6 port";
  //            type union {
  //              type string {
  //                pattern "<.*>|$.*";
  //              }
  //              type uint32 {
  //                range "1 .. 65535";
  //              }
  //            }
  //          }
  //          leaf mpls {
  //            description "Tunnel port profile udp mpls port";
  //            type union {
  //              type string {
  //                pattern "<.*>|$.*";
  //              }
  //              type uint32 {
  //                range "1 .. 65535";
  //              }
  //            }
  //          }
  //          leaf iso {
  //            description "Tunnel port profile udp iso port";
  //            type union {
  //              type string {
  //                pattern "<.*>|$.*";
  //              }
  //              type uint32 {
  //                range "1 .. 65535";
  //              }
  //            }
  //          }
  //        }
  //      }
  //    }
  //    leaf suppress-interface-leaf-nodes {
  //      description "Enable suppression of exporting leaf nodes under interfaces";
  //      type empty;
  //    }
  //    choice sampling-or-packet-capture {
  //      case case_1 {
  //        container sampling {
  //          description "Statistical traffic sampling options";
  //          uses juniper-sampling-options;
  //        }
  //      }
  //      case case_2 {
  //        container packet-capture {
  //          description "Packet capture options";
  //          uses juniper-packet-capture-options;
  //        }
  //      }
  //    }
  //    list monitoring {
  //      key name;
  //      description "Configure lawful interception of traffic";
  //      uses juniper-monitoring-options;
  //    }
  //    list accounting {
  //      key name;
  //      description "Configure accounting of traffic";
  //      uses juniper-packet-accounting-options;
  //    }
  //    list analyzer {
  //      key name;
  //      description "Analyzer options";
  //      uses smpl-analyzer-type;
  //    }
  //    container port-mirroring {
  //      description "Configure port mirroring of traffic";
  //      uses juniper-port-mirror-options;
  //    }
  //    container pfe-sensor {
  //      description "Enable sensor for pfe resources";
  //      // uses apply-advanced;
  //      container npu-memory {
  //        description "Gather npu memory information";
  //        // uses apply-advanced;
  //        container resource-list {
  //          description "List of resources monitored for pfe sensors";
  //          // uses apply-advanced;
  //          leaf l3-next-hop {
  //            description "Fetch l3 next hop information";
  //            type empty;
  //          }
  //          leaf host-ipv4 {
  //            description "Fetch host ipv4 information";
  //            type empty;
  //          }
  //          leaf host-ipv6 {
  //            description "Fetch host ipv6 information";
  //            type empty;
  //          }
  //          leaf lpm-table-ipv4 {
  //            description "Fetch lpm table ipv4 information";
  //            type empty;
  //          }
  //          leaf lpm-table-ipv6-64 {
  //            description "Fetch lpm table ipv6 information for /64 prefix routes";
  //            type empty;
  //          }
  //          leaf lpm-table-ipv6-128 {
  //            description "Fetch lpm table ipv6 information for /128 prefix routes";
  //            type empty;
  //          }
  //          leaf egress-l3-interface {
  //            description "Fetch egress l3 interface information";
  //            type empty;
  //          }
  //          leaf vport {
  //            description "Fetch vport information";
  //            type empty;
  //          }
  //          leaf mpls-swap-table {
  //            description "Fetch mpls swap table information";
  //            type empty;
  //          }
  //          leaf mpls-ingress-table {
  //            description "Fetch mpls ingress table information";
  //            type empty;
  //          }
  //          leaf tunnel-table {
  //            description "Fetch mpls/Ip tunnel table information";
  //            type empty;
  //          }
  //          leaf vfp {
  //            description "Fetch vlan filter information";
  //            type empty;
  //          }
  //          leaf ifp {
  //            description "Fetch ingress filter information";
  //            type empty;
  //          }
  //          leaf efp {
  //            description "Fetch egress filter information";
  //            type empty;
  //          }
  //          leaf ecmp-group-table {
  //            description "Fetch ecmp group table information";
  //            type empty;
  //          }
  //          leaf ecmp-member-table {
  //            description "Fetch ecmp member table information";
  //            type empty;
  //          }
  //        }
  //      }
  //    }
  //    container evpn-vxlan {
  //      description "EVPN VXLAN configurations";
  //      // uses apply-advanced;
  //      leaf shared-tunnels {
  //        description "Create VTEP tunnels to EVPN PE";
  //        type empty;
  //      }
  //      container host-originated-packets {
  //        presence "enable host-originated-packets";
  //        description "Host Originated Packets";
  //        // uses apply-advanced;
  //        leaf gbp-src-tag {
  //          description "GBP source tag for host originated packets";
  //          type union {
  //            type string {
  //              pattern "<.*>|$.*";
  //            }
  //            type uint32 {
  //              range "1 .. 65535";
  //            }
  //          }
  //        }
  //      }
  //      container reroute-address {
  //        description "Reroute IP address for vxlan encapsulation";
  //        // uses apply-advanced;
  //        choice family {
  //          case case_1 {
  //            container inet {
  //              presence "enable inet";
  //              description "IPv4 address family";
  //              // uses apply-advanced;
  //              leaf address {
  //                description "Reroute address for IPV4 FRR";
  //                type jt:ipv4addr;
  //              }
  //            }
  //          }
  //          case case_2 {
  //            container inet6 {
  //              presence "enable inet6";
  //              description "IPv6 address family";
  //              // uses apply-advanced;
  //              leaf address {
  //                description "Reroute address for IPV6 FRR";
  //                type jt:ipv6addr;
  //              }
  //            }
  //          }
  //        }
  //      }
  //      container gbp {
  //        presence "enable gbp";
  //        description "Group Based Policy options";
  //        // uses apply-advanced;
  //        leaf ingress-enforcement {
  //          description "Enable GBP ingress policy enforcement (restarts PFE if standalone and need reboot for VC)";
  //          type empty;
  //        }
  //        leaf tag-only-policy {
  //          description "Support only src and dst GBP tag match (restarts PFE if standalone and need reboot for VC)";
  //          type empty;
  //        }
  //      }
  //      leaf vxlan-trans-vni-enable {
  //        description "Enable VxLAN Translated VNI in DCI. This will restart PFE";
  //        type empty;
  //      }
  //    }
  //    container multicast-replication {
  //      description "Set mode of multicast replication";
  //      // uses apply-advanced;
  //      leaf ingress {
  //        description "Complete ingress replication";
  //        type empty;
  //      }
  //      leaf local-latency-fairness {
  //        description "Complete parallel replication";
  //        type empty;
  //      }
  //      container evpn {
  //        description "EVPN IRB multicast related options";
  //        // uses apply-advanced;
  //        leaf irb {
  //          type enumeration {
  //            enum "local-only" {
  //              description "Multicast forward in local-only mode";
  //            }
  //            enum "local-remote" {
  //              description "Multicast forward in local-remote mode";
  //            }
  //            enum "oism" {
  //              description "Optimized inter subnet multicast mode";
  //            }
  //            enum "enhanced-oism" {
  //              description "Enhanced OISM to support asymmetric bridge domains";
  //            }
  //          }
  //        }
  //        leaf smet-nexthop-limit {
  //          description "Flood traffic to all egress when count goes above limit";
  //          type union {
  //            type string {
  //              pattern "<.*>|$.*";
  //            }
  //            type uint32 {
  //              range "10000 .. 40000";
  //            }
  //          }
  //        }
  //      }
  //    }
  //    container load-balance {
  //      description "Configure load-balancing attributes on the forwarding path";
  //      // uses apply-advanced;
  //      leaf ecmp-local-bias {
  //        description "Apply locality bias for ecmp nexthops";
  //        type empty;
  //      }
  //      container indexed-load-balance {
  //        presence "enable indexed-load-balance";
  //        description "Use indexed permuted next hop lists for unilist and aggregate next hops";
  //        // uses apply-advanced;
  //      }
  //      container per-flow {
  //        // uses apply-advanced;
  //        leaf hash-seed {
  //          description "Enable per flow seed value on packet forwarding engine";
  //          type empty;
  //        }
  //      }
  //      container per-prefix {
  //        presence "enable per-prefix";
  //        // uses apply-advanced;
  //        leaf hash-seed {
  //          description "Specifies per-router input value for per-prefix load-balancing hash function";
  //          default "0";
  //          type union {
  //            type string {
  //              pattern "<.*>|$.*";
  //            }
  //            type uint16 {
  //              range "0 .. 65534";
  //            }
  //          }
  //        }
  //      }
  //    }
  //    container hash-key {
  //      description "Select data used in the hash key";
  //      uses junos_hash_key;
  //    }
  //    container local-bias {
  //      presence "enable local-bias";
  //      description "Turn on local bias functionality";
  //      // uses apply-advanced;
  //      leaf disable {
  //        description "Disable local-bias";
  //        type empty;
  //      }
  //    }
  //    container enhanced-hash-key {
  //      description "Select data used in the hash key for Enhanced IP Forwarding Engines";
  //      // uses apply-advanced;
  //      container lag-dlb {
  //        presence "enable lag-dlb";
  //        description "Setting dynamic load balancing options for LAG";
  //        // uses apply-advanced;
  //        container ether-type {
  //          presence "enable ether-type";
  //          description "Setting ether type for LAG DLB";
  //          // uses apply-advanced;
  //          leaf ipv4 {
  //            description "Ether type is ipv4";
  //            type empty;
  //          }
  //          leaf ipv6 {
  //            description "Ether type is ipv6";
  //            type empty;
  //          }
  //          leaf mpls {
  //            description "Ether type is mpls";
  //            type empty;
  //          }
  //        }
  //      }
  //      container ecmp-dlb {
  //        description "Set load balancing options for VC-Fabric forwarding";
  //        // uses apply-advanced;
  //        container egress-quantization {
  //          description "Configure egress attributes quantization";
  //          // uses apply-advanced;
  //          leaf min {
  //            description "Min in percentage";
  //            default "50";
  //            type union {
  //              type string {
  //                pattern "<.*>|$.*";
  //              }
  //              type uint32 {
  //                range "1 .. 100";
  //              }
  //            }
  //          }
  //          leaf max {
  //            description "Max in percentage";
  //            default "90";
  //            type union {
  //              type string {
  //                pattern "<.*>|$.*";
  //              }
  //              type uint32 {
  //                range "1 .. 100";
  //              }
  //            }
  //          }
  //          leaf rate-weightage {
  //            description "Weightage between rate versus buffer";
  //            default "0";
  //            type union {
  //              type string {
  //                pattern "<.*>|$.*";
  //              }
  //              type uint32 {
  //                range "0 .. 100";
  //              }
  //            }
  //          }
  //        }
  //        choice mode {
  //          case case_1 {
  //            leaf assigned-flow {
  //              description "Flow-based fixed link assignment";
  //              type empty;
  //            }
  //          }
  //          case case_2 {
  //            container flowlet {
  //              presence "enable flowlet";
  //              description "Inactivity-based flowlet link assignment (default)";
  //              // uses apply-advanced;
  //              leaf inactivity-interval {
  //                description "Minimum inactivity interval in micro-seconds for flowlet detection";
  //                default "256";
  //                type union {
  //                  type string {
  //                    pattern "<.*>|$.*";
  //                  }
  //                  type uint32;
  //                }
  //              }
  //              leaf flowset-table-size {
  //                description "Number of flowset (MacroFlow) entries in DLB hash bucket";
  //                default "256";
  //                type enumeration {
  //                  enum "256" {
  //                    description "Flowset size assigned to DLB group is 256 (default)";
  //                  }
  //                  enum "512" {
  //                    description "Flowset size assigned to DLB group is 512";
  //                  }
  //                  enum "1024" {
  //                    description "Flowset size assigned to DLB group is 1024";
  //                  }
  //                  enum "2048" {
  //                    description "Flowset size assigned to DLB group is 2048";
  //                  }
  //                  enum "4096" {
  //                    description "Flowset size assigned to DLB group is 4096";
  //                  }
  //                  enum "8192" {
  //                    description "Flowset size assigned to DLB group is 8192";
  //                  }
  //                  enum "16384" {
  //                    description "Flowset size assigned to DLB group is 16384";
  //                  }
  //                  enum "32768" {
  //                    description "Flowset size assigned to DLB group is 32768";
  //                  }
  //                }
  //              }
  //              container reassignment {
  //                description "Configure flow reassigment attributes when better quality link is available";
  //                // uses apply-advanced;
  //                leaf prob-threshold {
  //                  description "Probability threshold for flows";
  //                  default "0";
  //                  type union {
  //                    type string {
  //                      pattern "<.*>|$.*";
  //                    }
  //                    type uint32 {
  //                      range "0 .. 255";
  //                    }
  //                  }
  //                }
  //                leaf quality-delta {
  //                  description "Quality difference between members";
  //                  default "0";
  //                  type union {
  //                    type string {
  //                      pattern "<.*>|$.*";
  //                    }
  //                    type uint32 {
  //                      range "0 .. 8";
  //                    }
  //                  }
  //                }
  //              }
  //            }
  //          }
  //          case case_3 {
  //            leaf per-packet {
  //              description "Per-packet optimal spraying";
  //              type empty;
  //            }
  //          }
  //        }
  //        container ether-type {
  //          presence "enable ether-type";
  //          description "Ether type";
  //          // uses apply-advanced;
  //          leaf ipv4 {
  //            description "Set DLB for ipv4";
  //            type empty;
  //          }
  //          leaf ipv6 {
  //            description "Set DLB for ipv6";
  //            type empty;
  //          }
  //          leaf mpls {
  //            description "Set DLB for mpls";
  //            type empty;
  //          }
  //          leaf none {
  //            description "None of the ether type qualify for DLB";
  //            type empty;
  //          }
  //        }
  //        leaf sampling-rate {
  //          description "Set sampled rate for DLB";
  //          units "per second";
  //          type union {
  //            type string {
  //              pattern "<.*>|$.*";
  //            }
  //            type uint32;
  //          }
  //        }
  //      }
  //      container hash-mode {
  //        description "Hashing mode";
  //        // uses apply-advanced;
  //        choice instance {
  //          case case_1 {
  //            leaf layer2-header {
  //              description "Only layer2 header fields are considered for hashing";
  //              type empty;
  //            }
  //          }
  //          case case_2 {
  //            leaf layer2-payload {
  //              description "Only layer2 payload fields are considered for hashing";
  //              type empty;
  //            }
  //          }
  //          case case_3 {
  //            leaf gtp-header-offset {
  //              description "Gtp header first byte offset";
  //              type union {
  //                type uint8;
  //                type string {
  //                  pattern "<.*>|$.*";
  //                }
  //              }
  //            }
  //          }
  //        }
  //      }
  //      container hash-seed {
  //        presence "enable hash-seed";
  //        description "Hash seed";
  //        // uses apply-advanced;
  //        leaf seed-value {
  //          description "Hash seed value";
  //          type union {
  //            type string {
  //              pattern "<.*>|$.*";
  //            }
  //            type uint32 {
  //              range "0 .. 4294967295";
  //            }
  //          }
  //        }
  //      }
  //      container resilient-hash-seed {
  //        presence "enable resilient-hash-seed";
  //        description "Resilient hash seed";
  //        // uses apply-advanced;
  //        leaf resilient-seed-value {
  //          description "Hash seed value for resilient ECMP and LAG";
  //          type union {
  //            type string {
  //              pattern "<.*>|$.*";
  //            }
  //            type uint32 {
  //              range "0 .. 4294967295";
  //            }
  //          }
  //        }
  //      }
  //      container mpls {
  //        description "Configure mpls fields";
  //        // uses apply-advanced;
  //        leaf no-incoming-port {
  //          description "Exclude incoming port from the hash key";
  //          type empty;
  //        }
  //        leaf no-incoming-device {
  //          description "Exclude incoming device from the hash key";
  //          type empty;
  //        }
  //      }
  //      container layer2 {
  //        description "Configure layer2 fields";
  //        // uses apply-advanced;
  //        leaf no-incoming-port {
  //          description "Exclude incoming port from the hash key";
  //          type empty;
  //        }
  //        leaf no-incoming-device {
  //          description "Exclude incoming device from the hash key";
  //          type empty;
  //        }
  //        leaf no-source-mac-address {
  //          description "Exclude source MAC address from the hash key";
  //          type empty;
  //        }
  //        leaf no-destination-mac-address {
  //          description "Exclude destination MAC address from the hash key";
  //          type empty;
  //        }
  //        leaf no-ether-type {
  //          description "Exclude ether type from the hash key";
  //          type empty;
  //        }
  //        leaf vlan-id {
  //          description "Include incoming vlan-id in hash key";
  //          type empty;
  //        }
  //      }
  //      container inet {
  //        description "Configure inet4 fields";
  //        // uses apply-advanced;
  //        leaf no-incoming-port {
  //          description "Exclude incoming port from the hash key";
  //          type empty;
  //        }
  //        leaf no-incoming-device {
  //          description "Exclude incoming device from the hash key";
  //          type empty;
  //        }
  //        leaf no-l4-source-port {
  //          description "Exclude l4 source port from the hash key";
  //          type empty;
  //        }
  //        leaf no-l4-destination-port {
  //          description "Exclude l4 dest port from the hash key";
  //          type empty;
  //        }
  //        leaf no-protocol {
  //          description "Exclude protocol from the hash key";
  //          type empty;
  //        }
  //        leaf no-ipv4-source-address {
  //          description "Exclude IPv4 source address";
  //          type empty;
  //        }
  //        leaf no-ipv4-destination-address {
  //          description "Exclude IPv4 destination address";
  //          type empty;
  //        }
  //        leaf vlan-id {
  //          description "Include incoming vlan-id in hash key";
  //          type empty;
  //        }
  //      }
  //      container inet6 {
  //        description "Configure inet6 fields";
  //        // uses apply-advanced;
  //        leaf no-incoming-port {
  //          description "Exclude incoming port from the hash key";
  //          type empty;
  //        }
  //        leaf no-incoming-device {
  //          description "Exclude incoming device from the hash key";
  //          type empty;
  //        }
  //        leaf no-l4-source-port {
  //          description "Exclude l4 source port from the hash key";
  //          type empty;
  //        }
  //        leaf no-l4-destination-port {
  //          description "Exclude l4 dest port from the hash key";
  //          type empty;
  //        }
  //        leaf no-next-header {
  //          description "Exclude next header from the hash key";
  //          type empty;
  //        }
  //        leaf no-ipv6-source-address {
  //          description "Exclude IPv6 source address";
  //          type empty;
  //        }
  //        leaf no-ipv6-destination-address {
  //          description "Exclude IPv6 destination address";
  //          type empty;
  //        }
  //        leaf vlan-id {
  //          description "Include vlan-id in hash key";
  //          type empty;
  //        }
  //      }
  //      leaf no-mpls {
  //        description "Disable mpls in hash key";
  //        type empty;
  //      }
  //      container gre {
  //        description "Configure for GRE ";
  //        // uses apply-advanced;
  //        leaf key {
  //          description "Include key in hash key";
  //          type empty;
  //        }
  //        leaf protocol {
  //          description "Include protocol in hash key";
  //          type empty;
  //        }
  //      }
  //      container symmetric-hash {
  //        description "Enable symmetric hash for load-balancing";
  //        // uses apply-advanced;
  //        leaf inet {
  //          description "Enable symmetric hash on ipv4 flows";
  //          type empty;
  //        }
  //        leaf inet6 {
  //          description "Enable symmetric hash on ipv6 flows";
  //          type empty;
  //        }
  //      }
  //      container services-loadbalancing {
  //        description "Select key to load balance across service PICs";
  //        // uses apply-advanced;
  //        container family {
  //          description "Protocol family";
  //          container inet {
  //            description "IPv4 protocol family";
  //            // uses apply-advanced;
  //            container layer-3-services {
  //              description "Include Layer 3 (IP) data in the hash key";
  //              // uses apply-advanced;
  //              leaf source-address {
  //                description "Include IP source address in the hash key";
  //                type empty;
  //              }
  //              leaf destination-address {
  //                description "Include IP destination address in the hash key";
  //                type empty;
  //              }
  //              leaf incoming-interface-index {
  //                description "Include incoming interface index in the hash key";
  //                type empty;
  //              }
  //            }
  //          }
  //          container inet6 {
  //            description "IPv6 protocol family";
  //            // uses apply-advanced;
  //            container layer-3-services {
  //              description "Include Layer 3 (IP) data in the hash key";
  //              // uses apply-advanced;
  //              leaf source-address {
  //                description "Include IP source address in the hash key";
  //                type empty;
  //              }
  //              leaf destination-address {
  //                description "Include IP destination address in the hash key";
  //                type empty;
  //              }
  //              leaf incoming-interface-index {
  //                description "Include incoming interface index in the hash key";
  //                type empty;
  //              }
  //              leaf src-prefix-len {
  //                description "Enhanced hash key inet6 source prefix length";
  //                default "127";
  //                units "bits";
  //                type union {
  //                  type string {
  //                    pattern "<.*>|$.*";
  //                  }
  //                  type uint32 {
  //                    range "56 .. 127";
  //                  }
  //                }
  //              }
  //            }
  //          }
  //        }
  //      }
  //      container source-destination-only-loadbalancing {
  //        description "Configure key for source/destination-ip-only load balancing";
  //        // uses apply-advanced;
  //        container family {
  //          description "Protocol family";
  //          container inet {
  //            description "IPv4 protocol family";
  //            // uses apply-advanced;
  //            leaf prefix-length {
  //              description "Source/Destination Only Load-Balancing inet prefix length";
  //              default "32";
  //              units "bits";
  //              type union {
  //                type string {
  //                  pattern "<.*>|$.*";
  //                }
  //                type uint32 {
  //                  range "1 .. 32";
  //                }
  //              }
  //            }
  //          }
  //          container inet6 {
  //            description "IPv6 protocol family";
  //            // uses apply-advanced;
  //            leaf prefix-length {
  //              description "Source/Destination Only Load-Balancing inet6 prefix length";
  //              default "128";
  //              units "bits";
  //              type union {
  //                type string {
  //                  pattern "<.*>|$.*";
  //                }
  //                type uint32 {
  //                  range "1 .. 128";
  //                }
  //              }
  //            }
  //          }
  //        }
  //      }
  //      container family {
  //        description "Protocol family";
  //        container any {
  //          description "Applicable to all protocol families";
  //          // uses apply-advanced;
  //          leaf incoming-interface-index {
  //            description "Include incoming interface index in the hash key";
  //            type empty;
  //          }
  //          leaf no-source-mac {
  //            description "Omit source mac in the hash key";
  //            type empty;
  //          }
  //          leaf no-destination-mac {
  //            description "Omit destination mac in the hash key";
  //            type empty;
  //          }
  //          leaf no-tunnel-payload {
  //            description "Omit tunnel payload in the hash key";
  //            type empty;
  //          }
  //        }
  //        container inet {
  //          description "IPv4 protocol family";
  //          // uses apply-advanced;
  //          leaf incoming-interface-index {
  //            description "Include incoming interface index in the hash key";
  //            type empty;
  //          }
  //          leaf no-destination-port {
  //            description "Omit IP destination port in the hash key";
  //            type empty;
  //          }
  //          leaf no-source-port {
  //            description "Omit IP source port in the hash key";
  //            type empty;
  //          }
  //          leaf type-of-service {
  //            description "Include TOS byte in the hash key";
  //            type empty;
  //          }
  //          leaf gtp-tunnel-endpoint-identifier {
  //            description "Include TEID in the hash key for GTP-U packets";
  //            type empty;
  //          }
  //          leaf l2tp-tunnel-session-identifier {
  //            description "Include TID SID in the hash key for L2TP packets";
  //            type empty;
  //          }
  //          leaf session-id {
  //            description "Include session ID in the enhanced hash key";
  //            type empty;
  //          }
  //        }
  //        container inet6 {
  //          description "IPv6 protocol family";
  //          // uses apply-advanced;
  //          leaf incoming-interface-index {
  //            description "Include incoming interface index in the hash key";
  //            type empty;
  //          }
  //          leaf traffic-class {
  //            description "Include Traffic Class byte in the hash key";
  //            type empty;
  //          }
  //          leaf no-destination-port {
  //            description "Omit IP destination port in the hash key";
  //            type empty;
  //          }
  //          leaf no-source-port {
  //            description "Omit IP source port in the hash key";
  //            type empty;
  //          }
  //          leaf gtp-tunnel-endpoint-identifier {
  //            description "Include TEID in the hash key for GTP-U packets";
  //            type empty;
  //          }
  //          leaf session-id {
  //            description "Include session ID in the enhanced hash key";
  //            type empty;
  //          }
  //          leaf no-flow-label {
  //            description "Omit Flow label in the hash key";
  //            type empty;
  //          }
  //          leaf type-of-service {
  //            description "Include TOS byte in the hash key";
  //            status deprecated;
  //            type empty;
  //          }
  //        }
  //        container mpls {
  //          description "MPLS protocol family";
  //          // uses apply-advanced;
  //          leaf label-1-exp {
  //            description "Include EXP of first MPLS label from the hash key";
  //            type empty;
  //          }
  //          leaf incoming-interface-index {
  //            description "Include incoming interface index in the hash key";
  //            type empty;
  //          }
  //          choice pseudowire_option {
  //            case case_1 {
  //              leaf no-ether-pseudowire {
  //                description "Omit IP payload over ethernet PW from the hash-key";
  //                type empty;
  //              }
  //            }
  //            case case_2 {
  //              container ether-pseudowire {
  //                description "Load-balance ethernet over ethernet PW";
  //                leaf zero-control-word {
  //                  description "Parse zero control word in packet header";
  //                  type empty;
  //                }
  //              }
  //            }
  //          }
  //          leaf no-labels {
  //            description "Exclude all MPLS labels from hash key";
  //            type empty;
  //          }
  //          leaf no-payload {
  //            description "Omit MPLS payload data from the hash key";
  //            type empty;
  //          }
  //        }
  //        container multiservice {
  //          description "Multiservice protocol (bridged/CCC/VPLS) family";
  //          // uses apply-advanced;
  //          leaf incoming-interface-index {
  //            description "Include incoming interface index in hash key";
  //            type empty;
  //          }
  //          leaf outer-priority {
  //            description "Include Outer 802.1 Priority bits in the hash key";
  //            type empty;
  //          }
  //          leaf no-payload {
  //            description "Omit payload data from the hash key";
  //            type empty;
  //          }
  //          leaf no-mac-addresses {
  //            description "Omit source and destination MAC addresses from the hash key";
  //            type empty;
  //          }
  //        }
  //      }
  //      container profile1 {
  //        description "Hashkey protocol profile-1";
  //        // uses apply-advanced;
  //        leaf hash-seed {
  //          description "Hash seed value";
  //          type union {
  //            type string {
  //              pattern "<.*>|$.*";
  //            }
  //            type uint32 {
  //              range "0 .. 4294967295";
  //            }
  //          }
  //        }
  //        leaf no-in-interface {
  //          description "Omit inner interface in the hash key";
  //          type empty;
  //        }
  //        leaf no-in-flexbytes {
  //          description "Omit inner flex bytes in the hash key";
  //          type empty;
  //        }
  //        leaf no-flexbytes {
  //          description "Omit flex bytes in the hash key";
  //          type empty;
  //        }
  //        leaf no-in-layer3-pri {
  //          description "Omit inner L3 priority in the hash key";
  //          type empty;
  //        }
  //        leaf no-in-layer3-proto {
  //          description "Omit inner L3 protocol in the hash key";
  //          type empty;
  //        }
  //        leaf no-layer3-pri {
  //          description "Omit L3 priority fields in the hash key";
  //          type empty;
  //        }
  //        leaf no-layer3-proto {
  //          description "Omit L3 protocol in the hash key";
  //          type empty;
  //        }
  //        leaf no-interface {
  //          description "Omit interface in the hash key";
  //          type empty;
  //        }
  //        leaf no-layer2 {
  //          description "Omit L2 attributes in the hash key";
  //          type empty;
  //        }
  //        leaf no-layer3-source-address {
  //          description "Omit L3 source address in the hash key";
  //          type empty;
  //        }
  //        leaf no-layer3-destination-address {
  //          description "Omit L3 destination address in the hash key";
  //          type empty;
  //        }
  //        leaf no-layer4-source-port {
  //          description "Omit L4 source port in the hash key";
  //          type empty;
  //        }
  //        leaf no-layer4-destination-port {
  //          description "Omit L4 destination port in the hash key";
  //          type empty;
  //        }
  //        leaf no-tunnel {
  //          description "Omit tunnel in the hash key";
  //          type empty;
  //        }
  //        leaf no-in-layer2 {
  //          description "Omit inner L2 attributes in the hash key";
  //          type empty;
  //        }
  //        leaf no-in-layer3 {
  //          description "Omit inner L3 attributes in the hash key";
  //          type empty;
  //        }
  //        leaf no-in-layer4 {
  //          description "Omit inner L4 attributes in the hash key";
  //          type empty;
  //        }
  //        leaf no-in-tunnel {
  //          description "Omit inner tunnel fields in the hash key";
  //          type empty;
  //        }
  //      }
  //      container profile2 {
  //        description "Hashkey protocol profile-2";
  //        // uses apply-advanced;
  //        leaf hash-seed {
  //          description "Hash seed value";
  //          type union {
  //            type string {
  //              pattern "<.*>|$.*";
  //            }
  //            type uint32 {
  //              range "0 .. 4294967295";
  //            }
  //          }
  //        }
  //        leaf no-in-interface {
  //          description "Omit inner interface in the hash key";
  //          type empty;
  //        }
  //        leaf no-in-flexbytes {
  //          description "Omit inner flex bytes in the hash key";
  //          type empty;
  //        }
  //        leaf no-flexbytes {
  //          description "Omit flex bytes in the hash key";
  //          type empty;
  //        }
  //        leaf no-in-layer3-pri {
  //          description "Omit inner L3 priority in the hash key";
  //          type empty;
  //        }
  //        leaf no-in-layer3-proto {
  //          description "Omit inner L3 protocol in the hash key";
  //          type empty;
  //        }
  //        leaf no-layer3-pri {
  //          description "Omit L3 priority fields in the hash key";
  //          type empty;
  //        }
  //        leaf no-layer3-proto {
  //          description "Omit L3 protocol in the hash key";
  //          type empty;
  //        }
  //        leaf no-interface {
  //          description "Omit interface in the hash key";
  //          type empty;
  //        }
  //        leaf no-layer2 {
  //          description "Omit L2 attributes in the hash key";
  //          type empty;
  //        }
  //        leaf no-layer3-source-address {
  //          description "Omit L3 source address in the hash key";
  //          type empty;
  //        }
  //        leaf no-layer3-destination-address {
  //          description "Omit L3 destination address in the hash key";
  //          type empty;
  //        }
  //        leaf no-layer4-source-port {
  //          description "Omit L4 source port in the hash key";
  //          type empty;
  //        }
  //        leaf no-layer4-destination-port {
  //          description "Omit L4 destination port in the hash key";
  //          type empty;
  //        }
  //        leaf no-tunnel {
  //          description "Omit tunnel in the hash key";
  //          type empty;
  //        }
  //        leaf no-in-layer2 {
  //          description "Omit inner L2 attributes in the hash key";
  //          type empty;
  //        }
  //        leaf no-in-layer3 {
  //          description "Omit inner L3 attributes in the hash key";
  //          type empty;
  //        }
  //        leaf no-in-layer4 {
  //          description "Omit inner L4 attributes in the hash key";
  //          type empty;
  //        }
  //        leaf no-in-tunnel {
  //          description "Omit inner tunnel fields in the hash key";
  //          type empty;
  //        }
  //      }
  //      container hash-function {
  //        description "Configure hash functions";
  //        // uses apply-advanced;
  //        choice instance {
  //          case case_1 {
  //            leaf CRC16-CCITT {
  //              description "16-bit CRC16 using CCITT polynomial";
  //              type empty;
  //            }
  //          }
  //          case case_2 {
  //            leaf CRC16 {
  //              description "16-bit CRC16 calculated using the BISYNC polynomial";
  //              type empty;
  //            }
  //          }
  //          case case_3 {
  //            leaf CRC16XOR1 {
  //              description "Upper 8 bits BISYNC CRC16 and 8 bit XOR1";
  //              type empty;
  //            }
  //          }
  //          case case_4 {
  //            leaf CRC16XOR2 {
  //              description "Upper 8 bit BISYNC CRC16 and 8 bit XOR2";
  //              type empty;
  //            }
  //          }
  //          case case_5 {
  //            leaf CRC16XOR4 {
  //              description "Upper 8 bit BISYNC CRC16 and 8 bit XOR4";
  //              type empty;
  //            }
  //          }
  //          case case_6 {
  //            leaf CRC16XOR8 {
  //              description "Upper 8 bit BISYNC CRC16 and 8 bit XOR8";
  //              type empty;
  //            }
  //          }
  //          case case_7 {
  //            leaf CRC32HI {
  //              description "16 LSBs of computed CRC32";
  //              type empty;
  //            }
  //          }
  //          case case_8 {
  //            leaf CRC32LO {
  //              description "16 MSBs of computed CRC32";
  //              type empty;
  //            }
  //          }
  //          case case_9 {
  //          }
  //          case case_10 {
  //          }
  //          case case_11 {
  //          }
  //          case case_12 {
  //          }
  //        }
  //      }
  //      container vxlan {
  //        description "Vxlan traffic";
  //        // uses apply-advanced;
  //        leaf no-inner-payload {
  //          description "To enable load-balancing on Vxlan traffic based on outer IP/UDP header";
  //          type empty;
  //        }
  //      }
  //      list conditional-match {
  //        key name;
  //        ordered-by user;
  //        description "Configures a conditional match";
  //        leaf name {
  //          description "Name identifier";
  //          type string;
  //        }
  //        // uses apply-advanced;
  //        container offset1 {
  //          presence "enable offset1";
  //          description "Configure offset 1";
  //          // uses apply-advanced;
  //          leaf base-offset1 {
  //            description "Configure base-offset";
  //            type enumeration {
  //              enum "start-of-L2Header" {
  //                description "Offset will be extracted from start of L2 header";
  //              }
  //              enum "start-of-L3-OuterHeader" {
  //                description "Offset will be extracted from start of outer L3 header";
  //              }
  //              enum "start-of-L3-InnerHeader" {
  //                description "Offset will be extracted from start of inner L3 header";
  //              }
  //              enum "start-of-L4-Header" {
  //                description "Offset will be extracted from start of L4 header";
  //              }
  //            }
  //          }
  //          leaf offset1-value {
  //            description "Offset of the data to be extracted from the base offset. Only even number";
  //            type union {
  //              type string {
  //                pattern "<.*>|$.*";
  //              }
  //              type uint8 {
  //                range "0 .. 126";
  //              }
  //            }
  //          }
  //          leaf matchdata1 {
  //            description "Data to be matched";
  //            type string {
  //              length 4;
  //            }
  //          }
  //          leaf matchdata1-mask {
  //            description "Matchdata mask";
  //            type string {
  //              length 4;
  //            }
  //          }
  //        }
  //        container offset2 {
  //          presence "enable offset2";
  //          description "Configure offset 2";
  //          // uses apply-advanced;
  //          leaf base-offset2 {
  //            description "Configure base-offset";
  //            type enumeration {
  //              enum "start-of-L2Header" {
  //                description "Offset will be extracted from start of L2 header";
  //              }
  //              enum "start-of-L3-OuterHeader" {
  //                description "Offset will be extracted from start of outer L3 header";
  //              }
  //              enum "start-of-L3-InnerHeader" {
  //                description "Offset will be extracted from start of inner L3 header";
  //              }
  //              enum "start-of-L4-Header" {
  //                description "Offset will be extracted from start of L4 header";
  //              }
  //            }
  //          }
  //          leaf offset2-value {
  //            description "Offset of the data to be extracted from the base offset. Only even number";
  //            type union {
  //              type string {
  //                pattern "<.*>|$.*";
  //              }
  //              type uint8 {
  //                range "0 .. 126";
  //              }
  //            }
  //          }
  //          leaf matchdata2 {
  //            description "Data to be matched";
  //            type string {
  //              length 4;
  //            }
  //          }
  //          leaf matchdata2-mask {
  //            description "Matchdata mask";
  //            type string {
  //              length 4;
  //            }
  //          }
  //        }
  //        container offset3 {
  //          presence "enable offset3";
  //          description "Configure offset 3";
  //          // uses apply-advanced;
  //          leaf base-offset3 {
  //            description "Configure base-offset";
  //            type enumeration {
  //              enum "start-of-L2Header" {
  //                description "Offset will be extracted from start of L2 header";
  //              }
  //              enum "start-of-L3-OuterHeader" {
  //                description "Offset will be extracted from start of outer L3 header";
  //              }
  //              enum "start-of-L3-InnerHeader" {
  //                description "Offset will be extracted from start of inner L3 header";
  //              }
  //              enum "start-of-L4-Header" {
  //                description "Offset will be extracted from start of L4 header";
  //              }
  //            }
  //          }
  //          leaf offset3-value {
  //            description "Offset of the data to be extracted from the base offset. Only even number";
  //            type union {
  //              type string {
  //                pattern "<.*>|$.*";
  //              }
  //              type uint8 {
  //                range "0 .. 126";
  //              }
  //            }
  //          }
  //          leaf matchdata3 {
  //            description "Data to be matched";
  //            type string {
  //              length 4;
  //            }
  //          }
  //          leaf matchdata3-mask {
  //            description "Matchdata mask";
  //            type string {
  //              length 4;
  //            }
  //          }
  //        }
  //        container offset4 {
  //          presence "enable offset4";
  //          description "Configure offset 4";
  //          // uses apply-advanced;
  //          leaf base-offset4 {
  //            description "Configure base-offset";
  //            type enumeration {
  //              enum "start-of-L2Header" {
  //                description "Offset will be extracted from start of L2 header";
  //              }
  //              enum "start-of-L3-OuterHeader" {
  //                description "Offset will be extracted from start of outer L3 header";
  //              }
  //              enum "start-of-L3-InnerHeader" {
  //                description "Offset will be extracted from start of inner L3 header";
  //              }
  //              enum "start-of-L4-Header" {
  //                description "Offset will be extracted from start of L4 header";
  //              }
  //            }
  //          }
  //          leaf offset4-value {
  //            description "Offset of the data to be extracted from the base offset. Only even number";
  //            type union {
  //              type string {
  //                pattern "<.*>|$.*";
  //              }
  //              type uint8 {
  //                range "0 .. 126";
  //              }
  //            }
  //          }
  //          leaf matchdata4 {
  //            description "Data to be matched";
  //            type string {
  //              length 4;
  //            }
  //          }
  //          leaf matchdata4-mask {
  //            description "Matchdata mask";
  //            type string {
  //              length 4;
  //            }
  //          }
  //        }
  //      }
  //      list flex-hashing {
  //        key name;
  //        ordered-by user;
  //        description "Set flex hashing";
  //        leaf name {
  //          description "Name identifier";
  //          type string;
  //        }
  //        // uses apply-advanced;
  //        container ethtype {
  //          presence "enable ethtype";
  //          description "Configure ether-type of packet";
  //          // uses apply-advanced;
  //          container inet {
  //            description "Enable flex-hashing on ipv4";
  //            // uses apply-advanced;
  //            leaf interface {
  //              description "Incoming interface name. This is optional parameter";
  //              type union {
  //                type jt:interface-name;
  //                type string {
  //                  pattern "<.*>|$.*";
  //                }
  //              }
  //            }
  //            leaf conditional-match {
  //              description "Conditional match to be matched in the packet";
  //              type string;
  //            }
  //            container hash-offset {
  //              description "Configure the offsets for hashing";
  //              // uses apply-advanced;
  //              container offset1 {
  //                presence "enable offset1";
  //                description "Configure offset 1 value";
  //                // uses apply-advanced;
  //                leaf base-offset1 {
  //                  description "Configure base-offset";
  //                  type enumeration {
  //                    enum "start-of-L2Header" {
  //                      description "Offset will be extracted from start of L2 header";
  //                    }
  //                    enum "start-of-L3-OuterHeader" {
  //                      description "Offset will be extracted from start of outer L3 header";
  //                    }
  //                    enum "start-of-L3-InnerHeader" {
  //                      description "Offset will be extracted from start of inner L3 header";
  //                    }
  //                    enum "start-of-L4-Header" {
  //                      description "Offset will be extracted from start of L4 header";
  //                    }
  //                  }
  //                }
  //                leaf offset1-value {
  //                  description "Offset of the data to be extracted from the base offset. Only even number";
  //                  type union {
  //                    type string {
  //                      pattern "<.*>|$.*";
  //                    }
  //                    type uint8 {
  //                      range "0 .. 126";
  //                    }
  //                  }
  //                }
  //                leaf offset1-mask {
  //                  description "Mask for the hash data extracted. 2 byte mask";
  //                  type string {
  //                    length 4;
  //                  }
  //                }
  //                container offset2 {
  //                  presence "enable offset2";
  //                  description "Configure offset 2 value";
  //                  // uses apply-advanced;
  //                  leaf base-offset2 {
  //                    description "Configure base-offset";
  //                    type enumeration {
  //                      enum "start-of-L2Header" {
  //                        description "Offset will be extracted from start of L2 header";
  //                      }
  //                      enum "start-of-L3-OuterHeader" {
  //                        description "Offset will be extracted from start of outer L3 header";
  //                      }
  //                      enum "start-of-L3-InnerHeader" {
  //                        description "Offset will be extracted from start of inner L3 header";
  //                      }
  //                      enum "start-of-L4-Header" {
  //                        description "Offset will be extracted from start of L4 header";
  //                      }
  //                    }
  //                  }
  //                  leaf offset2-value {
  //                    description "Offset of the data to be extracted from the base offset. Only even number";
  //                    type union {
  //                      type string {
  //                        pattern "<.*>|$.*";
  //                      }
  //                      type uint8 {
  //                        range "0 .. 126";
  //                      }
  //                    }
  //                  }
  //                  leaf offset2-mask {
  //                    description "Mask for the hash data extracted. 2 byte mask";
  //                    type string {
  //                      length 4;
  //                    }
  //                  }
  //                }
  //              }
  //            }
  //          }
  //          container inet6 {
  //            description "Enable flex-hashing on ipv6";
  //            // uses apply-advanced;
  //            leaf interface {
  //              description "Incoming interface name. This is optional parameter";
  //              type union {
  //                type jt:interface-name;
  //                type string {
  //                  pattern "<.*>|$.*";
  //                }
  //              }
  //            }
  //            leaf conditional-match {
  //              description "Conditional match to be matched in the packet";
  //              type string;
  //            }
  //            container hash-offset {
  //              description "Configure the offsets for hashing";
  //              // uses apply-advanced;
  //              container offset1 {
  //                presence "enable offset1";
  //                description "Configure offset 1 value";
  //                // uses apply-advanced;
  //                leaf base-offset1 {
  //                  description "Configure base-offset";
  //                  type enumeration {
  //                    enum "start-of-L2Header" {
  //                      description "Offset will be extracted from start of L2 header";
  //                    }
  //                    enum "start-of-L3-OuterHeader" {
  //                      description "Offset will be extracted from start of outer L3 header";
  //                    }
  //                    enum "start-of-L3-InnerHeader" {
  //                      description "Offset will be extracted from start of inner L3 header";
  //                    }
  //                    enum "start-of-L4-Header" {
  //                      description "Offset will be extracted from start of L4 header";
  //                    }
  //                  }
  //                }
  //                leaf offset1-value {
  //                  description "Offset of the data to be extracted from the base offset. Only even number";
  //                  type union {
  //                    type string {
  //                      pattern "<.*>|$.*";
  //                    }
  //                    type uint8 {
  //                      range "0 .. 126";
  //                    }
  //                  }
  //                }
  //                leaf offset1-mask {
  //                  description "Mask for the hash data extracted. 2 byte mask";
  //                  type string {
  //                    length 4;
  //                  }
  //                }
  //                container offset2 {
  //                  presence "enable offset2";
  //                  description "Configure offset 2 value";
  //                  // uses apply-advanced;
  //                  leaf base-offset2 {
  //                    description "Configure base-offset";
  //                    type enumeration {
  //                      enum "start-of-L2Header" {
  //                        description "Offset will be extracted from start of L2 header";
  //                      }
  //                      enum "start-of-L3-OuterHeader" {
  //                        description "Offset will be extracted from start of outer L3 header";
  //                      }
  //                      enum "start-of-L3-InnerHeader" {
  //                        description "Offset will be extracted from start of inner L3 header";
  //                      }
  //                      enum "start-of-L4-Header" {
  //                        description "Offset will be extracted from start of L4 header";
  //                      }
  //                    }
  //                  }
  //                  leaf offset2-value {
  //                    description "Offset of the data to be extracted from the base offset. Only even number";
  //                    type union {
  //                      type string {
  //                        pattern "<.*>|$.*";
  //                      }
  //                      type uint8 {
  //                        range "0 .. 126";
  //                      }
  //                    }
  //                  }
  //                  leaf offset2-mask {
  //                    description "Mask for the hash data extracted. 2 byte mask";
  //                    type string {
  //                      length 4;
  //                    }
  //                  }
  //                }
  //              }
  //            }
  //          }
  //          container mpls {
  //            description "Configure number of MPLS labels";
  //            // uses apply-advanced;
  //            leaf num-labels {
  //              description "Configure number of MPLS labels";
  //              type union {
  //                type string {
  //                  pattern "<.*>|$.*";
  //                }
  //                type uint8 {
  //                  range "1 .. 5";
  //                }
  //              }
  //            }
  //            leaf interface {
  //              description "Incoming interface name. This is optional parameter";
  //              type union {
  //                type jt:interface-name;
  //                type string {
  //                  pattern "<.*>|$.*";
  //                }
  //              }
  //            }
  //            leaf conditional-match {
  //              description "Conditional match to be matched in the packet";
  //              type string;
  //            }
  //            container hash-offset {
  //              description "Configure the offsets for hashing";
  //              // uses apply-advanced;
  //              container offset1 {
  //                presence "enable offset1";
  //                description "Configure offset 1 value";
  //                // uses apply-advanced;
  //                leaf base-offset1 {
  //                  description "Configure base-offset";
  //                  type enumeration {
  //                    enum "start-of-L2Header" {
  //                      description "Offset will be extracted from start of L2 header";
  //                    }
  //                    enum "start-of-L3-OuterHeader" {
  //                      description "Offset will be extracted from start of outer L3 header";
  //                    }
  //                    enum "start-of-L3-InnerHeader" {
  //                      description "Offset will be extracted from start of inner L3 header";
  //                    }
  //                    enum "start-of-L4-Header" {
  //                      description "Offset will be extracted from start of L4 header";
  //                    }
  //                  }
  //                }
  //                leaf offset1-value {
  //                  description "Offset of the data to be extracted from the base offset. Only even number";
  //                  type union {
  //                    type string {
  //                      pattern "<.*>|$.*";
  //                    }
  //                    type uint8 {
  //                      range "0 .. 126";
  //                    }
  //                  }
  //                }
  //                leaf offset1-mask {
  //                  description "Mask for the hash data extracted. 2 byte mask";
  //                  type string {
  //                    length 4;
  //                  }
  //                }
  //                container offset2 {
  //                  presence "enable offset2";
  //                  description "Configure offset 2 value";
  //                  // uses apply-advanced;
  //                  leaf base-offset2 {
  //                    description "Configure base-offset";
  //                    type enumeration {
  //                      enum "start-of-L2Header" {
  //                        description "Offset will be extracted from start of L2 header";
  //                      }
  //                      enum "start-of-L3-OuterHeader" {
  //                        description "Offset will be extracted from start of outer L3 header";
  //                      }
  //                      enum "start-of-L3-InnerHeader" {
  //                        description "Offset will be extracted from start of inner L3 header";
  //                      }
  //                      enum "start-of-L4-Header" {
  //                        description "Offset will be extracted from start of L4 header";
  //                      }
  //                    }
  //                  }
  //                  leaf offset2-value {
  //                    description "Offset of the data to be extracted from the base offset. Only even number";
  //                    type union {
  //                      type string {
  //                        pattern "<.*>|$.*";
  //                      }
  //                      type uint8 {
  //                        range "0 .. 126";
  //                      }
  //                    }
  //                  }
  //                  leaf offset2-mask {
  //                    description "Mask for the hash data extracted. 2 byte mask";
  //                    type string {
  //                      length 4;
  //                    }
  //                  }
  //                }
  //              }
  //            }
  //          }
  //        }
  //      }
  //      leaf symmetric {
  //        description "Enable symmetric load-balancing";
  //        type empty;
  //      }
  //    }
  //    container next-hop {
  //      description "Next hop throttle";
  //      // uses apply-advanced;
  //    }
  //    container sflow {
  //      description "Sflow related";
  //      // uses apply-advanced;
  //      container egress-multicast {
  //        description "Sflow for egress multicast";
  //        // uses apply-advanced;
  //        leaf max-replication-rate {
  //          description "To configure max replication rate (0 to 2K pps)";
  //          type union {
  //            type string {
  //              pattern "<.*>|$.*";
  //            }
  //            type uint32 {
  //              range "0 .. 2000";
  //            }
  //          }
  //        }
  //      }
  //      container flow-sample {
  //        description "Flow sample input";
  //        // uses apply-advanced;
  //      }
  //    }
  //    container multicast {
  //      description "Multicast resolve and mismatch rate";
  //      // uses apply-advanced;
  //      leaf resolve-rate {
  //        description "Multicast resolve rate";
  //        units "per second";
  //        type union {
  //          type string {
  //            pattern "<.*>|$.*";
  //          }
  //          type uint32 {
  //            range "100 .. 1000";
  //          }
  //        }
  //      }
  //      leaf mismatch-rate {
  //        description "Multicast interface mismatch rate";
  //        units "per second";
  //        type union {
  //          type string {
  //            pattern "<.*>|$.*";
  //          }
  //          type uint32 {
  //            range "50 .. 1000";
  //          }
  //        }
  //      }
  //      container policer {
  //        presence "enable policer";
  //        // uses apply-advanced;
  //        leaf bandwidth-limit {
  //          description "Bandwidth limit";
  //          units "bits per second";
  //          type string;
  //        }
  //        leaf burst-size-limit {
  //          description "Burst size limit";
  //          units "bytes";
  //          type string;
  //        }
  //      }
  //    }
  //    container packet-capture-telemetry {
  //      description "Packet capture telemetry options";
  //      // uses apply-advanced;
  //      container egress {
  //        description "Egress options";
  //        uses packet-capture-egress-intf-type;
  //      }
  //    }
  //    container rpf-loose-mode-discard {
  //      description "Configure rpf loose mode behavior";
  //      // uses apply-advanced;
  //      container family {
  //        description "Protocol family";
  //        // uses apply-advanced;
  //        leaf inet {
  //          description "Configure rpf loose mode behavior for IPv4";
  //          type empty;
  //        }
  //        leaf inet6 {
  //          description "Configure rpf loose mode behavior for IPv6";
  //          type empty;
  //        }
  //      }
  //    }
  //    leaf inband-telemetry {
  //      description "Enable Datapath Inband Telemetry";
  //      type empty;
  //    }
  //    leaf bier {
  //      description "Enable BIER protocol on all quipped FPCs";
  //      type empty;
  //    }
  //    container inband-telemetry-metaoptions {
  //      description "Configure Inband Telemetry meta data";
  //      // uses apply-advanced;
  //      leaf node-id {
  //        description "Inband Telemetry node id";
  //        type union {
  //          type uint32;
  //          type string {
  //            pattern "<.*>|$.*";
  //          }
  //        }
  //      }
  //      leaf ts-rs {
  //        description "Timestamp right shift value";
  //        type union {
  //          type string {
  //            pattern "<.*>|$.*";
  //          }
  //          type uint32 {
  //            range "0 .. 30";
  //          }
  //        }
  //      }
  //    }
  //    leaf l2circuit-control-passthrough {
  //      description "Configure passthrough for control protocol packets on L2 Circuit";
  //      type empty;
  //    }
  //    container explicit-null-cos {
  //      presence "enable explicit-null-cos";
  //      description "Configure to use MPLS explicit null exp for COS classification";
  //      // uses apply-advanced;
  //      leaf inet {
  //        description "Include family inet";
  //        type empty;
  //      }
  //      leaf inet6 {
  //        description "Include family inet6";
  //        type empty;
  //      }
  //    }
  //    container helpers {
  //      description "Port forwarding configuration";
  //      // uses apply-advanced;
  //      container traceoptions {
  //        description "Trace options for helper";
  //        // uses apply-advanced;
  //        leaf no-remote-trace {
  //          description "Disable remote tracing";
  //          type empty;
  //        }
  //        container file {
  //          description "Trace file information";
  //          leaf filename {
  //            description "Name of file in which to write trace information";
  //            type string {
  //              length "1 .. 1024";
  //            }
  //          }
  //          leaf size {
  //            description "Maximum trace file size";
  //            type string;
  //          }
  //          leaf files {
  //            description "Maximum number of trace files";
  //            default "3";
  //            type union {
  //              type string {
  //                pattern "<.*>|$.*";
  //              }
  //              type uint32 {
  //                range "2 .. 1000";
  //              }
  //            }
  //          }
  //          choice world-readable-choice {
  //            leaf world-readable {
  //              description "Allow any user to read the log file";
  //              type empty;
  //            }
  //            leaf no-world-readable {
  //              description "Don't allow any user to read the log file";
  //              type empty;
  //            }
  //          }
  //          leaf match {
  //            description "Regular expression for lines to be logged";
  //            type jt:regular-expression;
  //          }
  //        }
  //        leaf level {
  //          description "Level of debugging output";
  //          default "error";
  //          type enumeration {
  //            enum "error" {
  //              description "Match error conditions";
  //            }
  //            enum "warning" {
  //              description "Match warning messages";
  //            }
  //            enum "notice" {
  //              description "Match conditions that should be handled specially";
  //            }
  //            enum "info" {
  //              description "Match informational messages";
  //            }
  //            enum "verbose" {
  //              description "Match verbose messages";
  //            }
  //            enum "all" {
  //              description "Match all levels";
  //            }
  //          }
  //        }
  //        list flag {
  //          key name;
  //          ordered-by user;
  //          description "Area of UDP forwarding helper process on which to enable debugging output";
  //          leaf name {
  //            type enumeration {
  //              enum "trace" {
  //                description "Trace tracing code";
  //              }
  //              enum "address" {
  //                description "Trace address management code";
  //              }
  //              enum "main" {
  //                description "Trace main loop code";
  //              }
  //              enum "config" {
  //                description "Trace configuration code";
  //              }
  //              enum "ifdb" {
  //                description "Trace interface database code";
  //              }
  //              enum "io" {
  //                description "Trace I/O code";
  //              }
  //              enum "rtsock" {
  //                description "Trace routing socket code";
  //              }
  //              enum "ui" {
  //                description "Trace user interface code";
  //              }
  //              enum "util" {
  //                description "Trace miscellaneous utility code";
  //              }
  //              enum "gencfg" {
  //                description "Trace fud gencfg message";
  //              }
  //              enum "domain" {
  //                description "Trace DNS service-specific code";
  //              }
  //              enum "tftp" {
  //                description "Trace TFTP service-specific code";
  //              }
  //              enum "bootp" {
  //                description "Trace BOOTP/DHCP service-specific code";
  //              }
  //              enum "port" {
  //                description "Trace arbitrary protocol code";
  //              }
  //              enum "if-rtsdb" {
  //                description "Trace interface hierarchy rtsdb";
  //              }
  //              enum "all" {
  //                description "Trace all areas of code";
  //              }
  //            }
  //          }
  //        }
  //      }
  //      container rtsdb-client-traceoptions {
  //        presence "enable rtsdb-client-traceoptions";
  //        description "SHM rtsock database client library trace options";
  //        status deprecated;
  //        // uses apply-advanced;
  //        container if-rtsdb {
  //          presence "enable if-rtsdb";
  //          description "Trace interface hierarchy rtsdb";
  //          // uses apply-advanced;
  //          list flag {
  //            key name;
  //            ordered-by user;
  //            description "Tracing parameters";
  //            leaf name {
  //              type enumeration {
  //                enum "init" {
  //                  description "Trace initialization";
  //                }
  //                enum "routing-socket" {
  //                  description "Trace routing socket messages";
  //                }
  //                enum "map" {
  //                  description "Trace shared memory mapping";
  //                }
  //                enum "all" {
  //                  description "Trace all";
  //                }
  //              }
  //            }
  //            leaf disable {
  //              description "Disable this trace flag";
  //              type empty;
  //            }
  //          }
  //        }
  //      }
  //      container domain {
  //        description "Incoming DNS request forwarding configuration";
  //        // uses apply-advanced;
  //        leaf description {
  //          description "Text description of server";
  //          type string;
  //        }
  //        container server {
  //          description "Server information";
  //          leaf address {
  //            description "Name or address of server to which to forward";
  //            type jt:ipv4addr;
  //          }
  //          choice instance {
  //            case case_1 {
  //              container logical-system {
  //                description "Logical system of server to which to forward";
  //                leaf logical-system-name {
  //                  description "Name of logical system";
  //                  type string {
  //                  }
  //                }
  //                leaf routing-instance {
  //                  description "Routing instance of server to which to forward";
  //                  type union {
  //                    type string {
  //                      pattern "default";
  //                    }
  //                    type string {
  //                    }
  //                  }
  //                }
  //              }
  //            }
  //            case case_2 {
  //              leaf routing-instance {
  //                description "Routing instance of server to which to forward";
  //                type union {
  //                  type string {
  //                    pattern "default";
  //                  }
  //                  type string {
  //                  }
  //                }
  //              }
  //            }
  //          }
  //        }
  //        list interface {
  //          key name;
  //          ordered-by user;
  //          description "Incoming DNS request forwarding interface configuration";
  //          leaf name {
  //            description "Name of interface or group of interfaces";
  //            type union {
  //              type jt:interface-wildcard;
  //              type string {
  //                pattern "<.*>|$.*";
  //              }
  //            }
  //          }
  //          // uses apply-advanced;
  //          leaf no-listen {
  //            description "Do not listen on this interface";
  //            type empty;
  //          }
  //          leaf broadcast {
  //            description "If the layer 2 interface is unknown then broadcast";
  //            type empty;
  //          }
  //          leaf description {
  //            description "Text description of server";
  //            type string;
  //          }
  //          container server {
  //            description "Server information";
  //            leaf address {
  //              description "Name or address of server to which to forward";
  //              type jt:ipv4addr;
  //            }
  //            choice instance {
  //              case case_1 {
  //                container logical-system {
  //                  description "Logical system of server to which to forward";
  //                  leaf logical-system-name {
  //                    description "Name of logical system";
  //                    type string {
  //                    }
  //                  }
  //                  leaf routing-instance {
  //                    description "Routing instance of server to which to forward";
  //                    type union {
  //                      type string {
  //                        pattern "default";
  //                      }
  //                      type string {
  //                      }
  //                    }
  //                  }
  //                }
  //              }
  //              case case_2 {
  //                leaf routing-instance {
  //                  description "Routing instance of server to which to forward";
  //                  type union {
  //                    type string {
  //                      pattern "default";
  //                    }
  //                    type string {
  //                    }
  //                  }
  //                }
  //              }
  //            }
  //          }
  //        }
  //      }
  //      container tftp {
  //        description "Incoming TFTP request forwarding configuration";
  //        // uses apply-advanced;
  //        leaf description {
  //          description "Text description of server";
  //          type string;
  //        }
  //        container server {
  //          description "Server information";
  //          leaf address {
  //            description "Name or address of server to which to forward";
  //            type jt:ipv4addr;
  //          }
  //          choice instance {
  //            case case_1 {
  //              container logical-system {
  //                description "Logical system of server to which to forward";
  //                leaf logical-system-name {
  //                  description "Name of logical system";
  //                  type string {
  //                  }
  //                }
  //                leaf routing-instance {
  //                  description "Routing instance of server to which to forward";
  //                  type union {
  //                    type string {
  //                      pattern "default";
  //                    }
  //                    type string {
  //                    }
  //                  }
  //                }
  //              }
  //            }
  //            case case_2 {
  //              leaf routing-instance {
  //                description "Routing instance of server to which to forward";
  //                type union {
  //                  type string {
  //                    pattern "default";
  //                  }
  //                  type string {
  //                  }
  //                }
  //              }
  //            }
  //          }
  //        }
  //        list interface {
  //          key name;
  //          ordered-by user;
  //          description "Incoming TFTP request forwarding interface configuration";
  //          leaf name {
  //            description "Name of interface or group of interfaces";
  //            type union {
  //              type jt:interface-wildcard;
  //              type string {
  //                pattern "<.*>|$.*";
  //              }
  //            }
  //          }
  //          // uses apply-advanced;
  //          leaf no-listen {
  //            description "Do not listen on this interface";
  //            type empty;
  //          }
  //          leaf broadcast {
  //            description "If the layer 2 interface is unknown then broadcast";
  //            type empty;
  //          }
  //          leaf description {
  //            description "Text description of server";
  //            type string;
  //          }
  //          container server {
  //            description "Server information";
  //            leaf address {
  //              description "Name or address of server to which to forward";
  //              type jt:ipv4addr;
  //            }
  //            choice instance {
  //              case case_1 {
  //                container logical-system {
  //                  description "Logical system of server to which to forward";
  //                  leaf logical-system-name {
  //                    description "Name of logical system";
  //                    type string {
  //                    }
  //                  }
  //                  leaf routing-instance {
  //                    description "Routing instance of server to which to forward";
  //                    type union {
  //                      type string {
  //                        pattern "default";
  //                      }
  //                      type string {
  //                      }
  //                    }
  //                  }
  //                }
  //              }
  //              case case_2 {
  //                leaf routing-instance {
  //                  description "Routing instance of server to which to forward";
  //                  type union {
  //                    type string {
  //                      pattern "default";
  //                    }
  //                    type string {
  //                    }
  //                  }
  //                }
  //              }
  //            }
  //          }
  //        }
  //      }
  //      container bootp {
  //        description "Incoming BOOTP/DHCP request forwarding configuration";
  //        // uses apply-advanced;
  //        leaf relay-agent-option {
  //          description "Use DHCP Relay Agent option in relayed BOOTP/DHCP messages";
  //          type empty;
  //        }
  //        leaf description {
  //          description "Text description of servers";
  //          type string;
  //        }
  //        list server {
  //          key name;
  //          ordered-by user;
  //          description "Server information";
  //          leaf name {
  //            description "Name or address of servers to which to forward";
  //            type jt:ipv4addr;
  //          }
  //          // uses apply-advanced;
  //          list logical-system {
  //            key name;
  //            ordered-by user;
  //            description "Logical system of server to which to forward";
  //            leaf name {
  //              description "Name of logical system";
  //              type string {
  //              }
  //            }
  //            leaf-list routing-instance {
  //              ordered-by user;
  //              description "Routing instance of server to which to forward";
  //              type string;
  //            }
  //          }
  //          leaf-list routing-instance {
  //            ordered-by user;
  //            description "Routing instance of server to which to forward";
  //            type string;
  //          }
  //        }
  //        leaf maximum-hop-count {
  //          description "Maximum number of hops per packet";
  //          default "4";
  //          type union {
  //            type string {
  //              pattern "<.*>|$.*";
  //            }
  //            type uint32 {
  //              range "1 .. 16";
  //            }
  //          }
  //        }
  //        leaf minimum-wait-time {
  //          description "Minimum number of seconds before requests are forwarded";
  //          default "0";
  //          type union {
  //            type string {
  //              pattern "<.*>|$.*";
  //            }
  //            type uint32 {
  //              range "0 .. 30000";
  //            }
  //          }
  //        }
  //        leaf client-response-ttl {
  //          description "IP time-to-live value to set in responses to client";
  //          type union {
  //            type string {
  //              pattern "<.*>|$.*";
  //            }
  //            type uint32 {
  //              range "1 .. 255";
  //            }
  //          }
  //        }
  //        leaf vpn {
  //          description "Enable vpn encryption ";
  //          type empty;
  //        }
  //        leaf apply-secondary-as-giaddr {
  //          description "Enable DHCP relay to use secondary gateway ip on all interfaces";
  //          type empty;
  //        }
  //        list interface {
  //          key name;
  //          ordered-by user;
  //          description "Incoming BOOTP/DHCP request forwarding interface configuration";
  //          leaf name {
  //            description "Name of interface or group of interfaces";
  //            type union {
  //              type jt:interface-wildcard;
  //              type string {
  //                pattern "<.*>|$.*";
  //              }
  //            }
  //          }
  //          // uses apply-advanced;
  //          leaf no-listen {
  //            description "Do not listen on this interface";
  //            type empty;
  //          }
  //          leaf broadcast {
  //            description "If the layer 2 interface is unknown then broadcast";
  //            type empty;
  //          }
  //          leaf description {
  //            description "Text description of servers";
  //            type string;
  //          }
  //          list server {
  //            key name;
  //            ordered-by user;
  //            description "Server information";
  //            leaf name {
  //              description "Name or address of servers to which to forward";
  //              type jt:ipv4addr;
  //            }
  //            // uses apply-advanced;
  //            list logical-system {
  //              key name;
  //              ordered-by user;
  //              description "Logical system of server to which to forward";
  //              leaf name {
  //                description "Name of logical system";
  //                type string {
  //                }
  //              }
  //              leaf-list routing-instance {
  //                ordered-by user;
  //                description "Routing instance of server to which to forward";
  //                type string;
  //              }
  //            }
  //            leaf-list routing-instance {
  //              ordered-by user;
  //              description "Routing instance of server to which to forward";
  //              type string;
  //            }
  //          }
  //          leaf maximum-hop-count {
  //            description "Maximum number of hops per packet";
  //            default "4";
  //            type union {
  //              type string {
  //                pattern "<.*>|$.*";
  //              }
  //              type uint32 {
  //                range "1 .. 16";
  //              }
  //            }
  //          }
  //          leaf minimum-wait-time {
  //            description "Minimum number of seconds before requests are forwarded";
  //            default "0";
  //            type union {
  //              type string {
  //                pattern "<.*>|$.*";
  //              }
  //              type uint32 {
  //                range "0 .. 30000";
  //              }
  //            }
  //          }
  //          leaf client-response-ttl {
  //            description "IP time-to-live value to set in responses to client";
  //            type union {
  //              type string {
  //                pattern "<.*>|$.*";
  //              }
  //              type uint32 {
  //                range "1 .. 255";
  //              }
  //            }
  //          }
  //          leaf vpn {
  //            description "Enable vpn encryption ";
  //            type empty;
  //          }
  //          leaf apply-secondary-as-giaddr {
  //            description "Enable DHCP relay to use secondary gateway ip on this interface";
  //            type empty;
  //          }
  //        }
  //      }
  //      list port {
  //        key name;
  //        ordered-by user;
  //        description "Incoming arbitrary protocol request forwarding configuration";
  //        leaf name {
  //          description "Port number of the protocol to listen";
  //          type union {
  //            type string {
  //              pattern "<.*>|$.*";
  //            }
  //            type uint32 {
  //              range "1 .. 65535";
  //            }
  //          }
  //        }
  //        // uses apply-advanced;
  //        leaf description {
  //          description "Text description of server";
  //          type string;
  //        }
  //        list server {
  //          key name;
  //          ordered-by user;
  //          description "Server information";
  //          leaf name {
  //            description "Name or address of server to which to forward";
  //            type jt:ipv4addr;
  //          }
  //          // uses apply-advanced;
  //          choice instance {
  //            case case_1 {
  //              container logical-system {
  //                description "Logical system of server to which to forward";
  //                leaf logical-system-name {
  //                  description "Name of logical system";
  //                  type string {
  //                  }
  //                }
  //                leaf routing-instance {
  //                  description "Routing instance of server to which to forward";
  //                  type union {
  //                    type string {
  //                      pattern "default";
  //                    }
  //                    type string {
  //                    }
  //                  }
  //                }
  //              }
  //            }
  //            case case_2 {
  //              leaf routing-instance {
  //                description "Routing instance of server to which to forward";
  //                type union {
  //                  type string {
  //                    pattern "default";
  //                  }
  //                  type string {
  //                  }
  //                }
  //              }
  //            }
  //          }
  //        }
  //        list interface {
  //          key name;
  //          ordered-by user;
  //          description "Incoming request forwarding interface configuration";
  //          leaf name {
  //            description "Name of interface or group of interfaces";
  //            type union {
  //              type jt:interface-wildcard;
  //              type string {
  //                pattern "<.*>|$.*";
  //              }
  //            }
  //          }
  //          // uses apply-advanced;
  //          leaf no-listen {
  //            description "Do not listen on this interface";
  //            type empty;
  //          }
  //          leaf broadcast {
  //            description "If the layer 2 interface is unknown then broadcast";
  //            type empty;
  //          }
  //          leaf description {
  //            description "Text description of server";
  //            type string;
  //          }
  //          list server {
  //            key name;
  //            ordered-by user;
  //            description "Server information";
  //            leaf name {
  //              description "Name or address of server to which to forward";
  //              type jt:ipv4addr;
  //            }
  //            // uses apply-advanced;
  //            choice instance {
  //              case case_1 {
  //                container logical-system {
  //                  description "Logical system of server to which to forward";
  //                  leaf logical-system-name {
  //                    description "Name of logical system";
  //                    type string {
  //                    }
  //                  }
  //                  leaf routing-instance {
  //                    description "Routing instance of server to which to forward";
  //                    type union {
  //                      type string {
  //                        pattern "default";
  //                      }
  //                      type string {
  //                      }
  //                    }
  //                  }
  //                }
  //              }
  //              case case_2 {
  //                leaf routing-instance {
  //                  description "Routing instance of server to which to forward";
  //                  type union {
  //                    type string {
  //                      pattern "default";
  //                    }
  //                    type string {
  //                    }
  //                  }
  //                }
  //              }
  //            }
  //          }
  //        }
  //      }
  //    }
  //    container family {
  //      description "Protocol family";
  //      container inet {
  //        description "IPv4 parameters";
  //        // uses apply-advanced;
  //        container dscp-mapping-classifier {
  //          description "Bind classifier name Globally";
  //          leaf classifier-name {
  //            description "Ipv4 classifier-name";
  //            type union {
  //              type string {
  //                pattern "default";
  //              }
  //              type string {
  //                length "1 .. 64";
  //              }
  //            }
  //          }
  //        }
  //        container filter {
  //          description "Filtering for forwarding table";
  //          // uses apply-advanced;
  //          leaf input {
  //            description "Name of input filter to apply for forwarded packets";
  //            type string;
  //          }
  //          leaf output {
  //            description "Name of output filter to apply for forwarded packets";
  //            type string;
  //          }
  //        }
  //        leaf route-accounting {
  //          description "Enable IPv4 route accounting";
  //          type empty;
  //        }
  //      }
  //      container inet6 {
  //        description "IPv6 parameters";
  //        // uses apply-advanced;
  //        container dscp-ipv6-mapping-classifier {
  //          description "Bind classifier name Globally";
  //          leaf classifier-name {
  //            description "Ipv6 classifier-name";
  //            type union {
  //              type string {
  //                pattern "default";
  //              }
  //              type string {
  //                length "1 .. 64";
  //              }
  //            }
  //          }
  //        }
  //        container filter {
  //          description "Filtering for forwarding table";
  //          // uses apply-advanced;
  //          leaf input {
  //            description "Name of input filter to apply for forwarded packets";
  //            type string;
  //          }
  //          leaf output {
  //            description "Name of output filter to apply for forwarded packets";
  //            type string;
  //          }
  //        }
  //        leaf route-accounting {
  //          description "Enable IPv6 route accounting";
  //          type empty;
  //        }
  //        leaf source-checking {
  //          description "Discard IPv6 packet when source address type is unspecified, loopback, multicast or link-local ";
  //          type empty;
  //        }
  //      }
  //      container mpls {
  //        description "MPLS parameters";
  //        // uses apply-advanced;
  //        container filter {
  //          description "Filtering for forwarding table";
  //          // uses apply-advanced;
  //          leaf input {
  //            description "Name of input filter to apply for forwarded packets";
  //            type string;
  //          }
  //          leaf output {
  //            description "Name of output filter to apply for forwarded packets";
  //            type string;
  //          }
  //        }
  //      }
  //      container vpls {
  //        description "VPLS parameters";
  //        // uses apply-advanced;
  //        container filter {
  //          description "Filtering for VPLS DMAC forwarding table";
  //          // uses apply-advanced;
  //          leaf input {
  //            description "Name of input filter to apply for forwarded packets";
  //            type string;
  //          }
  //        }
  //        container flood {
  //          description "Filtering for VPLS flood table";
  //          // uses apply-advanced;
  //          leaf input {
  //            description "Name of input filter to apply for VPLS flood packets";
  //            type string;
  //          }
  //        }
  //      }
  //      container evpn {
  //        description "EVPN parameters";
  //        // uses apply-advanced;
  //        container filter {
  //          description "Filtering for EVPN DMAC forwarding table";
  //          // uses apply-advanced;
  //          leaf input {
  //            description "Name of input filter to apply for forwarded packets";
  //            type string;
  //          }
  //        }
  //        container flood {
  //          description "Filtering for EVPN flood table";
  //          // uses apply-advanced;
  //          leaf input {
  //            description "Name of input filter to apply for EVPN flood packets";
  //            type string;
  //          }
  //        }
  //      }
  //    }
  //    list next-hop-group {
  //      key name;
  //      description "Next hop group forwarding option";
  //      uses juniper-next-hop-group-options;
  //    }
  //    container dhcp-relay {
  //      description "Dynamic Host Configuration Protocol relay configuration";
  //      uses jdhcp-relay-type;
  //    }
  //    choice load-balance-label-capability-choice {
  //      leaf load-balance-label-capability {
  //        description "Load balance label capability";
  //        type empty;
  //      }
  //      leaf no-load-balance-label-capability {
  //        description "Don't load balance label capability";
  //        type empty;
  //      }
  //    }
  //    leaf fast-reroute-priority {
  //      description "Fast-reroute repair priority";
  //      type enumeration {
  //        enum "low" {
  //          description "Set priority to low";
  //        }
  //        enum "medium" {
  //          description "Set priority to medium";
  //        }
  //        enum "high" {
  //          description "Set priority to high";
  //        }
  //      }
  //    }
  //    list ip-options-protocol-queue {
  //      key name;
  //      ordered-by user;
  //      description "IP Options protocol logical queue parameters";
  //      leaf name {
  //        description "Protocol name";
  //        type string;
  //      }
  //      // uses apply-advanced;
  //      leaf protocol-id {
  //        description "Protocol Identifier";
  //        type union {
  //          type string {
  //            pattern "<.*>|$.*";
  //          }
  //          type uint8 {
  //            range "1 .. 254";
  //          }
  //        }
  //      }
  //      leaf queue-depth {
  //        description "Size of the protocol logical options queue";
  //        type union {
  //          type string {
  //            pattern "<.*>|$.*";
  //          }
  //          type uint32 {
  //            range "1 .. 807";
  //          }
  //        }
  //      }
  //    }
  //    leaf link-layer-broadcast-inet-check {
  //      description "Enable destination mac and destination ip address check";
  //      type empty;
  //    }
  //    choice hyper-mode-choice {
  //      leaf hyper-mode {
  //        description "Enable hyper mode";
  //        type empty;
  //      }
  //      leaf no-hyper-mode {
  //        description "Don't enable hyper mode";
  //        type empty;
  //      }
  //    }
  //    leaf port-mac-in-tcam {
  //      description "Enable Port+mac knob in my_station_tcam. This will restart PFE";
  //      type empty;
  //    }
  //    leaf vxlan-flexflow {
  //      description "Enable VxLAN flexflow. This will restart PFE";
  //      type empty;
  //    }
  //    container access-security {
  //      description "Access security configuration";
  //      uses jdhcp-access-security-type;
  //    }
  //    list forwarding-sandbox {
  //      key name;
  //      description "Create forwarding sandbox";
  //      max-elements 8;
  //      uses juniper-forwarding-sandbox-options;
  //    }
  //    container vxlan-routing {
  //      description "VXLAN Routing forwarding options";
  //      // uses apply-advanced;
  //      leaf next-hop {
  //        description "Next-hop. Must be multiple of 4096. This will restart PFE";
  //        type union {
  //          type string {
  //            pattern "<.*>|$.*";
  //          }
  //          type uint32;
  //        }
  //      }
  //      leaf interface-num {
  //        description "Interface. Must be multiple of 2048. This will restart PFE";
  //        type union {
  //          type string {
  //            pattern "<.*>|$.*";
  //          }
  //          type uint32;
  //        }
  //      }
  //      leaf overlay-ecmp {
  //        description "Enable overlay ecmp for vxlan L3. This will restart PFE";
  //        type empty;
  //      }
  //      leaf loopback-port {
  //        description "AE loopback interface used for VXLAN routing. This will restart PFE";
  //        type string;
  //      }
  //    }
  //    container satellite {
  //      description "Satellite forwarding options";
  //      // uses apply-advanced;
  //      container traceoptions {
  //        description "Global tracing options for satellite control plane";
  //        // uses apply-advanced;
  //        leaf no-remote-trace {
  //          description "Disable remote tracing";
  //          type empty;
  //        }
  //        container file {
  //          description "Trace file information";
  //          leaf filename {
  //            description "Name of file in which to write trace information";
  //            type string {
  //              length "1 .. 1024";
  //            }
  //          }
  //          leaf size {
  //            description "Maximum trace file size";
  //            type string;
  //          }
  //          leaf files {
  //            description "Maximum number of trace files";
  //            default "3";
  //            type union {
  //              type string {
  //                pattern "<.*>|$.*";
  //              }
  //              type uint32 {
  //                range "2 .. 1000";
  //              }
  //            }
  //          }
  //          choice world-readable-choice {
  //            leaf world-readable {
  //              description "Allow any user to read the log file";
  //              type empty;
  //            }
  //            leaf no-world-readable {
  //              description "Don't allow any user to read the log file";
  //              type empty;
  //            }
  //          }
  //          leaf match {
  //            description "Regular expression for lines to be logged";
  //            type jt:regular-expression;
  //          }
  //        }
  //        list flag {
  //          key name;
  //          ordered-by user;
  //          description "Tracing parameters";
  //          leaf name {
  //            type enumeration {
  //              enum "all" {
  //                description "Trace everything";
  //              }
  //              enum "bd" {
  //                description "Trace BD events";
  //              }
  //              enum "config-internal" {
  //                description "Trace configuration internals";
  //              }
  //              enum "interface" {
  //                description "Trace interface events";
  //              }
  //              enum "interface-vlan" {
  //                description "Trace IFBD events";
  //              }
  //              enum "ipc" {
  //                description "Trace internal IPC messages";
  //              }
  //              enum "kernel" {
  //                description "Trace Kernel messages";
  //              }
  //              enum "krt" {
  //                description "Trace communication over routing socket";
  //              }
  //              enum "mac" {
  //                description "Trace MAC events ";
  //              }
  //              enum "nh" {
  //                description "Trace NH events";
  //              }
  //              enum "normal" {
  //                description "Trace normal events";
  //              }
  //              enum "parse" {
  //                description "Trace configuration parsing";
  //              }
  //              enum "stp" {
  //                description "Trace STP events";
  //              }
  //              enum "task" {
  //                description "Trace task processing";
  //              }
  //              enum "timer" {
  //                description "Trace task timer processing";
  //              }
  //              enum "firewall" {
  //                description "Trace firewall processing";
  //              }
  //              enum "l3" {
  //                description "Trace Layer-3 processing";
  //              }
  //              enum "fip-snooping" {
  //                description "Trace FIP-Snooping processing";
  //              }
  //            }
  //          }
  //        }
  //      }
  //      leaf local-replication {
  //        description "Enable satellite multicast replication";
  //        type empty;
  //      }
  //      list fpc {
  //        key name;
  //        leaf name {
  //          description "Satellite slot identifier";
  //          type union {
  //            type string {
  //              pattern "<.*>|$.*";
  //            }
  //            type uint32 {
  //              range "65 .. 254";
  //            }
  //          }
  //        }
  //        // uses apply-advanced;
  //        choice local-switching-mode-choice {
  //          case case_1 {
  //            container local-switching {
  //              presence "enable local-switching";
  //              description "Enable local-switching on Satellite device";
  //              // uses apply-advanced;
  //              leaf l3 {
  //                description "Enable L3 local switching on the Satellite device";
  //                type empty;
  //              }
  //            }
  //          }
  //          case case_2 {
  //            container selective-vlan-switching {
  //              description "Enable selective-vlan-switching on Satellite device";
  //              // uses apply-advanced;
  //              leaf routing-instance {
  //                description "Associated Routing instance name";
  //                type string {
  //                }
  //              }
  //            }
  //          }
  //        }
  //      }
  //      container vlan-auto-sense {
  //        description "Vlan-auto-sense attributes provisioning";
  //        // uses apply-advanced;
  //        leaf expiry-time {
  //          description "Expiry time (in seconds) after last MAC aged out";
  //          default "600";
  //          units "seconds";
  //          type union {
  //            type string {
  //              pattern "<.*>|$.*";
  //            }
  //            type uint32 {
  //              range "30 .. 3600";
  //            }
  //          }
  //        }
  //      }
  //      container analyzer-vlan {
  //        description "Output VLAN for Analyzer";
  //        // uses apply-advanced;
  //        leaf vlan-name {
  //          description "Name of the analyzer VLAN";
  //          type string;
  //        }
  //      }
  //      choice disable-heartbeat-choice {
  //        leaf disable-heartbeat {
  //          description "Disable heartbeat between Aggregation and Satellite";
  //          type empty;
  //        }
  //        leaf no-disable-heartbeat {
  //          description "Don't disable heartbeat between Aggregation and Satellite";
  //          type empty;
  //        }
  //      }
  //    }
  //  }
  //  grouping jdhcp-access-security-type {
  //    description "Access security configuration";
  //    // uses apply-advanced;
  //    container slaac-snooping {
  //      description "Stateless address auto configuration options";
  //      uses slaacd-config-type;
  //    }
  //    container router-advertisement-guard {
  //      presence "enable router-advertisement-guard";
  //      description "Router Advertisement Guard Configuration";
  //      // uses apply-advanced;
  //      list policy {
  //        key name;
  //        ordered-by user;
  //        description "Router Advertisement Guard policy";
  //        leaf name {
  //          description "Router Advertisement Guard policy name";
  //          type string {
  //            length "1 .. 64";
  //          }
  //        }
  //        // uses apply-advanced;
  //        container discard {
  //          description "Discard parameters";
  //          // uses apply-advanced;
  //          leaf source-ip-address-list {
  //            description "IPv6 Source address list name";
  //            type string;
  //          }
  //          leaf source-mac-address-list {
  //            description "Source mac address list name";
  //            type string;
  //          }
  //          leaf prefix-list-name {
  //            description "Prefix-list Name";
  //            type string;
  //          }
  //        }
  //        container accept {
  //          description "Accept parameters";
  //          // uses apply-advanced;
  //          container match-list {
  //            description "List of parameters to check";
  //            // uses apply-advanced;
  //            leaf source-ip-address-list {
  //              description "IPv6 Source address list name";
  //              type string;
  //            }
  //            leaf source-mac-address-list {
  //              description "Source mac address list name";
  //              type string;
  //            }
  //            leaf prefix-list-name {
  //              description "Prefix-list Name";
  //              type string;
  //            }
  //            leaf match-criteria {
  //              description "Match Criteria";
  //              type enumeration {
  //                enum "match-all" {
  //                  description "A match from every list";
  //                }
  //                enum "match-any" {
  //                  description "A match from any list";
  //                }
  //              }
  //            }
  //          }
  //          container match-options {
  //            presence "enable match-options";
  //            description "List of Options to check";
  //            // uses apply-advanced;
  //            container hop-limit {
  //              description "Hop limit";
  //              // uses apply-advanced;
  //              leaf maximum {
  //                description "Maximum hop limit";
  //                type union {
  //                  type string {
  //                    pattern "<.*>|$.*";
  //                  }
  //                  type uint32 {
  //                    range "1 .. 255";
  //                  }
  //                }
  //              }
  //              leaf minimum {
  //                description "Minimum hop limit";
  //                type union {
  //                  type string {
  //                    pattern "<.*>|$.*";
  //                  }
  //                  type uint32 {
  //                    range "1 .. 255";
  //                  }
  //                }
  //              }
  //            }
  //            container route-preference {
  //              description "Accept route preference";
  //              // uses apply-advanced;
  //              leaf maximum {
  //                description "Maximum route preference";
  //                type enumeration {
  //                  enum "low" {
  //                    description "Route preference low";
  //                  }
  //                  enum "medium" {
  //                    description "Route preference medium";
  //                  }
  //                  enum "high" {
  //                    description "Route preference high";
  //                  }
  //                }
  //              }
  //            }
  //            leaf managed-config-flag {
  //              description "Check Managed config flag";
  //              type empty;
  //            }
  //            leaf other-config-flag {
  //              description "Check Other config flag";
  //              type empty;
  //            }
  //          }
  //        }
  //      }
  //      container interface {
  //        description "RA Guard config on Interface";
  //        // uses apply-advanced;
  //        list intf-config {
  //          key name;
  //          description "Interface Configuration";
  //          uses interface-policy;
  //        }
  //      }
  //      container vlans {
  //        description "RA Guard config on Vlan";
  //        // uses apply-advanced;
  //        list vlan-config {
  //          key name;
  //          description "Virtual LAN Configuration";
  //          uses vlan-policy;
  //        }
  //      }
  //    }
  //  }
   grouping interface-policy {
     description "Interface Name";
     leaf name {
       description "Interface Name";
       type union {
         type jt:interface-name;
         type string {
           pattern "<.*>|$.*";
         }
       }
     }
     // uses apply-advanced;
     container policy {
       description "Attach policy";
       // uses apply-advanced;
       leaf policy-name {
         description "Router Advertisement Guard policy name";
         type string;
       }
       choice policy-type {
         case case_1 {
           leaf stateful {
             description "Stateful router advertisement guard";
             type empty;
           }
         }
         case case_2 {
           leaf stateless {
             description "Stateless router advertisement guard";
             type empty;
           }
         }
       }
     }
     container mark-interface {
       description "Mark interface";
       // uses apply-advanced;
       choice mark-intf-type {
         case case_1 {
           leaf trusted {
             description "Mark interface trusted";
             type empty;
           }
         }
         case case_2 {
           leaf block {
             description "Block router-advertisement";
             type empty;
           }
         }
       }
     }
   }
  //  grouping juniper-forwarding-sandbox-options {
  //    leaf name {
  //      description "Sandbox name";
  //      type string;
  //    }
  //    // uses apply-advanced;
  //    leaf size {
  //      description "Size of the sandbox";
  //      default "small";
  //      type enumeration {
  //        enum "small" {
  //          description "Sandbox size small";
  //        }
  //        enum "medium" {
  //          description "Sandbox size medium";
  //        }
  //        enum "large" {
  //          description "Sandbox size large";
  //        }
  //      }
  //    }
  //    list port {
  //      key name;
  //      description "Sandbox port";
  //      max-elements 64;
  //      uses juniper-forwarding-sandbox-port-options;
  //    }
  //  }
  //  grouping juniper-forwarding-sandbox-port-options {
  //    leaf name {
  //      description "Port name";
  //      type string;
  //    }
  //    // uses apply-advanced;
  //    list interface {
  //      key name;
  //      ordered-by user;
  //      description "Interface to which the port is mapped";
  //      max-elements 1;
  //      leaf name {
  //        description "Interface name";
  //        type union {
  //          type jt:interface-device;
  //          type string {
  //            pattern "<.*>|$.*";
  //          }
  //        }
  //      }
  //      // uses apply-advanced;
  //    }
  //  }
  //  grouping juniper-igmp-snooping-options {
  //    // uses apply-advanced;
  //    leaf use-p2mp-lsp {
  //      description "P2MP will be used to forward traffic instead of PW";
  //      type empty;
  //    }
  //    container snoop-pseudowires {
  //      presence "enable snoop-pseudowires";
  //      description "VPLS PE would send traffic selectively to PE's having interest";
  //      // uses apply-advanced;
  //    }
  //  }
  //  grouping juniper-mld-snooping-options {
  //    // uses apply-advanced;
  //    leaf use-p2mp-lsp {
  //      description "P2MP will be used to forward traffic instead of PW";
  //      type empty;
  //    }
  //    container snoop-pseudowires {
  //      presence "enable snoop-pseudowires";
  //      description "VPLS PE would send traffic selectively to PE's having interest";
  //      // uses apply-advanced;
  //    }
  //  }
  //  grouping juniper-monitoring-options {
  //    leaf name {
  //      description "Name for monitoring group";
  //      type string;
  //    }
  //    // uses apply-advanced;
  //    container family {
  //      description "Address family of packets to monitor";
  //      container inet {
  //        presence "enable inet";
  //        description "Monitor IPv4 packets";
  //        // uses apply-advanced;
  //        container input {
  //          description "Monitor data acquisition";
  //          presence "enable input";
  //          status deprecated;
  //          uses monitoring_input_type;
  //        }
  //        container output {
  //          description "Monitoring data disposition";
  //          presence "enable output";
  //          uses monitoring_output_type;
  //        }
  //      }
  //    }
  //  }
  //  grouping juniper-multicast-snooping-options {
  //    // uses apply-advanced;
  //    container options {
  //      description "Miscellaneous options";
  //      // uses apply-advanced;
  //      container syslog {
  //        description "Set system logging level";
  //        // uses apply-advanced;
  //        container level {
  //          description "Logging level";
  //          leaf emergency {
  //            description "Emergency level";
  //            type empty;
  //          }
  //          leaf alert {
  //            description "Alert level";
  //            type empty;
  //          }
  //          leaf critical {
  //            description "Critical level";
  //            type empty;
  //          }
  //          leaf error {
  //            description "Error level";
  //            type empty;
  //          }
  //          leaf warning {
  //            description "Warning level";
  //            type empty;
  //          }
  //          leaf notice {
  //            description "Notice level";
  //            type empty;
  //          }
  //          leaf info {
  //            description "Informational level";
  //            type empty;
  //          }
  //          leaf debug {
  //            description "Debugging level";
  //            type empty;
  //          }
  //        }
  //        leaf upto {
  //          description "Log up to a particular logging level";
  //          type enumeration {
  //            enum "emergency" {
  //              description "Emergency level";
  //            }
  //            enum "alert" {
  //              description "Alert level";
  //            }
  //            enum "critical" {
  //              description "Critical level";
  //            }
  //            enum "error" {
  //              description "Error level";
  //            }
  //            enum "warning" {
  //              description "Warning level";
  //            }
  //            enum "notice" {
  //              description "Notice level";
  //            }
  //            enum "info" {
  //              description "Informational level";
  //            }
  //            enum "debug" {
  //              description "Debugging level";
  //            }
  //          }
  //        }
  //        leaf mark {
  //          description "Periodically mark the trace file";
  //          units "seconds";
  //          type union {
  //            type int32;
  //            type string {
  //              pattern "<.*>|$.*";
  //            }
  //          }
  //        }
  //      }
  //    }
  //    container traceoptions {
  //      description "Multicast snooping trace options";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "parse" {
  //              description "Trace configuration parsing";
  //            }
  //            enum "config-internal" {
  //              description "Trace configuration internals";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf disable {
  //          description "Disable this trace flag";
  //          type empty;
  //        }
  //      }
  //    }
  //    container forwarding-cache {
  //      description "Multicast forwarding cache";
  //      // uses apply-advanced;
  //      container threshold {
  //        description "Threshold";
  //        // uses apply-advanced;
  //        leaf suppress {
  //          description "Suppress threshold";
  //          type union {
  //            type string {
  //              pattern "<.*>|$.*";
  //            }
  //            type uint32 {
  //              range "1 .. 200000";
  //            }
  //          }
  //        }
  //        leaf reuse {
  //          description "Reuse threshold";
  //          type union {
  //            type string {
  //              pattern "<.*>|$.*";
  //            }
  //            type uint32 {
  //              range "1 .. 200000";
  //            }
  //          }
  //        }
  //      }
  //    }
  //    leaf-list flood-groups {
  //      ordered-by user;
  //      description "Groups for which the traffic will be flooded";
  //      type jt:ipaddr;
  //    }
  //    container host-outbound-traffic {
  //      description "Host generated protocol packets";
  //      // uses apply-advanced;
  //      leaf forwarding-class {
  //        description "Forwarding class name";
  //        type string {
  //        }
  //      }
  //      leaf dot1p {
  //        description "Dot1p bits";
  //        type union {
  //          type string {
  //            pattern "<.*>|$.*";
  //          }
  //          type uint32 {
  //            range "0 .. 7";
  //          }
  //        }
  //      }
  //    }
  //    container graceful-restart {
  //      description "Configure graceful restart attributes";
  //      // uses apply-advanced;
  //      choice enable-disable {
  //        case case_1 {
  //          leaf disable {
  //            description "Disable graceful restart";
  //            type empty;
  //          }
  //        }
  //      }
  //      leaf restart-duration {
  //        description "Maximum time for graceful restart to finish";
  //        default "180";
  //        units "seconds";
  //        type union {
  //          type string {
  //            pattern "<.*>|$.*";
  //          }
  //          type uint32 {
  //            range "0 .. 300";
  //          }
  //        }
  //      }
  //    }
  //    leaf ignore-stp-topology-change {
  //      description "Don't process stp topology change";
  //      type empty;
  //    }
  //    container multichassis-lag-replicate-state {
  //      presence "enable multichassis-lag-replicate-state";
  //      description "Enable multichassis lag replication";
  //      // uses apply-advanced;
  //      leaf suppress-report {
  //        description "Enable mclag report suppression";
  //        type empty;
  //      }
  //    }
  //    container oism {
  //      description "Optimized inter subnet multicast options";
  //      // uses apply-advanced;
  //      leaf install-star-g-routes {
  //        description "Install (*,G) multicast routes in data plane";
  //        type empty;
  //      }
  //      leaf conserve-mcast-routes-in-pfe {
  //        description "Don't install snooping routes in forwarding plane";
  //        type empty;
  //      }
  //    }
  //    leaf nexthop-hold-time {
  //      description "Nexthop hold time in milliseconds";
  //      units "milliseconds";
  //      type union {
  //        type string {
  //          pattern "<.*>|$.*";
  //        }
  //        type uint32 {
  //          range "1 .. 1000";
  //        }
  //      }
  //    }
  //  }
  //  grouping juniper-next-hop-group-options {
  //    leaf name {
  //      description "Next hop group name";
  //      type string;
  //    }
  //    // uses apply-advanced;
  //    leaf group-type {
  //      description "Next hop group type";
  //      default "inet";
  //      type enumeration {
  //        enum "inet" {
  //          description "Group of family inet next-hops";
  //        }
  //        enum "layer-2" {
  //          description "Layer-2 next-hop group";
  //        }
  //        enum "inet6" {
  //          description "Group of family inet6 next-hops";
  //        }
  //      }
  //    }
  //    list interface {
  //      key name;
  //      description "Interfaces through which to send sampled traffic";
  //      uses next_hop_group_intf_type;
  //    }
  //    list next-hop-subgroup {
  //      key name;
  //      description "Group of interfaces through which to send sampled traffic";
  //      uses juniper-next-hop-subgroup-options;
  //    }
  //  }
  //  grouping juniper-next-hop-subgroup-options {
  //    leaf name {
  //      description "Next-hop sub-group name";
  //      type string;
  //    }
  //    // uses apply-advanced;
  //    list interface {
  //      key name;
  //      description "Interface through which to send the sampled traffic";
  //      max-elements 16;
  //      uses next_hop_subgroup_intf_type;
  //    }
  //  }
  //  grouping juniper-packet-accounting-options {
  //    leaf name {
  //      description "Name for accounting group";
  //      type string;
  //    }
  //    // uses apply-advanced;
  //    container output {
  //      description "Accounting data disposition";
  //      uses packet_accounting_output_type;
  //    }
  //  }
  //  grouping juniper-packet-capture-options {
  //    description "Packet capture options";
  //    // uses apply-advanced;
  //    choice enable-disable {
  //      case case_1 {
  //        leaf disable {
  //          description "Disable packet-capture";
  //          type empty;
  //        }
  //      }
  //    }
  //    container file {
  //      description "Parameters for file that contains captured packets";
  //      leaf filename {
  //        description "Name of file";
  //        type string {
  //          length "1 .. 900";
  //        }
  //      }
  //      leaf files {
  //        description "Maximum number of files";
  //        default "10";
  //        type union {
  //          type string {
  //            pattern "<.*>|$.*";
  //          }
  //          type uint32 {
  //            range "2 .. 10000";
  //          }
  //        }
  //      }
  //      leaf size {
  //        description "Maximum file size";
  //        type string;
  //      }
  //      choice world-readable-choice {
  //        leaf world-readable {
  //          description "Allow any user to read packet-capture files";
  //          type empty;
  //        }
  //        leaf no-world-readable {
  //          description "Don't allow any user to read packet-capture files";
  //          type empty;
  //        }
  //      }
  //    }
  //    leaf maximum-capture-size {
  //      description "Maximum packet size to capture";
  //      default "68";
  //      units "bytes";
  //      type union {
  //        type string {
  //          pattern "<.*>|$.*";
  //        }
  //        type uint32 {
  //          range "68 .. 1520";
  //        }
  //      }
  //    }
  //  }
  //  grouping juniper-port-mirror-options {
  //    // uses apply-advanced;
  //    container traceoptions {
  //      description "Port-mirroring trace options";
  //      uses sampling_traceoptions_type;
  //    }
  //    leaf disable {
  //      description "Disable the global port-mirroring instance";
  //      type empty;
  //    }
  //    leaf disable-all-instances {
  //      description "Disable the all port-mirroring instances";
  //      type empty;
  //    }
  //    leaf mirror-once {
  //      description "Sample the packet for port mirroring only once";
  //      type empty;
  //    }
  //    leaf no-preserve-ingress-tag {
  //      description "Mirror the packet retaining tag value before normalization";
  //      type empty;
  //    }
  //    leaf remote-port-mirroring {
  //      description "Flag to specify about remote-port-mirroring";
  //      type empty;
  //    }
  //    container input {
  //      description "Settings for sampling of input packets";
  //      uses pm_family_input_type;
  //    }
  //    container family {
  //      description "Address family of packets to mirror";
  //      container inet {
  //        description "Mirror IPv4 packets";
  //        // uses apply-advanced;
  //        container input {
  //          description "Settings for sampling of input packets";
  //          status deprecated;
  //          uses pm_family_input_type;
  //        }
  //        container output {
  //          description "One or more next hops for port-mirrored packets";
  //          uses inet_pm_family_output_type;
  //        }
  //      }
  //      container inet6 {
  //        description "Mirror IPv6 packets";
  //        // uses apply-advanced;
  //        container input {
  //          description "Settings for sampling of input packets";
  //          status deprecated;
  //          uses pm_family_input_type;
  //        }
  //        container output {
  //          description "One or more next hops for port-mirrored packets";
  //          uses inet6_pm_family_output_type;
  //        }
  //      }
  //      container mpls {
  //        description "Mirror MPLS packets";
  //        // uses apply-advanced;
  //        container input {
  //          description "Settings for sampling of input packets";
  //          status deprecated;
  //          uses pm_family_input_type;
  //        }
  //        container output {
  //          description "One or more next hops for port-mirrored packets";
  //          uses mpls_pm_family_output_type;
  //        }
  //      }
  //      container any {
  //        description "Mirror any packets";
  //        // uses apply-advanced;
  //        container output {
  //          description "One or more next hops for port-mirrored packets";
  //          uses any_pm_family_output_type;
  //        }
  //      }
  //      container vpls {
  //        description "Mirror Layer-2 bridged/vpls packets";
  //        // uses apply-advanced;
  //        container input {
  //          description "Settings for sampling of input packets";
  //          status deprecated;
  //          uses pm_family_input_type;
  //        }
  //        container output {
  //          description "Destination for port-mirrored packets";
  //          uses layer2_pm_family_output_type;
  //        }
  //      }
  //      container ethernet-switching {
  //        description "Mirror Layer-2 ethernet-switched packets";
  //        // uses apply-advanced;
  //        container output {
  //          description "Destination for port-mirrored packets";
  //          uses layer2_pm_family_output_type;
  //        }
  //      }
  //      container ccc {
  //        description "Mirror layer-2 ccc packets";
  //        // uses apply-advanced;
  //        container input {
  //          description "Settings for sampling of input packets";
  //          status deprecated;
  //          uses pm_family_input_type;
  //        }
  //        container output {
  //          description "Destination for port-mirrored packets";
  //          uses layer2_pm_family_output_type;
  //        }
  //      }
  //    }
  //    list instance {
  //      key name;
  //      ordered-by user;
  //      description "Instance of port-mirroring parameters";
  //      leaf name {
  //        description "Name for port-mirroring instance";
  //        type string {
  //          length "1 .. 63";
  //        }
  //      }
  //      // uses apply-advanced;
  //      leaf disable {
  //        description "Disable the this port-mirroring instance";
  //        type empty;
  //      }
  //      choice input_params_or_instance {
  //        case case_1 {
  //          container input {
  //            description "Settings for sampling of input packets";
  //            uses pm_family_input_type;
  //          }
  //        }
  //        case case_2 {
  //          leaf input-parameters-instance {
  //            description "Name of port-mirroring instance to use for input parameters";
  //            type string;
  //          }
  //        }
  //      }
  //      container output {
  //        description "One or more next hops for port-mirrored packets";
  //        uses inet_pm_output_type;
  //      }
  //      container family {
  //        description "Address family of packets to mirror";
  //        container inet {
  //          description "Mirror IPv4 packets";
  //          // uses apply-advanced;
  //          container input {
  //            description "Settings for sampling of input packets";
  //            status deprecated;
  //            uses pm_family_input_type;
  //          }
  //          container output {
  //            description "One or more next hops for port-mirrored packets";
  //            uses inet_pm_family_output_type;
  //          }
  //        }
  //        container inet6 {
  //          description "Mirror IPv6 packets";
  //          // uses apply-advanced;
  //          container input {
  //            description "Settings for sampling of input packets";
  //            status deprecated;
  //            uses pm_family_input_type;
  //          }
  //          container output {
  //            description "One or more next hops for port-mirrored packets";
  //            uses inet6_pm_family_output_type;
  //          }
  //        }
  //        container mpls {
  //          description "Mirror MPLS packets";
  //          // uses apply-advanced;
  //          container input {
  //            description "Settings for sampling of input packets";
  //            status deprecated;
  //            uses pm_family_input_type;
  //          }
  //          container output {
  //            description "One or more next hops for port-mirrored packets";
  //            uses mpls_pm_family_output_type;
  //          }
  //        }
  //        container any {
  //          description "Mirror any packets";
  //          // uses apply-advanced;
  //          container output {
  //            description "One or more next hops for port-mirrored packets";
  //            uses any_pm_family_output_type;
  //          }
  //        }
  //        container vpls {
  //          description "Mirror Layer-2 bridged/vpls packets";
  //          // uses apply-advanced;
  //          container input {
  //            description "Settings for sampling of input packets";
  //            status deprecated;
  //            uses pm_family_input_type;
  //          }
  //          container output {
  //            description "Destination for port-mirrored packets";
  //            uses layer2_pm_family_output_type;
  //          }
  //        }
  //        container ethernet-switching {
  //          description "Mirror Layer-2 ethernet-switched packets";
  //          // uses apply-advanced;
  //          container output {
  //            description "Destination for port-mirrored packets";
  //            uses layer2_pm_family_output_type;
  //          }
  //        }
  //        container ccc {
  //          description "Mirror layer-2 ccc packets";
  //          // uses apply-advanced;
  //          container input {
  //            description "Settings for sampling of input packets";
  //            status deprecated;
  //            uses pm_family_input_type;
  //          }
  //          container output {
  //            description "Destination for port-mirrored packets";
  //            uses layer2_pm_family_output_type;
  //          }
  //        }
  //      }
  //    }
  //  }
  //  grouping any_pm_family_output_type {
  //    // uses apply-advanced;
  //    choice interface-or-next-hop-index {
  //      case case_1 {
  //        list interface {
  //          key name;
  //          description "Interfaces through which to send sampled traffic";
  //          uses any_pm_intf_type;
  //        }
  //      }
  //      case case_2 {
  //        leaf next-hop-group {
  //          description "Next-hop-group through which to send port-mirror traffic";
  //          type string;
  //        }
  //      }
  //    }
  //    leaf no-filter-check {
  //      description "Do not check for filters on port-mirroring interface";
  //      type empty;
  //    }
  //    container hosted-service {
  //      description "Configure Hosted Service";
  //      // uses apply-advanced;
  //      leaf server-profile {
  //        description "Server profile name";
  //        type string {
  //          length "3 .. 32";
  //        }
  //      }
  //    }
  //    leaf policer {
  //      description "Name of policer to use to rate-limit traffic";
  //      type string {
  //      }
  //    }
  //    leaf forwarding-class {
  //      description "Forwarding-class for TOS";
  //      type string {
  //        length "1 .. 64";
  //      }
  //    }
  //  }
  //  grouping any_pm_intf_type {
  //    leaf name {
  //      description "Interface through which to send sampled traffic";
  //      type union {
  //        type jt:interface-name;
  //        type string {
  //          pattern "<.*>|$.*";
  //        }
  //      }
  //    }
  //    // uses apply-advanced;
  //    list next-hop {
  //      key name;
  //      ordered-by user;
  //      description "Address of next hop through which to send sampled traffic";
  //      uses inet_next_hop_type;
  //    }
  //  }
  //  grouping inet6_pm_family_output_type {
  //    // uses apply-advanced;
  //    choice interface-or-next-hop-index {
  //      case case_1 {
  //        list interface {
  //          key name;
  //          description "Interfaces through which to send sampled traffic";
  //          uses inet6_pm_intf_type;
  //        }
  //      }
  //      case case_2 {
  //        leaf next-hop-group {
  //          description "Next-hop-group through which to send port-mirror traffic";
  //          type string;
  //        }
  //      }
  //    }
  //    leaf policer {
  //      description "Name of policer to use to rate-limit traffic";
  //      type string {
  //      }
  //    }
  //    leaf forwarding-class {
  //      description "Forwarding-class for TOS";
  //      type string {
  //        length "1 .. 64";
  //      }
  //    }
  //    leaf no-filter-check {
  //      description "Do not check for filters on port-mirroring interface";
  //      type empty;
  //    }
  //    leaf ipv6-address {
  //      description "ERSPAN Destination IPv6 Address";
  //      type jt:ipv6addr;
  //    }
  //    leaf server-profile {
  //      description "Server profile name";
  //      type string {
  //        length "3 .. 32";
  //      }
  //    }
  //  }
  //  grouping inet6_pm_intf_type {
  //    leaf name {
  //      description "Interface through which to send sampled traffic";
  //      type union {
  //        type jt:interface-name;
  //        type string {
  //          pattern "<.*>|$.*";
  //        }
  //      }
  //    }
  //    // uses apply-advanced;
  //    list next-hop {
  //      key name;
  //      ordered-by user;
  //      description "Address of next hop through which to send sampled traffic";
  //      uses inet6_next_hop_type;
  //    }
  //  }
  //  grouping inet6_next_hop_type {
  //    description "Address of next hop through which to send sampled traffic";
  //    leaf name {
  //      type jt:ipv6addr;
  //    }
  //    // uses apply-advanced;
  //  }
   grouping inet_next_hop_type {
     description "Address of next hop through which to send sampled traffic";
     leaf name {
       type jt:ipv4addr;
     }
     // uses apply-advanced;
   }
  //  grouping inet_pm_family_output_type {
  //    // uses apply-advanced;
  //    choice interface-or-next-hop-index {
  //      case case_1 {
  //        list interface {
  //          key name;
  //          description "Interfaces through which to send sampled traffic";
  //          uses inet_pm_intf_type;
  //        }
  //      }
  //      case case_2 {
  //        leaf next-hop-group {
  //          description "Next-hop-group through which to send port-mirror traffic";
  //          type string;
  //        }
  //      }
  //    }
  //    leaf no-filter-check {
  //      description "Do not check for filters on port-mirroring interface";
  //      type empty;
  //    }
  //    leaf ip-address {
  //      description "ERSPAN Destination IP Address";
  //      type jt:ipv4addr;
  //    }
  //    list routing-instance {
  //      key name;
  //      description "Routing instances";
  //      max-elements 1;
  //      uses inet_pm_output-routing-instance-type;
  //    }
  //    leaf server-profile {
  //      description "Server profile name";
  //      type string {
  //        length "3 .. 32";
  //      }
  //    }
  //    leaf policer {
  //      description "Name of policer to use to rate-limit traffic";
  //      type string {
  //      }
  //    }
  //    leaf forwarding-class {
  //      description "Forwarding-class for TOS";
  //      type string {
  //        length "1 .. 64";
  //      }
  //    }
  //  }
  //  grouping inet_pm_intf_type {
  //    leaf name {
  //      description "Interface through which to send sampled traffic";
  //      type union {
  //        type jt:interface-name;
  //        type string {
  //          pattern "<.*>|$.*";
  //        }
  //      }
  //    }
  //    // uses apply-advanced;
  //    list next-hop {
  //      key name;
  //      ordered-by user;
  //      description "Address of next hop through which to send sampled traffic";
  //      uses inet_next_hop_type;
  //    }
  //  }
  //  grouping inet_pm_output-routing-instance-type {
  //    leaf name {
  //      description "Routing instance name";
  //      type string {
  //      }
  //    }
  //    // uses apply-advanced;
  //    leaf ip-address {
  //      description "ERSPAN Destination IP Address";
  //      type jt:ipv4addr;
  //    }
  //  }
  //  grouping inet_pm_output_type {
  //    // uses apply-advanced;
  //    leaf ip-source-address {
  //      description "IP source address";
  //      type jt:ipv4addr;
  //    }
  //    leaf ip-destination-address {
  //      description "IP destination address";
  //      type jt:ipv4addr;
  //    }
  //    leaf policer {
  //      description "Name of policer to use to rate-limit traffic";
  //      type string {
  //      }
  //    }
  //    leaf dscp {
  //      description " DSCP value 0 to 63";
  //      type union {
  //        type string {
  //          pattern "<.*>|$.*";
  //        }
  //        type uint8 {
  //          range "0 .. 63";
  //        }
  //      }
  //    }
  //    leaf forwarding-class {
  //      description "Forwarding-class for TOS";
  //      type string {
  //        length "1 .. 64";
  //      }
  //    }
  //  }
  //  grouping juniper-protocols-amt {
  //    // uses apply-advanced;
  //    container traceoptions {
  //      description "Trace options for AMT";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "packets" {
  //              description "Trace all AMT packets";
  //            }
  //            enum "errors" {
  //              description "Trace all error messages";
  //            }
  //            enum "tunnels" {
  //              description "Trace all AMT tunnel messages";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    container relay {
  //      description "AMT relay";
  //      presence "enable relay";
  //      uses juniper-protocols-amt-relay;
  //    }
  //  }
  //  grouping juniper-protocols-amt-relay {
  //    // uses apply-advanced;
  //    container family {
  //      presence "enable family";
  //      description "Protocol family";
  //      // uses apply-advanced;
  //      container inet {
  //        presence "enable inet";
  //        // uses apply-advanced;
  //        leaf anycast-prefix {
  //          description "IPv4 anycast prefix";
  //          type jt:ipv4prefix;
  //        }
  //        leaf local-address {
  //          description "IPv4 local address";
  //          type jt:ipv4addr;
  //        }
  //      }
  //    }
  //    leaf secret-key-timeout {
  //      description "Time interval for the secret key to expire";
  //      units "minutes";
  //      type union {
  //        type string {
  //          pattern "<.*>|$.*";
  //        }
  //        type uint32 {
  //          range "5 .. 1440";
  //        }
  //      }
  //    }
  //    leaf tunnel-limit {
  //      description "Number of AMT tunnels";
  //      type union {
  //        type uint32;
  //        type string {
  //          pattern "<.*>|$.*";
  //        }
  //      }
  //    }
  //    leaf unicast-stream-limit {
  //      description "Maximum number of AMT unicast streams(s,g,intf)";
  //      type union {
  //        type uint32;
  //        type string {
  //          pattern "<.*>|$.*";
  //        }
  //      }
  //    }
  //    leaf accounting {
  //      description "Enable AMT accounting";
  //      type empty;
  //    }
  //    leaf-list tunnel-devices {
  //      ordered-by user;
  //      description "Tunnel devices to be used for creating ud interfaces";
  //      type union {
  //        type jt:interface-device;
  //        type string {
  //          pattern "<.*>|$.*";
  //        }
  //      }
  //    }
  //  }
  //  grouping juniper-protocols-bd {
  //    description "Bridging configuration";
  //    // uses apply-advanced;
  //    container mac-table-size {
  //      description "Size of MAC address forwarding table";
  //      // uses apply-advanced;
  //      leaf limit {
  //        description "Maximum number of MAC addresses";
  //        type union {
  //          type string {
  //            pattern "<.*>|$.*";
  //          }
  //          type uint32;
  //        }
  //      }
  //      leaf packet-action {
  //        description "Action when MAC limit is reached";
  //        type enumeration {
  //          enum "none" {
  //            description "Forward the packet";
  //          }
  //          enum "drop" {
  //            description "Drop packets and do not learn. Default is forward";
  //          }
  //        }
  //      }
  //    }
  //    container mac-ip-table-size {
  //      description "Size of MAC+IP bindings table";
  //      // uses apply-advanced;
  //      leaf limit {
  //        description "Maximum number of MAC+IP bindings";
  //        type union {
  //          type string {
  //            pattern "<.*>|$.*";
  //          }
  //          type uint32;
  //        }
  //      }
  //    }
  //    container interface-mac-limit {
  //      description "Maximum MAC address learned per interface";
  //      // uses apply-advanced;
  //      leaf limit {
  //        description "Maximum number of MAC addresses per interface";
  //        type union {
  //          type string {
  //            pattern "<.*>|$.*";
  //          }
  //          type uint32;
  //        }
  //      }
  //      leaf packet-action {
  //        description "Action when MAC limit is reached";
  //        type enumeration {
  //          enum "none" {
  //            description "Forward the packet";
  //          }
  //          enum "drop" {
  //            description "Drop packets and do not learn. Default is forward";
  //          }
  //          enum "log" {
  //            description "Do not drop the packet but generate an alarm, an SNMP trap or a system log entry";
  //          }
  //          enum "shutdown" {
  //            description "Disable the interface and generate an alarm, an SNMP trap or a system log entry";
  //          }
  //          enum "drop-and-log" {
  //            description "Drop the packet and generate an alarm, an SNMP trap or a system log entry";
  //          }
  //        }
  //      }
  //    }
  //    container interface-mac-ip-limit {
  //      description "Maximum MAC+IP bindings learned per interface";
  //      // uses apply-advanced;
  //      leaf limit {
  //        description "Maximum number of MAC+IP bindings per interface";
  //        type union {
  //          type string {
  //            pattern "<.*>|$.*";
  //          }
  //          type uint32;
  //        }
  //      }
  //    }
  //    container mac-move-limit {
  //      presence "enable mac-move-limit";
  //      description "Number of MAC movements allowed on this VLAN";
  //      // uses apply-advanced;
  //      choice limit-choice {
  //        case case_1 {
  //          leaf none {
  //            description "Disable mac-move-limit for this VLAN";
  //            type empty;
  //          }
  //        }
  //        case case_2 {
  //          leaf limit {
  //            description "Number of MAC movements allowed on this VLAN";
  //            type union {
  //              type string {
  //                pattern "<.*>|$.*";
  //              }
  //              type uint32 {
  //                range "1 .. 4294967295";
  //              }
  //            }
  //          }
  //        }
  //      }
  //      leaf packet-action {
  //        description "Action to be taken in case the MAC movement limit is exceeded";
  //        default "drop";
  //        type enumeration {
  //          enum "none" {
  //            description "Take no action";
  //          }
  //          enum "drop" {
  //            description "Drop the packet and do not generate an alarm";
  //          }
  //          enum "log" {
  //            description "Do not drop the packet but generate an alarm, an SNMP trap, or a system log entry.";
  //          }
  //          enum "shutdown" {
  //            description "Disable the interface and generate an alarm, an SNMP trap, or a system log entry.";
  //          }
  //          enum "drop-and-log" {
  //            description "Drop the packet and generate an alarm, an SNMP trap, or a system log entry.";
  //          }
  //          enum "vlan-member-shutdown" {
  //            description "Disable the interface of this VLAN";
  //          }
  //        }
  //      }
  //      list interface {
  //        key name;
  //        description "Interface that connect this site to the VPN";
  //        leaf name {
  //          description "Interface name";
  //          type union {
  //            type jt:interface-name;
  //            type string {
  //              pattern "<.*>|$.*";
  //            }
  //          }
  //        }
  //        // uses apply-advanced;
  //        leaf action-priority {
  //          description "Blocking priority of this interface on mac move detection";
  //          type union {
  //            type string {
  //              pattern "<.*>|$.*";
  //            }
  //            type uint32 {
  //              range "0 .. 7";
  //            }
  //          }
  //        }
  //      }
  //    }
  //    container mac-notification {
  //      presence "enable mac-notification";
  //      description "MAC notification options";
  //      // uses apply-advanced;
  //      leaf notification-interval {
  //        description "Interval for sending MAC notifications";
  //        default "30";
  //        units "seconds";
  //        type union {
  //          type string {
  //            pattern "<.*>|$.*";
  //          }
  //          type uint32 {
  //            range "1 .. 60";
  //          }
  //        }
  //      }
  //    }
  //    leaf mac-table-aging-time {
  //      description "Delay for discarding MAC address if no updates are received";
  //      units "seconds";
  //      type union {
  //        type string {
  //          pattern "<.*>|$.*";
  //        }
  //        type uint32;
  //      }
  //    }
  //    leaf no-mac-learning {
  //      description "Disable dynamic MAC address learning";
  //      type empty;
  //    }
  //    leaf no-normalization {
  //      description "Disable vlan id normalization for interfaces";
  //      type empty;
  //    }
  //    leaf drop-unknown-mac-ip {
  //      description "Drop unknown MAC-IP traffic";
  //      type empty;
  //    }
  //    leaf mac-statistics {
  //      description "Enable MAC address statistics";
  //      type empty;
  //    }
  //    container mib {
  //      presence "enable mib";
  //      description "Snmp mib options";
  //      // uses apply-advanced;
  //      container dot1q-mib {
  //        presence "enable dot1q-mib";
  //        description "Dot1q MIB configuration options";
  //        // uses apply-advanced;
  //        leaf port-list {
  //          description "Port list for staticegressports and staticuntaggedports MIB";
  //          type enumeration {
  //            enum "bit-map" {
  //              description "Port list is represented in bit-map format";
  //            }
  //            enum "string" {
  //              description "Port list is represented in string format";
  //            }
  //          }
  //        }
  //      }
  //    }
  //    container static-rvtep-mac {
  //      description "Configure Static MAC and remote VxLAN tunnel endpoint entries";
  //      // uses apply-advanced;
  //      list mac {
  //        key "mac_addr remote-vtep";
  //        description "Unicast MAC address";
  //        leaf mac_addr {
  //          type jt:mac-unicast;
  //        }
  //        leaf remote-vtep {
  //          description "Configure static remote VXLAN tunnel endpoints";
  //          type jt:ipaddr;
  //        }
  //      }
  //    }
  //    container network-isolation-profile {
  //      description "Network isolation configuration";
  //      // uses apply-advanced;
  //      list group {
  //        key name;
  //        description "Network isolation group";
  //        leaf name {
  //          description "Group name";
  //          type string;
  //        }
  //        // uses apply-advanced;
  //      }
  //    }
  //    list interface {
  //      key name;
  //      description "Interface that connect this site to the VPN";
  //      leaf name {
  //        description "Interface name";
  //        type union {
  //          type jt:interface-name;
  //          type string {
  //            pattern "<.*>|$.*";
  //          }
  //        }
  //      }
  //      // uses apply-advanced;
  //      container mac-learning-priority {
  //        description "MAC learning priority for the interface";
  //        // uses apply-advanced;
  //        leaf priority {
  //          description "Mac learning priority for the interface";
  //          type union {
  //            type string {
  //              pattern "<.*>|$.*";
  //            }
  //            type uint32 {
  //              range "1 .. 65535";
  //            }
  //          }
  //        }
  //        leaf packet-action {
  //          default "discard";
  //          type enumeration {
  //            enum "discard" {
  //              description "Discard the packets and do not learn. Default is forward";
  //            }
  //            enum "forward" {
  //              description "Forward the packet";
  //            }
  //          }
  //        }
  //      }
  //      container interface-mac-limit {
  //        description "Maximum number of MAC addresses learned on the interface";
  //        // uses apply-advanced;
  //        leaf limit {
  //          description "Maximum number of MAC addresses per interface";
  //          type union {
  //            type string {
  //              pattern "<.*>|$.*";
  //            }
  //            type uint32;
  //          }
  //        }
  //        leaf disable {
  //          description "Disable interface for interface-mac-limit";
  //          type empty;
  //        }
  //        leaf packet-action {
  //          description "Action when MAC limit is reached";
  //          type enumeration {
  //            enum "none" {
  //              description "Forward the packet";
  //            }
  //            enum "drop" {
  //              description "Drop packets and do not learn. Default is forward";
  //            }
  //            enum "log" {
  //              description "Do not drop the packet but generate an alarm, an SNMP trap or a system log entry";
  //            }
  //            enum "shutdown" {
  //              description "Disable the interface and generate an alarm, an SNMP trap or a system log entry";
  //            }
  //            enum "drop-and-log" {
  //              description "Drop the packet and generate an alarm, an SNMP trap or a system log entry";
  //            }
  //          }
  //        }
  //      }
  //      leaf action-priority {
  //        description "Blocking priority of this interface on mac move detection";
  //        type union {
  //          type string {
  //            pattern "<.*>|$.*";
  //          }
  //          type uint32 {
  //            range "0 .. 8";
  //          }
  //        }
  //      }
  //      list static-mac {
  //        key name;
  //        ordered-by user;
  //        description "Static MAC addresses assigned to this interface";
  //        leaf name {
  //          description "MAC address";
  //          type jt:mac-addr;
  //        }
  //        // uses apply-advanced;
  //        list vlan-id {
  //          key name;
  //          ordered-by user;
  //          description "VLAN ID of learning VLAN";
  //          leaf name {
  //            description "Learning VLAN";
  //            type union {
  //              type string {
  //                pattern "<.*>|$.*";
  //              }
  //              type uint32 {
  //                range "0 .. 4094";
  //              }
  //            }
  //          }
  //          // uses apply-advanced;
  //        }
  //      }
  //      list static-mac-ip {
  //        key name;
  //        ordered-by user;
  //        description "Static MAC-IP address bindings";
  //        leaf name {
  //          description "IP address";
  //          type jt:ipaddr;
  //        }
  //        // uses apply-advanced;
  //        leaf-list mac-address {
  //          ordered-by user;
  //          description "MAC address";
  //          type jt:mac-unicast;
  //          max-elements 8;
  //        }
  //        leaf router {
  //          description "Router flag for ipv6 addresses";
  //          type empty;
  //        }
  //      }
  //      container interface-mac-ip-limit {
  //        description "Maximum number of MAC+IP bindings learned on the interface";
  //        // uses apply-advanced;
  //        leaf limit {
  //          description "Maximum number of MAC+IP bindings per interface";
  //          type union {
  //            type string {
  //              pattern "<.*>|$.*";
  //            }
  //            type uint32;
  //          }
  //        }
  //      }
  //      leaf no-mac-learning {
  //        description "Disable dynamic MAC address learning";
  //        type empty;
  //      }
  //      leaf mac-pinning {
  //        description "Enable MAC pinning";
  //        type empty;
  //      }
  //    }
  //  }
   grouping juniper-protocols-bgp {
     // uses apply-advanced;
     container path-selection {
       description "Configure path selection strategy";
       // uses apply-advanced;
       leaf l2vpn-use-bgp-rules {
         description "Use standard BGP rules during L2VPN path selection";
         type empty;
       }
       leaf cisco-non-deterministic {
         description "Use Cisco IOS nondeterministic path selection algorithm";
         type empty;
       }
       leaf always-compare-med {
         description "Always compare MED values, regardless of neighbor AS";
         type empty;
       }
       container med-plus-igp {
         presence "enable med-plus-igp";
         description "Add IGP cost to next-hop to MED before comparing MED values";
         // uses apply-advanced;
         leaf med-multiplier {
           description "Multiplier for MED";
           default "1";
           type union {
             type string {
               pattern "<.*>|$.*";
             }
             type uint16 {
               range "1 .. 1000";
             }
           }
         }
         leaf igp-multiplier {
           description "Multiplier for IGP cost to next-hop";
           default "1";
           type union {
             type string {
               pattern "<.*>|$.*";
             }
             type uint16 {
               range "1 .. 1000";
             }
           }
         }
       }
       leaf external-router-id {
         description "Compare router ID on BGP externals";
         type empty;
       }
       leaf as-path-ignore {
         description "Ignore AS path comparison during path selection";
         type empty;
       }
     }
     container accept-prpd-connection {
       presence "enable accept-prpd-connection";
       description "Enable BGP to accept PRPD connections";
     }
     container global-load-balancing {
       presence "enable global-load-balancing";
       description "Enable global load balancing";
       // uses apply-advanced;
       leaf helper-only {
         description "Work as helper role only";
         type empty;
       }
       leaf load-balancer-only {
         description "Work as load balancer role only";
         type empty;
       }
     }
     leaf advertise-from-main-vpn-tables {
       description "Advertise VPN routes from bgp.Xvpn.0 tables in master instance";
       type empty;
     }
     leaf stale-labels-holddown-period {
       description "Duration (sec) MPLS labels allocated by BGP are kept after they go stale";
       type union {
         type string {
           pattern "<.*>|$.*";
         }
         type int32 {
           range "1 .. 600";
         }
       }
     }
     leaf holddown-all-stale-labels {
       description "Hold all BGP stale-labels, facilitating make-before-break for new label advertisements";
       type empty;
     }
     container egress-te-backup-paths {
       description "Backup-path for Egress-TE peer interface failure";
       // uses apply-advanced;
       list template {
         key name;
         description "Backup-path template";
         leaf name {
           description "Name of Egress-TE backup path";
           type string {
           }
         }
         // uses apply-advanced;
         list peer {
           key name;
           ordered-by user;
           description "Egress peer TE backup exit path";
           leaf name {
             description "Address of BGP peer to use as backup next-hop";
             type jt:ipaddr;
           }
           // uses apply-advanced;
         }
         container remote-nexthop {
           description "Resolve and use tunnel to this next-hop as backup path";
           // uses apply-advanced;
           leaf remote-nh-addr {
             description "Address of remote-nexthop to use as backup path";
             type jt:ipaddr;
           }
         }
         container ip-forward {
           presence "enable ip-forward";
           description "Use IP-forward backup path for Egress TE";
           // uses apply-advanced;
           leaf rti-name {
             description "Routing-instance to use as IP forward backup-path";
             type string {
             }
           }
         }
       }
     }
     leaf sr-preference-override {
       description "Replace received segment routing traffic engineering preference value with override value";
       type union {
         type uint32;
         type string {
           pattern "<.*>|$.*";
         }
       }
     }
     leaf vpn-apply-export {
       description "Apply BGP export policy when exporting VPN routes";
       type empty;
     }
     container family {
       description "Protocol family for NLRIs in updates";
       // uses apply-advanced;
       container inet {
         description "IPv4 NLRI parameters";
         // uses apply-advanced;
         container labeled-unicast {
           description "Include labeled unicast NLRI";
           presence "enable labeled-unicast";
           uses bgp-afi-labeled;
         }
        //  container segment-routing-te {
        //    description "Include segment-routing TE policy";
        //    presence "enable segment-routing-te";
        //    uses bgp-afi-srte;
        //  }
        //  container transport {
        //    description "Include Classful Transport NLRI";
        //    presence "enable transport";
        //    uses bgp-afi-inet-transport;
        //  }
         container unicast {
           description "Include unicast NLRI";
           presence "enable unicast";
           uses bgp-afi-topo;
         }
        //  container multicast {
        //    description "Include multicast NLRI";
        //    presence "enable multicast";
        //    uses bgp-afi-default;
        //  }
        //  container flow {
        //    description "Include flow NLRI";
        //    presence "enable flow";
        //    uses bgp-afi-flow-with-redirect-ip-action;
        //  }
         container any {
           description "Include unicast or multicast NLRI";
           presence "enable any";
           uses bgp-afi-default;
         }
       }
       container inet-vpn {
         description "IPv4 Layer 3 VPN NLRI parameters";
         // uses apply-advanced;
         container unicast {
           description "Include unicast NLRI";
           presence "enable unicast";
           uses bgp-afi-l3vpn;
         }
        //  container multicast {
        //    description "Include multicast NLRI";
        //    presence "enable multicast";
        //    uses bgp-afi-vpn;
        //  }
        //  container flow {
        //    description "Include flow VPN NLRI";
        //    presence "enable flow";
        //    uses bgp-afi-flow-with-redirect-ip-action;
        //  }
         container any {
           description "Include unicast or multicast NLRI";
           presence "enable any";
           uses bgp-afi-vpn;
         }
       }
      //  container inet6 {
      //    description "IPv6 NLRI parameters";
      //    // uses apply-advanced;
      //    container labeled-unicast {
      //      description "Include labeled unicast NLRI";
      //      presence "enable labeled-unicast";
      //      uses bgp-afi-inet6-labeled;
      //    }
      //    container segment-routing-te {
      //      description "Include segment-routing TE policy";
      //      presence "enable segment-routing-te";
      //      uses bgp-afi-srte;
      //    }
      //    container transport {
      //      description "Include Classful Transport NLRI";
      //      presence "enable transport";
      //      uses bgp-afi-inet6-transport;
      //    }
      //    container unicast {
      //      description "Include unicast NLRI";
      //      presence "enable unicast";
      //      uses bgp-afi-topo;
      //    }
      //    container multicast {
      //      description "Include multicast NLRI";
      //      presence "enable multicast";
      //      uses bgp-afi-default;
      //    }
      //    container flow {
      //      description "Include flow NLRI";
      //      presence "enable flow";
      //      uses bgp-afi-flow;
      //    }
      //    container any {
      //      description "Include unicast or multicast NLRI";
      //      presence "enable any";
      //      uses bgp-afi-default;
      //    }
      //  }
      //  container inet6-vpn {
      //    description "IPv6 Layer 3 VPN NLRI parameters";
      //    // uses apply-advanced;
      //    container unicast {
      //      description "Include unicast NLRI";
      //      presence "enable unicast";
      //      uses bgp-afi-l3vpn;
      //    }
      //    container multicast {
      //      description "Include multicast NLRI";
      //      presence "enable multicast";
      //      uses bgp-afi-vpn;
      //    }
      //    container flow {
      //      description "Include flow VPN NLRI";
      //      presence "enable flow";
      //      uses bgp-afi-flow;
      //    }
      //    container any {
      //      description "Include unicast or multicast NLRI";
      //      presence "enable any";
      //      uses bgp-afi-vpn;
      //    }
      //  }
      //  container iso-vpn {
      //    description "ISO Layer 3 VPN NLRI parameters";
      //    // uses apply-advanced;
      //    container unicast {
      //      description "Include unicast NLRI";
      //      presence "enable unicast";
      //      uses bgp-afi-vpn-protection;
      //    }
      //  }
      //  container l2vpn {
      //    description "MPLS-based Layer 2 VPN and VPLS NLRI parameters";
      //    // uses apply-advanced;
      //    container auto-discovery-only {
      //      description "Include auto-discovery NLRI for LDP Layer 2 VPN and VPLS";
      //      presence "enable auto-discovery-only";
      //      uses bgp-afi-default;
      //    }
      //    container auto-discovery-mspw {
      //      description "Include auto-discovery NLRI for LDP Signalled MultiSegment PW";
      //      presence "enable auto-discovery-mspw";
      //      uses bgp-afi-default;
      //    }
      //    container signaling {
      //      description "Include Layer 2 VPN and VPLS signaling NLRI";
      //      presence "enable signaling";
      //      uses bgp-afi-l2vpn;
      //    }
      //  }
      //  container evpn {
      //    description "EVPN NLRI parameters";
      //    // uses apply-advanced;
      //    container signaling {
      //      description "Include EVPN signaling NLRI";
      //      presence "enable signaling";
      //      uses bgp-afi-default;
      //    }
      //  }
      //  container inet-mvpn {
      //    description "IPv4 MVPN NLRI parameters";
      //    // uses apply-advanced;
      //    container signaling {
      //      description "Include IPv4 multicast VPN signaling NLRI";
      //      presence "enable signaling";
      //      uses bgp-afi-default;
      //    }
      //  }
      //  container inet6-mvpn {
      //    description "IPv6 MVPN NLRI parameters";
      //    // uses apply-advanced;
      //    container signaling {
      //      description "Include IPv6 multicast VPN signaling NLRI";
      //      presence "enable signaling";
      //      uses bgp-afi-default;
      //    }
      //  }
      //  container inet-mdt {
      //    description "IPv4 Multicast Distribution Tree (MDT) NLRI parameters";
      //    // uses apply-advanced;
      //    container signaling {
      //      description "Include IPv4 multicast VPN auto-discovery NLRI";
      //      presence "enable signaling";
      //      uses bgp-afi-default;
      //    }
      //  }
      //  container traffic-engineering {
      //    description "Traffic Engineering (BGP-TE) NLRI parameters";
      //    // uses apply-advanced;
      //    container unicast {
      //      description "Include BGP-TE NLRI";
      //      presence "enable unicast";
      //      uses bgp-afi-default;
      //    }
      //  }
       container route-target {
         presence "enable route-target";
         description "Route target NLRI used for VPN route filtering";
         // uses apply-advanced;
         container prefix-limit {
           description "Limit maximum number of prefixes from a peer";
           uses bgpaf-prefix-limit;
         }
         container accepted-prefix-limit {
           description "Limit maximum number of prefixes accepted from a peer";
           uses bgpaf-accepted-prefix-limit;
         }
         container proxy-generate {
           presence "enable proxy-generate";
           description "Generate route target NLRI for peers that don't support it";
           // uses apply-advanced;
           leaf-list route-target-policy {
             ordered-by user;
             description "Limit VPN routes that are used to generate proxy route-target filters";
             type jt:policy-algebra;
           }
         }
         leaf external-paths {
           description "Number of external paths accepted for route filtering";
           type union {
             type string {
               pattern "<.*>|$.*";
             }
             type uint32 {
               range "1 .. 256";
             }
           }
         }
         leaf advertise-default {
           description "Advertise default and suppress more specific routes";
           type empty;
         }
         leaf damping {
           description "Enable route flap damping";
           type empty;
         }
         container graceful-restart {
           description "BGP graceful restart options";
           uses bgp-af-gr;
         }
         leaf local-ipv4-address {
           description "Local IPv4 address";
           type jt:ipv4addr;
         }
        //  container nexthop-resolution {
        //    description "Configure nexthop resolution properties";
        //    // uses apply-advanced;
        //    leaf no-resolution {
        //      description "Consider nexthop good without resolution attempt";
        //      type empty;
        //    }
        //  }
        //  container output-queue-priority {
        //    description "Default output-queue to assign updates to";
        //    uses bgp-output-queue-priority-class;
        //  }
        //  container route-refresh-priority {
        //    description "Default output-queue to assign route refreshes to";
        //    uses bgp-output-queue-priority-class;
        //  }
        //  container withdraw-priority {
        //    description "Default output-queue to assign withdrawn routes to";
        //    uses bgp-output-queue-priority-class;
        //  }
       }
      //  container fabric {
      //    description "Fabric NLRI parameters";
      //    status deprecated;
      //    // uses apply-advanced;
      //    container unicast {
      //      description "Include unicast NLRI";
      //      presence "enable unicast";
      //      uses bgp-afi-default;
      //    }
      //  }
      //  container bridge {
      //    description "Bridge NLRI parameters";
      //    status deprecated;
      //    // uses apply-advanced;
      //    container unicast {
      //      description "Include unicast NLRI";
      //      presence "enable unicast";
      //      uses bgp-afi-default;
      //    }
      //  }
      //  container bridge-vpn {
      //    description "Bridge VPN NLRI parameters";
      //    status deprecated;
      //    // uses apply-advanced;
      //    container unicast {
      //      description "Include unicast NLRI";
      //      presence "enable unicast";
      //      uses bgp-afi-vpn;
      //    }
      //  }
      //  container fabric-vpn {
      //    description "Fabric VPN NLRI parameters";
      //    status deprecated;
      //    // uses apply-advanced;
      //    container unicast {
      //      description "Include unicast NLRI";
      //      presence "enable unicast";
      //      uses bgp-afi-vpn;
      //    }
      //  }
      //  container inet-bgpmcast {
      //    description "IPv4 BGPMCAST NLRI parameters";
      //    // uses apply-advanced;
      //    container signaling {
      //      description "Include IPv4 BGP multicast signaling NLRI";
      //      presence "enable signaling";
      //      uses bgp-afi-default;
      //    }
      //  }
      //  container inet6-bgpmcast {
      //    description "IPv6 BGPMCAST NLRI parameters";
      //    // uses apply-advanced;
      //    container signaling {
      //      description "Include IPv6 BGP multicast signaling NLRI";
      //      presence "enable signaling";
      //      uses bgp-afi-default;
      //    }
      //  }
     }
    //  container egress-te {
    //    presence "enable egress-te";
    //    description "Use Egress Peering traffic engineering";
    //    // uses apply-advanced;
    //    leaf install-address {
    //      description "Address to use in egress-te created inet route";
    //      type jt:ipaddr;
    //    }
    //    container rib {
    //      description "Select primary table for Egress-TE routes";
    //      // uses apply-advanced;
    //      leaf inet.0 {
    //        description "Install Egress-TE routes in inet.0";
    //        type empty;
    //      }
    //      leaf inet6.0 {
    //        description "Install Egress-TE routes in inet6.0";
    //        type empty;
    //      }
    //    }
    //    leaf no-install {
    //      description "Avoid installation to FIB or resolving over";
    //      type empty;
    //    }
    //    leaf-list import {
    //      ordered-by user;
    //      description "Import policy to set attributes";
    //      type jt:policy-algebra;
    //    }
    //    leaf backup-path {
    //      description "The 'egress-te-backup-paths template' to use for this peer";
    //      type string {
    //      }
    //    }
    //  }
    //  leaf advertise-prefix-sid {
    //    description "Advertise prefix sid to E-BGP peers";
    //    type empty;
    //  }
    //  leaf accept-prefix-sid {
    //    description "Accept prefix sid from E-BGP peers";
    //    type empty;
    //  }
    //  leaf advertise-srgb {
    //    description "Advertise SRGB TLV";
    //    type empty;
    //  }
    //  leaf tcp-connect-port {
    //    description "TCP port number to connect with peer on";
    //    type union {
    //      type string {
    //        pattern "<.*>|$.*";
    //      }
    //      type uint16 {
    //        range "1 .. 65535";
    //      }
    //    }
    //  }
    //  leaf egress-te-sid-stats {
    //    description "Create BGP-Peer-SID sensor";
    //    type empty;
    //  }
    //  list egress-te-set-segment {
    //    key name;
    //    ordered-by user;
    //    description "Configure BGP-Peer-Set segment";
    //    leaf name {
    //      description "The BGP-Peer-Set segment name";
    //      type string {
    //      }
    //    }
    //    // uses apply-advanced;
    //    container label {
    //      description "BGP-Peer-Set SID label from static label pool";
    //      // uses apply-advanced;
    //      leaf label-value {
    //        description "BGP-Peer-Set SID label value from static label pool";
    //        type union {
    //          type string {
    //            pattern "<.*>|$.*";
    //          }
    //          type uint32 {
    //            range "16 .. 1048575";
    //          }
    //        }
    //      }
    //    }
    //    container egress-te-backup-segment {
    //      description "Backup segment for FRR";
    //      // uses apply-advanced;
    //      container label {
    //        description "Backup segment label from static label pool";
    //        // uses apply-advanced;
    //        leaf label-value {
    //          description "Backup segment label value from static label pool";
    //          type union {
    //            type string {
    //              pattern "<.*>|$.*";
    //            }
    //            type uint32 {
    //              range "16 .. 1048575";
    //            }
    //          }
    //        }
    //      }
    //    }
    //    container egress-te-backup-ip-forward {
    //      presence "enable egress-te-backup-ip-forward";
    //      description "Use IP-forward backup path for Egress TE";
    //      // uses apply-advanced;
    //      leaf instance-name {
    //        description "Routing-instance to use as IP forward backup-path";
    //        type string {
    //        }
    //      }
    //    }
    //  }
     list group {
       key name;
       ordered-by user;
       description "Define a peer group";
       leaf name {
         description "Group name";
         type string;
       }
       // uses apply-advanced;
       leaf type {
         description "Type of peer group";
         type enumeration {
           enum "internal" {
             description "IBGP group";
           }
           enum "external" {
             description "EBGP group";
           }
         }
       }
       leaf protocol {
         description "IGP to use to resolve the next hop";
         status deprecated;
         type enumeration {
           enum "rip" {
             description "Use RIP to resolve the BGP next hop";
             status deprecated;
           }
           enum "ospf" {
             description "Use OSPF to resolve the BGP next hop";
             status deprecated;
           }
           enum "isis" {
             description "Use IS-IS to resolve the BGP next hop";
             status deprecated;
           }
         }
       }
      //  container traceoptions {
      //    description "Trace options for BGP";
      //    // uses apply-advanced;
      //    container file {
      //      description "Trace file options";
      //      leaf filename {
      //        description "Name of file in which to write trace information";
      //        type string {
      //          length "1 .. 1024";
      //        }
      //      }
      //      leaf replace {
      //        description "Replace trace file rather than appending to it";
      //        status deprecated;
      //        type empty;
      //      }
      //      leaf size {
      //        description "Maximum trace file size";
      //        type string;
      //      }
      //      leaf files {
      //        description "Maximum number of trace files";
      //        default "10";
      //        type union {
      //          type string {
      //            pattern "<.*>|$.*";
      //          }
      //          type uint32 {
      //            range "2 .. 1000";
      //          }
      //        }
      //      }
      //      leaf no-stamp {
      //        description "Do not timestamp trace file";
      //        status deprecated;
      //        type empty;
      //      }
      //      choice world-readable-choice {
      //        leaf world-readable {
      //          description "Allow any user to read the log file";
      //          type empty;
      //        }
      //        leaf no-world-readable {
      //          description "Don't allow any user to read the log file";
      //          type empty;
      //        }
      //      }
      //    }
      //    list flag {
      //      key name;
      //      ordered-by user;
      //      description "Tracing parameters";
      //      leaf name {
      //        type enumeration {
      //          enum "damping" {
      //            description "Trace BGP damping information";
      //          }
      //          enum "packets" {
      //            description "Trace all BGP protocol packets";
      //          }
      //          enum "open" {
      //            description "Trace BGP open packets";
      //          }
      //          enum "update" {
      //            description "Trace BGP update packets";
      //          }
      //          enum "keepalive" {
      //            description "Trace BGP keepalive packets";
      //          }
      //          enum "refresh" {
      //            description "Trace BGP refresh packets";
      //          }
      //          enum "nsr-synchronization" {
      //            description "Trace NSR synchronization events";
      //          }
      //          enum "bfd" {
      //            description "Trace BFD events";
      //          }
      //          enum "4byte-as" {
      //            description "Trace 4 byte AS events";
      //          }
      //          enum "add-path" {
      //            description "Trace add-path events";
      //          }
      //          enum "graceful-restart" {
      //            description "Trace Graceful Restart events";
      //          }
      //          enum "egress-te" {
      //            description "Egress Peering Traffic-Engineering events";
      //          }
      //          enum "thread-io" {
      //            description "Trace threaded I/O processing";
      //          }
      //          enum "sharding" {
      //            description "Trace BGP rib sharding";
      //          }
      //          enum "glb" {
      //            description "Trace BGP global-load-balancing";
      //          }
      //          enum "thread-update-io" {
      //            description "Trace threaded update I/O processing";
      //          }
      //          enum "route-validation" {
      //            description "Trace route validation";
      //          }
      //          enum "ipsec" {
      //            description "Trace ipsec";
      //          }
      //          enum "route" {
      //            description "Trace routing information";
      //          }
      //          enum "normal" {
      //            description "Trace normal events";
      //          }
      //          enum "general" {
      //            description "Trace general events";
      //          }
      //          enum "state" {
      //            description "Trace state transitions";
      //          }
      //          enum "policy" {
      //            description "Trace policy processing";
      //          }
      //          enum "task" {
      //            description "Trace routing protocol task processing";
      //          }
      //          enum "timer" {
      //            description "Trace routing protocol timer processing";
      //          }
      //          enum "all" {
      //            description "Trace everything";
      //          }
      //        }
      //      }
      //      leaf send {
      //        description "Trace transmitted packets";
      //        type empty;
      //      }
      //      leaf receive {
      //        description "Trace received packets";
      //        type empty;
      //      }
      //      leaf detail {
      //        description "Trace detailed information";
      //        type empty;
      //      }
      //      leaf disable {
      //        description "Disable this trace flag";
      //        type empty;
      //      }
      //      container filter {
      //        description "Filter to apply to this flag";
      //        presence "enable filter";
      //        uses bgp_filter_obj;
      //      }
      //    }
      //  }
       leaf description {
         description "Text description";
         type string {
           length "1 .. 255";
         }
       }
       container metric-out {
         description "Route metric sent in MED";
         choice metric_param {
           case case_1 {
             leaf metric-value {
               description "Metric value";
               type union {
                 type string {
                   pattern "<.*>|$.*";
                 }
                 type uint32 {
                   range "0 .. 4294967295";
                 }
               }
             }
           }
           case case_2 {
             container minimum-igp {
               presence "enable minimum-igp";
               description "Track the minimum IGP metric";
               leaf metric-offset {
                 description "Metric offset for MED";
                 type union {
                   type int32;
                   type string {
                     pattern "<.*>|$.*";
                   }
                 }
               }
             }
           }
           case case_3 {
             container igp {
               presence "enable igp";
               description "Track the IGP metric";
               leaf metric-offset {
                 description "Metric offset for MED";
                 type union {
                   type int32;
                   type string {
                     pattern "<.*>|$.*";
                   }
                 }
               }
               leaf delay-med-update {
                 description "Delay updating MED when IGP metric increases";
                 type empty;
               }
             }
           }
           case case_4 {
             container effective-aigp {
               presence "enable effective-aigp";
               description "Track the effective AIGP metric";
               leaf metric-offset {
                 description "Metric offset for MED";
                 type union {
                   type int32;
                   type string {
                     pattern "<.*>|$.*";
                   }
                 }
               }
             }
           }
           case case_5 {
             container minimum-effective-aigp {
               presence "enable minimum-effective-aigp";
               description "Track the minimum effective AIGP metric";
               leaf metric-offset {
                 description "Metric offset for MED";
                 type union {
                   type int32;
                   type string {
                     pattern "<.*>|$.*";
                   }
                 }
               }
             }
           }
         }
       }
       container multihop {
         presence "enable multihop";
         description "Configure an EBGP multihop session";
         // uses apply-advanced;
         leaf ttl {
           description "TTL value for the session";
           type union {
             type string {
               pattern "<.*>|$.*";
             }
             type uint8 {
               range "1 .. 255";
             }
           }
         }
         leaf no-nexthop-change {
           description "Do not change next hop to self in advertisements";
           type empty;
         }
       }
       container ebgp-community-cleanup {
         presence "enable ebgp-community-cleanup";
         description "Community specific cleanup for eBGP peers";
         // uses apply-advanced;
         leaf origin-validation {
           description "Origin Validation State receive behavior";
           type enumeration {
             enum "accept" {
               description "Accept Origin Validation State Community";
             }
             enum "reject" {
               description "Reject Origin Validation State Community";
             }
           }
         }
       }
       leaf route-server-client {
         description "Enable route server client behavior";
         type empty;
       }
       leaf accept-remote-nexthop {
         description "Allow import policy to specify a non-directly connected next-hop";
         type empty;
       }
       leaf preference {
         description "Preference value";
         type union {
           type uint32;
           type string {
             pattern "<.*>|$.*";
           }
         }
       }
       leaf local-preference {
         description "Value of LOCAL_PREF path attribute";
         type union {
           type uint32;
           type string {
             pattern "<.*>|$.*";
           }
         }
       }
       leaf local-address {
         description "Address of local end of BGP session";
         type jt:ipaddr;
       }
       leaf local-interface {
         description "Local interface for IPv6 link local EBGP peering";
         type union {
           type jt:interface-name;
           type string {
             pattern "<.*>|$.*";
           }
         }
       }
       leaf forwarding-context {
         description "Routing-instance used for data-forwarding and transport-session";
         type string {
         }
       }
       leaf hold-time {
         description "Hold time used when negotiating with a peer";
         type union {
           type string {
             pattern "<.*>|$.*";
           }
           type uint32 {
             range "0 .. 65535";
           }
         }
       }
       leaf minimum-hold-time {
         description "Minimum hold time accepted from the peer";
         type union {
           type string {
             pattern "<.*>|$.*";
           }
           type uint32 {
             range "3 .. 65535";
           }
         }
       }
       leaf passive {
         description "Do not send open messages to a peer";
         type empty;
       }
       leaf advertise-inactive {
         description "Advertise inactive routes";
         type empty;
       }
       choice advertise-peer-as-choice {
         leaf advertise-peer-as {
           description "Advertise routes received from the same autonomous system";
           type empty;
         }
         leaf no-advertise-peer-as {
           description "Don't advertise routes received from the same autonomous system";
           type empty;
         }
       }
       container advertise-external {
         presence "enable advertise-external";
         description "Advertise best external routes";
         leaf conditional {
           description "Route matches active route upto med-comparison rule";
           type empty;
         }
       }
       leaf keep {
         description "How to retain routes in the routing table";
         type enumeration {
           enum "all" {
             description "Retain all routes";
           }
           enum "none" {
             description "Retain no routes";
           }
         }
       }
       leaf rfc6514-compliant-safi129 {
         description "Compliant with RFC6514 SAFI129 format";
         type empty;
       }
       leaf no-aggregator-id {
         description "Set router ID in aggregator path attribute to 0";
         type empty;
       }
       leaf mtu-discovery {
         description "Enable TCP path MTU discovery";
         type empty;
       }
       leaf enforce-first-as {
         description "Enforce first AS in AS-path is the neighbor's AS";
         type empty;
       }
       leaf out-delay {
         description "How long before exporting routes from routing table";
         type union {
           type string {
             pattern "<.*>|$.*";
           }
           type uint32 {
             range "0 .. 65535";
           }
         }
       }
       leaf ttl {
         description "TTL value for the single-hop peer";
         type enumeration {
           enum "1" {
           }
           enum "255" {
           }
         }
       }
       leaf log-updown {
         description "Log a message for peer state transitions";
         type empty;
       }
       leaf damping {
         description "Enable route flap damping";
         type empty;
       }
       leaf-list import {
         ordered-by user;
         description "Import policy";
         type jt:policy-algebra;
       }
       leaf-list nlri {
         ordered-by user;
         description "NLRI type to include in updates";
         status deprecated;
         type enumeration {
           enum "unicast" {
             description "Include unicast NLRI";
             status deprecated;
           }
           enum "multicast" {
             description "Include multicast NLRI";
             status deprecated;
           }
           enum "any" {
             description "Include any kind of NLRI";
             status deprecated;
           }
         }
       }
       container bgp-error-tolerance {
         presence "enable bgp-error-tolerance";
         description "Handle BGP malformed updates softly";
         // uses apply-advanced;
         leaf malformed-update-log-interval {
           description "Time used when logging malformed update";
           default "300";
           units "seconds";
           type union {
             type string {
               pattern "<.*>|$.*";
             }
             type uint32 {
               range "10 .. 65535";
             }
           }
         }
         choice malformed-routes-limit-choice {
           case case_1 {
             leaf malformed-route-limit {
               description "Maximum number of malformed routes from a peer";
               default "1000";
               type union {
                 type string {
                   pattern "<.*>|$.*";
                 }
                 type uint32 {
                   range "0 .. 4294967295";
                 }
               }
             }
           }
           case case_2 {
             leaf no-malformed-route-limit {
               description "No malformed route limit";
               type empty;
             }
           }
         }
       }
       container family {
         description "Protocol family for NLRIs in updates";
         // uses apply-advanced;
         container inet {
           description "IPv4 NLRI parameters";
           // uses apply-advanced;
           container labeled-unicast {
             description "Include labeled unicast NLRI";
             presence "enable labeled-unicast";
             uses bgp-afi-labeled;
           }
          //  container segment-routing-te {
          //    description "Include segment-routing TE policy";
          //    presence "enable segment-routing-te";
          //    uses bgp-afi-srte;
          //  }
          //  container transport {
          //    description "Include Classful Transport NLRI";
          //    presence "enable transport";
          //    uses bgp-afi-inet-transport;
          //  }
           container unicast {
             description "Include unicast NLRI";
             presence "enable unicast";
             uses bgp-afi-topo;
           }
          //  container multicast {
          //    description "Include multicast NLRI";
          //    presence "enable multicast";
          //    uses bgp-afi-default;
          //  }
          //  container flow {
          //    description "Include flow NLRI";
          //    presence "enable flow";
          //    uses bgp-afi-flow-with-redirect-ip-action;
          //  }
           container any {
             description "Include unicast or multicast NLRI";
             presence "enable any";
             uses bgp-afi-default;
           }
         }
         container inet-vpn {
           description "IPv4 Layer 3 VPN NLRI parameters";
           // uses apply-advanced;
           container unicast {
             description "Include unicast NLRI";
             presence "enable unicast";
             uses bgp-afi-l3vpn;
           }
          //  container multicast {
          //    description "Include multicast NLRI";
          //    presence "enable multicast";
          //    uses bgp-afi-vpn;
          //  }
          //  container flow {
          //    description "Include flow VPN NLRI";
          //    presence "enable flow";
          //    uses bgp-afi-flow-with-redirect-ip-action;
          //  }
           container any {
             description "Include unicast or multicast NLRI";
             presence "enable any";
             uses bgp-afi-vpn;
           }
         }
        //  container inet6 {
        //    description "IPv6 NLRI parameters";
        //    // uses apply-advanced;
        //    container labeled-unicast {
        //      description "Include labeled unicast NLRI";
        //      presence "enable labeled-unicast";
        //      uses bgp-afi-inet6-labeled;
        //    }
        //    container segment-routing-te {
        //      description "Include segment-routing TE policy";
        //      presence "enable segment-routing-te";
        //      uses bgp-afi-srte;
        //    }
        //    container transport {
        //      description "Include Classful Transport NLRI";
        //      presence "enable transport";
        //      uses bgp-afi-inet6-transport;
        //    }
        //    container unicast {
        //      description "Include unicast NLRI";
        //      presence "enable unicast";
        //      uses bgp-afi-topo;
        //    }
        //    container multicast {
        //      description "Include multicast NLRI";
        //      presence "enable multicast";
        //      uses bgp-afi-default;
        //    }
        //    container flow {
        //      description "Include flow NLRI";
        //      presence "enable flow";
        //      uses bgp-afi-flow;
        //    }
        //    container any {
        //      description "Include unicast or multicast NLRI";
        //      presence "enable any";
        //      uses bgp-afi-default;
        //    }
        //  }
        //  container inet6-vpn {
        //    description "IPv6 Layer 3 VPN NLRI parameters";
        //    // uses apply-advanced;
        //    container unicast {
        //      description "Include unicast NLRI";
        //      presence "enable unicast";
        //      uses bgp-afi-l3vpn;
        //    }
        //    container multicast {
        //      description "Include multicast NLRI";
        //      presence "enable multicast";
        //      uses bgp-afi-vpn;
        //    }
        //    container flow {
        //      description "Include flow VPN NLRI";
        //      presence "enable flow";
        //      uses bgp-afi-flow;
        //    }
        //    container any {
        //      description "Include unicast or multicast NLRI";
        //      presence "enable any";
        //      uses bgp-afi-vpn;
        //    }
        //  }
        //  container iso-vpn {
        //    description "ISO Layer 3 VPN NLRI parameters";
        //    // uses apply-advanced;
        //    container unicast {
        //      description "Include unicast NLRI";
        //      presence "enable unicast";
        //      uses bgp-afi-vpn-protection;
        //    }
        //  }
        //  container l2vpn {
        //    description "MPLS-based Layer 2 VPN and VPLS NLRI parameters";
        //    // uses apply-advanced;
        //    container auto-discovery-only {
        //      description "Include auto-discovery NLRI for LDP Layer 2 VPN and VPLS";
        //      presence "enable auto-discovery-only";
        //      uses bgp-afi-default;
        //    }
        //    container auto-discovery-mspw {
        //      description "Include auto-discovery NLRI for LDP Signalled MultiSegment PW";
        //      presence "enable auto-discovery-mspw";
        //      uses bgp-afi-default;
        //    }
        //    container signaling {
        //      description "Include Layer 2 VPN and VPLS signaling NLRI";
        //      presence "enable signaling";
        //      uses bgp-afi-l2vpn;
        //    }
        //  }
        //  container evpn {
        //    description "EVPN NLRI parameters";
        //    // uses apply-advanced;
        //    container signaling {
        //      description "Include EVPN signaling NLRI";
        //      presence "enable signaling";
        //      uses bgp-afi-default;
        //    }
        //  }
        //  container inet-mvpn {
        //    description "IPv4 MVPN NLRI parameters";
        //    // uses apply-advanced;
        //    container signaling {
        //      description "Include IPv4 multicast VPN signaling NLRI";
        //      presence "enable signaling";
        //      uses bgp-afi-default;
        //    }
        //  }
        //  container inet6-mvpn {
        //    description "IPv6 MVPN NLRI parameters";
        //    // uses apply-advanced;
        //    container signaling {
        //      description "Include IPv6 multicast VPN signaling NLRI";
        //      presence "enable signaling";
        //      uses bgp-afi-default;
        //    }
        //  }
        //  container inet-mdt {
        //    description "IPv4 Multicast Distribution Tree (MDT) NLRI parameters";
        //    // uses apply-advanced;
        //    container signaling {
        //      description "Include IPv4 multicast VPN auto-discovery NLRI";
        //      presence "enable signaling";
        //      uses bgp-afi-default;
        //    }
        //  }
        //  container traffic-engineering {
        //    description "Traffic Engineering (BGP-TE) NLRI parameters";
        //    // uses apply-advanced;
        //    container unicast {
        //      description "Include BGP-TE NLRI";
        //      presence "enable unicast";
        //      uses bgp-afi-default;
        //    }
        //  }
         container route-target {
           presence "enable route-target";
           description "Route target NLRI used for VPN route filtering";
           // uses apply-advanced;
           container prefix-limit {
             description "Limit maximum number of prefixes from a peer";
             uses bgpaf-prefix-limit;
           }
           container accepted-prefix-limit {
             description "Limit maximum number of prefixes accepted from a peer";
             uses bgpaf-accepted-prefix-limit;
           }
          //  container proxy-generate {
          //    presence "enable proxy-generate";
          //    description "Generate route target NLRI for peers that don't support it";
          //    // uses apply-advanced;
          //    leaf-list route-target-policy {
          //      ordered-by user;
          //      description "Limit VPN routes that are used to generate proxy route-target filters";
          //      type jt:policy-algebra;
          //    }
          //  }
           leaf external-paths {
             description "Number of external paths accepted for route filtering";
             type union {
               type string {
                 pattern "<.*>|$.*";
               }
               type uint32 {
                 range "1 .. 256";
               }
             }
           }
           leaf advertise-default {
             description "Advertise default and suppress more specific routes";
             type empty;
           }
           leaf damping {
             description "Enable route flap damping";
             type empty;
           }
           container graceful-restart {
             description "BGP graceful restart options";
             uses bgp-af-gr;
           }
           leaf local-ipv4-address {
             description "Local IPv4 address";
             type jt:ipv4addr;
           }
           container nexthop-resolution {
             description "Configure nexthop resolution properties";
             // uses apply-advanced;
             leaf no-resolution {
               description "Consider nexthop good without resolution attempt";
               type empty;
             }
           }
          //  container output-queue-priority {
          //    description "Default output-queue to assign updates to";
          //    uses bgp-output-queue-priority-class;
          //  }
          //  container route-refresh-priority {
          //    description "Default output-queue to assign route refreshes to";
          //    uses bgp-output-queue-priority-class;
          //  }
          //  container withdraw-priority {
          //    description "Default output-queue to assign withdrawn routes to";
          //    uses bgp-output-queue-priority-class;
          //  }
         }
        //  container fabric {
        //    description "Fabric NLRI parameters";
        //    status deprecated;
        //    // uses apply-advanced;
        //    container unicast {
        //      description "Include unicast NLRI";
        //      presence "enable unicast";
        //      uses bgp-afi-default;
        //    }
        //  }
        //  container bridge {
        //    description "Bridge NLRI parameters";
        //    status deprecated;
        //    // uses apply-advanced;
        //    container unicast {
        //      description "Include unicast NLRI";
        //      presence "enable unicast";
        //      uses bgp-afi-default;
        //    }
        //  }
        //  container bridge-vpn {
        //    description "Bridge VPN NLRI parameters";
        //    status deprecated;
        //    // uses apply-advanced;
        //    container unicast {
        //      description "Include unicast NLRI";
        //      presence "enable unicast";
        //      uses bgp-afi-vpn;
        //    }
        //  }
        //  container fabric-vpn {
        //    description "Fabric VPN NLRI parameters";
        //    status deprecated;
        //    // uses apply-advanced;
        //    container unicast {
        //      description "Include unicast NLRI";
        //      presence "enable unicast";
        //      uses bgp-afi-vpn;
        //    }
        //  }
        //  container inet-bgpmcast {
        //    description "IPv4 BGPMCAST NLRI parameters";
        //    // uses apply-advanced;
        //    container signaling {
        //      description "Include IPv4 BGP multicast signaling NLRI";
        //      presence "enable signaling";
        //      uses bgp-afi-default;
        //    }
        //  }
        //  container inet6-bgpmcast {
        //    description "IPv6 BGPMCAST NLRI parameters";
        //    // uses apply-advanced;
        //    container signaling {
        //      description "Include IPv6 BGP multicast signaling NLRI";
        //      presence "enable signaling";
        //      uses bgp-afi-default;
        //    }
        //  }
       }
       leaf authentication-key {
         description "MD5 authentication key";
         type string {
           length "1 .. 126";
         }
       }
       leaf authentication-algorithm {
         description "Authentication algorithm name";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
      //  leaf tcpao-auth-mismatch {
      //    description "Continue without TCP-AO if any one TCP endpoint does not have TCP-AO configured";
      //    type enumeration {
      //      enum "allow-without-tcpao" {
      //        description "Allow the connection establishment without TCP-AO";
      //      }
      //    }
      //  }
      //  leaf authentication-key-chain {
      //    description "Key chain name";
      //    type string {
      //      length "1 .. 128";
      //    }
      //  }
       leaf-list export {
         ordered-by user;
         description "Export policy";
         type jt:policy-algebra;
       }
       container remove-private {
         presence "enable remove-private";
         description "Remove well-known private AS numbers";
         // uses apply-advanced;
         container all {
           presence "enable all";
           description "Remove all private AS numbers and do not stop at the first public AS number";
           container replace {
             presence "enable replace";
             description "Replace private AS numbers with the BGP Group's local AS number";
             leaf nearest {
               description "Use closest public AS number to replace a private AS number";
               type empty;
             }
           }
         }
         leaf no-peer-loop-check {
           description "Remove peer loop-check";
           type empty;
         }
       }
       leaf cluster {
         description "Cluster identifier";
         type jt:areaid;
       }
       leaf no-client-reflect {
         description "Disable intracluster route redistribution";
         type empty;
       }
       leaf peer-as {
         description " Autonomous system number in plain number or 'higher 16bits'.'Lower 16 bits' (asdot notation) format";
         type string {
         }
       }
       container local-as {
         description "Local autonomous system number";
         leaf as-number {
           description " Autonomous system number in plain number or 'higher 16bits'.'Lower 16 bits' (asdot notation) format";
           type string {
           }
         }
         leaf loops {
           description "Maximum number of times this AS can be in an AS path";
           type union {
             type string {
               pattern "<.*>|$.*";
             }
             type int32 {
               range "1 .. 10";
             }
           }
         }
         leaf private {
           description "Hide this local AS in paths learned from this peering";
           type empty;
         }
         leaf alias {
           description "Treat this AS as an alias to the system AS";
           type empty;
         }
         leaf no-prepend-global-as {
           description "Do not prepend global autonomous-system number in advertised paths";
           type empty;
         }
       }
      //  leaf ipsec-sa {
      //    description "IPSec SA name";
      //    type string {
      //      length "1 .. 32";
      //    }
      //  }
       container graceful-shutdown {
         description "BGP peer graceful shutdown option";
         // uses apply-advanced;
         container receiver {
           presence "enable receiver";
           description "BGP peer graceful-shutdown receiver";
           // uses apply-advanced;
           leaf disable {
             description "Disable graceful-shutdown receiver";
             type empty;
           }
           leaf local-preference {
             description "Value of receiver LOCAL_PREF path attribute";
             type union {
               type uint32;
               type string {
                 pattern "<.*>|$.*";
               }
             }
           }
         }
         container sender {
           presence "enable sender";
           description "BGP peer graceful-shutdown sender";
           // uses apply-advanced;
           leaf local-preference {
             description "Value of sender LOCAL_PREF path attribute";
             type union {
               type uint32;
               type string {
                 pattern "<.*>|$.*";
               }
             }
           }
         }
       }
       container shutdown {
         presence "enable shutdown";
         description "Shutdown";
         // uses apply-advanced;
         leaf notify-message {
           description "Notification message";
           type string;
         }
       }
       leaf unconfigured-peer-graceful-restart {
         description "BGP unconfigured peer graceful restart options";
         type empty;
       }
       container graceful-restart {
         presence "enable graceful-restart";
         description "BGP graceful restart options";
         // uses apply-advanced;
         choice enable-disable {
           case case_1 {
             leaf disable {
               description "Disable graceful restart";
               type empty;
             }
           }
         }
         leaf restart-time {
           description "Restart time used when negotiating with a peer";
           type union {
             type string {
               pattern "<.*>|$.*";
             }
             type uint32 {
               range "1 .. 1800";
             }
           }
         }
         leaf stale-routes-time {
           description "Maximum time for which stale routes are kept";
           type union {
             type string {
               pattern "<.*>|$.*";
             }
             type uint32 {
               range "1 .. 1800";
             }
           }
         }
         container long-lived {
           description "Long-lived graceful restart options";
           // uses apply-advanced;
           container receiver {
             description "Long-lived graceful restart receiver (helper) options";
             // uses apply-advanced;
             choice enable-disable {
               case case_1 {
                 leaf disable {
                   description "Disable receiver (helper) functionality";
                   type empty;
                 }
               }
             }
           }
           container advertise-to-non-llgr-neighbor {
             presence "enable advertise-to-non-llgr-neighbor";
             description "Advertise stale routes to non-LLGR neighbors";
             // uses apply-advanced;
             leaf omit-no-export {
               description "Do not attach no-export community to stale routes";
               type empty;
             }
           }
         }
         leaf disable-notification-extensions {
           description "Disable notification extensions";
           type empty;
         }
         leaf forwarding-state-bit {
           description "Control forwarding-state flag negotiation";
           type enumeration {
             enum "as-rr-client" {
               description "As for a route reflector client";
             }
             enum "from-fib" {
               description "Always use state of associated FIB(s)";
             }
           }
         }
         leaf dont-help-shared-fate-bfd-down {
           description "Honor BFD-Down(C=0) if GR-restart not in progress";
           type empty;
         }
       }
       leaf include-mp-next-hop {
         description "Include NEXT-HOP attribute in multiprotocol updates";
         type empty;
       }
       leaf disable-4byte-as {
         description "Disable 4 byte AS capability advertisement";
         type empty;
       }
      //  container idle-after-switch-over {
      //    description "Stop peer session from coming up after nonstop-routing switch-over";
      //    choice idle-interval {
      //      case case_1 {
      //        leaf forever {
      //          description "Idle the peer until the user intervenes";
      //          type empty;
      //        }
      //      }
      //      case case_2 {
      //        leaf timeout {
      //          description "Timeout value, in seconds, for starting peer after switch over";
      //          type union {
      //            type string {
      //              pattern "<.*>|$.*";
      //            }
      //            type uint32 {
      //              range "1 .. 4294967295";
      //            }
      //          }
      //        }
      //      }
      //    }
      //  }
      //  container outbound-route-filter {
      //    description "Dynamically negotiated cooperative route filtering";
      //    // uses apply-advanced;
      //    leaf bgp-orf-cisco-mode {
      //      description "Using BGP ORF capability code 130 and Prefix ORF type 128";
      //      type empty;
      //    }
      //    container extended-community {
      //      description "Extended community filtering";
      //      status deprecated;
      //      // uses apply-advanced;
      //      choice accept-choice {
      //        leaf accept {
      //          description "Honor remote requests for extended community ORF";
      //          type empty;
      //        }
      //        leaf no-accept {
      //          description "Don't honor remote requests for extended community ORF";
      //          type empty;
      //        }
      //      }
      //      leaf vrf-filter {
      //        description "Request remote filtering using locally configured VRF import targets";
      //        type empty;
      //      }
      //    }
      //    container prefix-based {
      //      presence "enable prefix-based";
      //      description "Prefix-based outbound route filtering";
      //      // uses apply-advanced;
      //      container accept {
      //        presence "enable accept";
      //        description "Honor Prefix-based ORFs from remote peers";
      //        // uses apply-advanced;
      //        leaf inet {
      //          description "Honor IPv4 prefix filters";
      //          type empty;
      //        }
      //        leaf inet6 {
      //          description "Honor IPv6 prefix filters";
      //          type empty;
      //        }
      //      }
      //    }
      //  }
       container message-batching {
         description "DEPRECATED - Batching of outgoing messages";
         status deprecated;
         // uses apply-advanced;
         choice enable-disable {
           case case_1 {
             leaf enable {
               description "Enable parameter";
               type empty;
             }
           }
           case case_2 {
             leaf disable {
               description "Disable parameter";
               type empty;
             }
           }
         }
         leaf interval {
           description "DEPRECATED - Interval over which to batch messages";
           default "250";
           units "milliseconds";
           type union {
             type string {
               pattern "<.*>|$.*";
             }
             type uint32 {
               range "100 .. 1000";
             }
           }
         }
       }
       container multipath {
         presence "enable multipath";
         description "Allow load sharing among multiple BGP paths";
         // uses apply-advanced;
         leaf disable {
           description "Disable Multipath";
           type empty;
         }
         leaf multiple-as {
           description "Use paths received from different ASs";
           type empty;
         }
         leaf allow-protection {
           description "Allow protection for multipath legs";
           type empty;
         }
         leaf pause-computation-during-churn {
           description "Pause multipath job to absorb churn";
           type empty;
         }
         leaf list-nexthop {
           description "Use List-NH for homogenous nexthop-set also";
           type empty;
         }
         container allow-external-internal {
           presence "enable allow-external-internal";
           description "Allow multipath to mix EBGP and IBGP routes";
           // uses apply-advanced;
           leaf-list prefix-policy {
             ordered-by user;
             description "Policy to constrain prefixes that apply";
             type jt:policy-algebra;
           }
         }
       }
       leaf tcp-mss {
         description "Maximum TCP segment size";
         type union {
           type string {
             pattern "<.*>|$.*";
           }
           type uint32 {
             range "1 .. 4096";
           }
         }
       }
       leaf bgp-identifier {
         description "BGP Identifier";
         type jt:ipv4addr;
       }
       leaf tcp-aggressive-transmission {
         description "Enable aggressive transmission of pure TCP ACKs and retransmissions";
         type empty;
       }
      //  container bmp {
      //    description "Specific settings to override the routing-options settings";
      //    // uses apply-advanced;
      //    leaf monitor {
      //      description "Enable/Disable monitoring";
      //      type enumeration {
      //        enum "enable" {
      //          description "Enable monitoring of BGP peer(s)";
      //        }
      //        enum "disable" {
      //          description "Disable monitoring of BGP peer(s)";
      //        }
      //      }
      //    }
      //    container route-monitoring {
      //      description "Control route monitoring settings";
      //      // uses apply-advanced;
      //      leaf none {
      //        description "Do not send route monitoring messages";
      //        type empty;
      //      }
      //      container pre-policy {
      //        presence "enable pre-policy";
      //        description "Send pre-policy route monitoring messages";
      //        leaf exclude-non-feasible {
      //          description "Exclude looped routes, etc";
      //          type empty;
      //        }
      //      }
      //      container post-policy {
      //        presence "enable post-policy";
      //        description "Send post-policy route monitoring messages";
      //        leaf exclude-non-eligible {
      //          description "Exclude unresolved routes, etc.";
      //          type empty;
      //        }
      //      }
      //      container rib-out {
      //        presence "enable rib-out";
      //        description "Send adj-ribs-out route monitoring messages";
      //        leaf pre-policy {
      //          description "Send pre-policy adj-ribs-out route monitoring messages";
      //          type empty;
      //        }
      //        leaf post-policy {
      //          description "Send post-policy adj-ribs-out route monitoring messages";
      //          type empty;
      //        }
      //      }
      //    }
      //  }
       container advertise-bgp-static {
         presence "enable advertise-bgp-static";
         description "Advertise bgp-static routes";
         // uses apply-advanced;
         leaf-list policy {
           ordered-by user;
           description "Static route advertisement policy";
           type jt:policy-algebra;
         }
       }
       leaf add-path-display-ipv4-address {
         description "Display add-path path-id in IPv4 address format";
         type empty;
       }
       container domain-path-id {
         description "Domain path id attribute";
         // uses apply-advanced;
         leaf send {
           description "Allow sending domain path id attribute";
           type empty;
         }
         leaf receive {
           description "Allow receiving domain path id attribute";
           type empty;
         }
       }
       container bfd-liveness-detection {
         description "Bidirectional Forwarding Detection (BFD) options";
         // uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 9000";
             }
           }
         }
         choice adaptation-choice {
           case case_1 {
             leaf no-adaptation {
               description "Disable adaptation";
               type empty;
             }
           }
         }
         container transmit-interval {
           description "Transmit-interval options";
           // uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           // uses apply-advanced;
           leaf threshold {
             description "High detection-time triggering a trap";
             units "milliseconds";
             type union {
               type uint32;
               type string {
                 pattern "<.*>|$.*";
               }
             }
           }
         }
         container authentication {
           description "Authentication options";
           // uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         leaf session-mode {
           description "BFD single-hop or multihop session-mode";
           default "automatic";
           type enumeration {
             enum "automatic" {
               description "Choose session-mode automatically";
             }
             enum "single-hop" {
               description "Use single-hop";
             }
             enum "multihop" {
               description "Use multihop";
             }
           }
         }
         container echo {
           description "Echo mode parameters";
           // uses apply-advanced;
           leaf minimum-interval {
             description "Minimum transmit and receive interval";
             units "milliseconds";
             type union {
               type string {
                 pattern "<.*>|$.*";
               }
               type uint32 {
                 range "100 .. 255000";
               }
             }
           }
         }
         container echo-lite {
           description "Echo-lite more parameters";
           // uses apply-advanced;
           leaf minimum-interval {
             description "Minimum transmit and receive interval";
             units "milliseconds";
             type union {
               type string {
                 pattern "<.*>|$.*";
               }
               type uint32 {
                 range "100 .. 255000";
               }
             }
           }
         }
         container strict-bfd {
           presence "enable strict-bfd";
           description "Bgp session waits for bfd";
           // uses apply-advanced;
           leaf bfd-up-wait-interval {
             description "Time to wait for bfd to come up";
             units "seconds";
             type union {
               type string {
                 pattern "<.*>|$.*";
               }
               type uint32 {
                 range "10 .. 255";
               }
             }
           }
         }
         leaf holddown-interval {
           description "Time to hold the session-UP notification to the client";
           units "milliseconds";
           type union {
             type string {
               pattern "<.*>|$.*";
             }
             type uint32 {
               range "0 .. 255000";
             }
           }
         }
       }
       leaf as-override {
         description "Replace neighbor AS number with our AS number";
         type empty;
       }
       container link-bandwidth {
         description "Configure link-bandwidth options";
         // uses apply-advanced;
         container auto-sense {
           presence "enable auto-sense";
           // uses apply-advanced;
           leaf hold-down {
             description "Hold down in secs for link bandwidth auto-sense";
             type union {
               type string {
                 pattern "<.*>|$.*";
               }
               type uint32 {
                 range "0 .. 3600";
               }
             }
           }
         }
       }
       leaf-list allow {
         ordered-by user;
         description "Configure peer connections for specific networks";
         type jt:ipprefix;
       }
       list dynamic-neighbor {
         key name;
         ordered-by user;
         description "Configure peer options for specific networks";
         leaf name {
           description "Template name";
           type string;
         }
         // uses apply-advanced;
         leaf-list allow {
           ordered-by user;
           description "Configure peer connections for specific networks";
           type jt:ipprefix;
         }
         leaf peer-limit {
           description "Limit the number of peers for each subnet configured via dynamic-neighbor";
           type union {
             type string {
               pattern "<.*>|$.*";
             }
             type uint32 {
               range "0 .. 2048";
             }
           }
         }
         leaf authentication-key {
           description "MD5 authentication key";
           type string {
             length "1 .. 126";
           }
         }
         leaf authentication-algorithm {
           description "Authentication algorithm name";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-auth-mismatch {
           description "Continue without TCP-AO if any one TCP endpoint does not have TCP-AO configured";
           type enumeration {
             enum "allow-without-tcpao" {
               description "Allow the connection establishment without TCP-AO";
             }
           }
         }
         leaf authentication-key-chain {
           description "Key chain name";
           type string {
             length "1 .. 128";
           }
         }
         container peer-auto-discovery {
           description "Configure auto-discovery options for BGP neighbors";
           // uses apply-advanced;
           container family {
             description "Address family based neighbor auto-discovery parameters";
             container inet6 {
               // uses apply-advanced;
               choice auto-discovery-type {
                 case case_1 {
                   container ipv6-nd {
                     presence "enable ipv6-nd";
                     description "Use ipv6 neighbor discovery to learn neighbor address";
                   }
                 }
               }
             }
           }
           list interface {
             key name;
             leaf name {
               description "Configure interfaces over which to discover bgp neighbors";
               type union {
                 type jt:interface-name;
                 type string {
                   pattern "<.*>|$.*";
                 }
               }
             }
             // uses apply-advanced;
             choice enable-disable {
               case case_1 {
                 leaf disable {
                   description "Disable peer discovery on interface";
                   type empty;
                 }
               }
             }
           }
         }
       }
       container optimal-route-reflection {
         description "Enable optimal route reflection for this client group";
         // uses apply-advanced;
         leaf igp-primary {
           description "Primary node identifier for this client group";
           type jt:ipv4addr;
         }
         leaf igp-backup {
           description "Backup node identifier for this client group";
           type jt:ipv4addr;
         }
         leaf-list export {
           description "Optimal route reflection export policy";
           type jt:policy-algebra;
         }
       }
       leaf peer-as-list {
         description "Configure list of peer autonomous systems for unconfigured neighbors";
         type string;
       }
       leaf send-non-transitive-link-bandwidth {
         description "Allow sending non transitive link-bandwidth to EBGP peers";
         type empty;
       }
       leaf mvpn-iana-rt-import {
         description "Use IANA assigned rt-import type value for MVPN";
         status deprecated;
         type empty;
       }
       list neighbor {
         key name;
         ordered-by user;
         description "Configure a neighbor";
         leaf name {
           type jt:ipaddr-scoped;
         }
         // uses apply-advanced;
        //  container traceoptions {
        //    description "Trace options for BGP";
        //    // uses apply-advanced;
        //    container file {
        //      description "Trace file options";
        //      leaf filename {
        //        description "Name of file in which to write trace information";
        //        type string {
        //          length "1 .. 1024";
        //        }
        //      }
        //      leaf replace {
        //        description "Replace trace file rather than appending to it";
        //        status deprecated;
        //        type empty;
        //      }
        //      leaf size {
        //        description "Maximum trace file size";
        //        type string;
        //      }
        //      leaf files {
        //        description "Maximum number of trace files";
        //        default "10";
        //        type union {
        //          type string {
        //            pattern "<.*>|$.*";
        //          }
        //          type uint32 {
        //            range "2 .. 1000";
        //          }
        //        }
        //      }
        //      leaf no-stamp {
        //        description "Do not timestamp trace file";
        //        status deprecated;
        //        type empty;
        //      }
        //      choice world-readable-choice {
        //        leaf world-readable {
        //          description "Allow any user to read the log file";
        //          type empty;
        //        }
        //        leaf no-world-readable {
        //          description "Don't allow any user to read the log file";
        //          type empty;
        //        }
        //      }
        //    }
        //    list flag {
        //      key name;
        //      ordered-by user;
        //      description "Tracing parameters";
        //      leaf name {
        //        type enumeration {
        //          enum "damping" {
        //            description "Trace BGP damping information";
        //          }
        //          enum "packets" {
        //            description "Trace all BGP protocol packets";
        //          }
        //          enum "open" {
        //            description "Trace BGP open packets";
        //          }
        //          enum "update" {
        //            description "Trace BGP update packets";
        //          }
        //          enum "keepalive" {
        //            description "Trace BGP keepalive packets";
        //          }
        //          enum "refresh" {
        //            description "Trace BGP refresh packets";
        //          }
        //          enum "nsr-synchronization" {
        //            description "Trace NSR synchronization events";
        //          }
        //          enum "bfd" {
        //            description "Trace BFD events";
        //          }
        //          enum "4byte-as" {
        //            description "Trace 4 byte AS events";
        //          }
        //          enum "add-path" {
        //            description "Trace add-path events";
        //          }
        //          enum "graceful-restart" {
        //            description "Trace Graceful Restart events";
        //          }
        //          enum "egress-te" {
        //            description "Egress Peering Traffic-Engineering events";
        //          }
        //          enum "thread-io" {
        //            description "Trace threaded I/O processing";
        //          }
        //          enum "sharding" {
        //            description "Trace BGP rib sharding";
        //          }
        //          enum "glb" {
        //            description "Trace BGP global-load-balancing";
        //          }
        //          enum "thread-update-io" {
        //            description "Trace threaded update I/O processing";
        //          }
        //          enum "route-validation" {
        //            description "Trace route validation";
        //          }
        //          enum "ipsec" {
        //            description "Trace ipsec";
        //          }
        //          enum "route" {
        //            description "Trace routing information";
        //          }
        //          enum "normal" {
        //            description "Trace normal events";
        //          }
        //          enum "general" {
        //            description "Trace general events";
        //          }
        //          enum "state" {
        //            description "Trace state transitions";
        //          }
        //          enum "policy" {
        //            description "Trace policy processing";
        //          }
        //          enum "task" {
        //            description "Trace routing protocol task processing";
        //          }
        //          enum "timer" {
        //            description "Trace routing protocol timer processing";
        //          }
        //          enum "all" {
        //            description "Trace everything";
        //          }
        //        }
        //      }
        //      leaf send {
        //        description "Trace transmitted packets";
        //        type empty;
        //      }
        //      leaf receive {
        //        description "Trace received packets";
        //        type empty;
        //      }
        //      leaf detail {
        //        description "Trace detailed information";
        //        type empty;
        //      }
        //      leaf disable {
        //        description "Disable this trace flag";
        //        type empty;
        //      }
        //      container filter {
        //        description "Filter to apply to this flag";
        //        presence "enable filter";
        //        uses bgp_filter_obj;
        //      }
        //    }
        //  }
         leaf description {
           description "Text description";
           type string {
             length "1 .. 255";
           }
         }
         container metric-out {
           description "Route metric sent in MED";
           choice metric_param {
             case case_1 {
               leaf metric-value {
                 description "Metric value";
                 type union {
                   type string {
                     pattern "<.*>|$.*";
                   }
                   type uint32 {
                     range "0 .. 4294967295";
                   }
                 }
               }
             }
             case case_2 {
               container minimum-igp {
                 presence "enable minimum-igp";
                 description "Track the minimum IGP metric";
                 leaf metric-offset {
                   description "Metric offset for MED";
                   type union {
                     type int32;
                     type string {
                       pattern "<.*>|$.*";
                     }
                   }
                 }
               }
             }
             case case_3 {
               container igp {
                 presence "enable igp";
                 description "Track the IGP metric";
                 leaf metric-offset {
                   description "Metric offset for MED";
                   type union {
                     type int32;
                     type string {
                       pattern "<.*>|$.*";
                     }
                   }
                 }
                 leaf delay-med-update {
                   description "Delay updating MED when IGP metric increases";
                   type empty;
                 }
               }
             }
             case case_4 {
               container effective-aigp {
                 presence "enable effective-aigp";
                 description "Track the effective AIGP metric";
                 leaf metric-offset {
                   description "Metric offset for MED";
                   type union {
                     type int32;
                     type string {
                       pattern "<.*>|$.*";
                     }
                   }
                 }
               }
             }
             case case_5 {
               container minimum-effective-aigp {
                 presence "enable minimum-effective-aigp";
                 description "Track the minimum effective AIGP metric";
                 leaf metric-offset {
                   description "Metric offset for MED";
                   type union {
                     type int32;
                     type string {
                       pattern "<.*>|$.*";
                     }
                   }
                 }
               }
             }
           }
         }
         container multihop {
           presence "enable multihop";
           description "Configure an EBGP multihop session";
           // uses apply-advanced;
           leaf ttl {
             description "TTL value for the session";
             type union {
               type string {
                 pattern "<.*>|$.*";
               }
               type uint8 {
                 range "1 .. 255";
               }
             }
           }
           leaf no-nexthop-change {
             description "Do not change next hop to self in advertisements";
             type empty;
           }
         }
         container ebgp-community-cleanup {
           presence "enable ebgp-community-cleanup";
           description "Community specific cleanup for eBGP peers";
           // uses apply-advanced;
           leaf origin-validation {
             description "Origin Validation State receive behavior";
             type enumeration {
               enum "accept" {
                 description "Accept Origin Validation State Community";
               }
               enum "reject" {
                 description "Reject Origin Validation State Community";
               }
             }
           }
         }
         leaf route-server-client {
           description "Enable route server client behavior";
           type empty;
         }
         leaf accept-remote-nexthop {
           description "Allow import policy to specify a non-directly connected next-hop";
           type empty;
         }
         leaf preference {
           description "Preference value";
           type union {
             type uint32;
             type string {
               pattern "<.*>|$.*";
             }
           }
         }
         leaf local-preference {
           description "Value of LOCAL_PREF path attribute";
           type union {
             type uint32;
             type string {
               pattern "<.*>|$.*";
             }
           }
         }
         leaf local-address {
           description "Address of local end of BGP session";
           type jt:ipaddr;
         }
         leaf local-interface {
           description "Local interface for IPv6 link local EBGP peering";
           type union {
             type jt:interface-name;
             type string {
               pattern "<.*>|$.*";
             }
           }
         }
         leaf forwarding-context {
           description "Routing-instance used for data-forwarding and transport-session";
           type string {
           }
         }
         leaf hold-time {
           description "Hold time used when negotiating with a peer";
           type union {
             type string {
               pattern "<.*>|$.*";
             }
             type uint32 {
               range "0 .. 65535";
             }
           }
         }
         leaf minimum-hold-time {
           description "Minimum hold time accepted from the peer";
           type union {
             type string {
               pattern "<.*>|$.*";
             }
             type uint32 {
               range "3 .. 65535";
             }
           }
         }
         leaf passive {
           description "Do not send open messages to a peer";
           type empty;
         }
         leaf advertise-inactive {
           description "Advertise inactive routes";
           type empty;
         }
         choice advertise-peer-as-choice {
           leaf advertise-peer-as {
             description "Advertise routes received from the same autonomous system";
             type empty;
           }
           leaf no-advertise-peer-as {
             description "Don't advertise routes received from the same autonomous system";
             type empty;
           }
         }
         container advertise-external {
           presence "enable advertise-external";
           description "Advertise best external routes";
           leaf conditional {
             description "Route matches active route upto med-comparison rule";
             type empty;
           }
         }
         leaf keep {
           description "How to retain routes in the routing table";
           type enumeration {
             enum "all" {
               description "Retain all routes";
             }
             enum "none" {
               description "Retain no routes";
             }
           }
         }
         leaf rfc6514-compliant-safi129 {
           description "Compliant with RFC6514 SAFI129 format";
           type empty;
         }
         leaf no-aggregator-id {
           description "Set router ID in aggregator path attribute to 0";
           type empty;
         }
         leaf mtu-discovery {
           description "Enable TCP path MTU discovery";
           type empty;
         }
         leaf enforce-first-as {
           description "Enforce first AS in AS-path is the neighbor's AS";
           type empty;
         }
         leaf out-delay {
           description "How long before exporting routes from routing table";
           type union {
             type string {
               pattern "<.*>|$.*";
             }
             type uint32 {
               range "0 .. 65535";
             }
           }
         }
         leaf ttl {
           description "TTL value for the single-hop peer";
           type enumeration {
             enum "1" {
             }
             enum "255" {
             }
           }
         }
         leaf log-updown {
           description "Log a message for peer state transitions";
           type empty;
         }
         leaf damping {
           description "Enable route flap damping";
           type empty;
         }
         leaf-list import {
           ordered-by user;
           description "Import policy";
           type jt:policy-algebra;
         }
         leaf-list nlri {
           ordered-by user;
           description "NLRI type to include in updates";
           status deprecated;
           type enumeration {
             enum "unicast" {
               description "Include unicast NLRI";
               status deprecated;
             }
             enum "multicast" {
               description "Include multicast NLRI";
               status deprecated;
             }
             enum "any" {
               description "Include any kind of NLRI";
               status deprecated;
             }
           }
         }
         container bgp-error-tolerance {
           presence "enable bgp-error-tolerance";
           description "Handle BGP malformed updates softly";
           // uses apply-advanced;
           leaf malformed-update-log-interval {
             description "Time used when logging malformed update";
             default "300";
             units "seconds";
             type union {
               type string {
                 pattern "<.*>|$.*";
               }
               type uint32 {
                 range "10 .. 65535";
               }
             }
           }
           choice malformed-routes-limit-choice {
             case case_1 {
               leaf malformed-route-limit {
                 description "Maximum number of malformed routes from a peer";
                 default "1000";
                 type union {
                   type string {
                     pattern "<.*>|$.*";
                   }
                   type uint32 {
                     range "0 .. 4294967295";
                   }
                 }
               }
             }
             case case_2 {
               leaf no-malformed-route-limit {
                 description "No malformed route limit";
                 type empty;
               }
             }
           }
         }
         container family {
           description "Protocol family for NLRIs in updates";
           // uses apply-advanced;
           container inet {
             description "IPv4 NLRI parameters";
             // uses apply-advanced;
             container labeled-unicast {
               description "Include labeled unicast NLRI";
               presence "enable labeled-unicast";
               uses bgp-afi-labeled;
             }
            //  container segment-routing-te {
            //    description "Include segment-routing TE policy";
            //    presence "enable segment-routing-te";
            //    uses bgp-afi-srte;
            //  }
            //  container transport {
            //    description "Include Classful Transport NLRI";
            //    presence "enable transport";
            //    uses bgp-afi-inet-transport;
            //  }
             container unicast {
               description "Include unicast NLRI";
               presence "enable unicast";
               uses bgp-afi-topo;
             }
            //  container multicast {
            //    description "Include multicast NLRI";
            //    presence "enable multicast";
            //    uses bgp-afi-default;
            //  }
            //  container flow {
            //    description "Include flow NLRI";
            //    presence "enable flow";
            //    uses bgp-afi-flow-with-redirect-ip-action;
            //  }
             container any {
               description "Include unicast or multicast NLRI";
               presence "enable any";
               uses bgp-afi-default;
             }
           }
           container inet-vpn {
             description "IPv4 Layer 3 VPN NLRI parameters";
             // uses apply-advanced;
             container unicast {
               description "Include unicast NLRI";
               presence "enable unicast";
               uses bgp-afi-l3vpn;
             }
            //  container multicast {
            //    description "Include multicast NLRI";
            //    presence "enable multicast";
            //    uses bgp-afi-vpn;
            //  }
            //  container flow {
            //    description "Include flow VPN NLRI";
            //    presence "enable flow";
            //    uses bgp-afi-flow-with-redirect-ip-action;
            //  }
             container any {
               description "Include unicast or multicast NLRI";
               presence "enable any";
               uses bgp-afi-vpn;
             }
           }
          //  container inet6 {
          //    description "IPv6 NLRI parameters";
          //    // uses apply-advanced;
          //    container labeled-unicast {
          //      description "Include labeled unicast NLRI";
          //      presence "enable labeled-unicast";
          //      uses bgp-afi-inet6-labeled;
          //    }
          //    container segment-routing-te {
          //      description "Include segment-routing TE policy";
          //      presence "enable segment-routing-te";
          //      uses bgp-afi-srte;
          //    }
          //    container transport {
          //      description "Include Classful Transport NLRI";
          //      presence "enable transport";
          //      uses bgp-afi-inet6-transport;
          //    }
          //    container unicast {
          //      description "Include unicast NLRI";
          //      presence "enable unicast";
          //      uses bgp-afi-topo;
          //    }
          //    container multicast {
          //      description "Include multicast NLRI";
          //      presence "enable multicast";
          //      uses bgp-afi-default;
          //    }
          //    container flow {
          //      description "Include flow NLRI";
          //      presence "enable flow";
          //      uses bgp-afi-flow;
          //    }
          //    container any {
          //      description "Include unicast or multicast NLRI";
          //      presence "enable any";
          //      uses bgp-afi-default;
          //    }
          //  }
          //  container inet6-vpn {
          //    description "IPv6 Layer 3 VPN NLRI parameters";
          //    // uses apply-advanced;
          //    container unicast {
          //      description "Include unicast NLRI";
          //      presence "enable unicast";
          //      uses bgp-afi-l3vpn;
          //    }
          //    container multicast {
          //      description "Include multicast NLRI";
          //      presence "enable multicast";
          //      uses bgp-afi-vpn;
          //    }
          //    container flow {
          //      description "Include flow VPN NLRI";
          //      presence "enable flow";
          //      uses bgp-afi-flow;
          //    }
          //    container any {
          //      description "Include unicast or multicast NLRI";
          //      presence "enable any";
          //      uses bgp-afi-vpn;
          //    }
          //  }
          //  container iso-vpn {
          //    description "ISO Layer 3 VPN NLRI parameters";
          //    // uses apply-advanced;
          //    container unicast {
          //      description "Include unicast NLRI";
          //      presence "enable unicast";
          //      uses bgp-afi-vpn-protection;
          //    }
          //  }
          //  container l2vpn {
          //    description "MPLS-based Layer 2 VPN and VPLS NLRI parameters";
          //    // uses apply-advanced;
          //    container auto-discovery-only {
          //      description "Include auto-discovery NLRI for LDP Layer 2 VPN and VPLS";
          //      presence "enable auto-discovery-only";
          //      uses bgp-afi-default;
          //    }
          //    container auto-discovery-mspw {
          //      description "Include auto-discovery NLRI for LDP Signalled MultiSegment PW";
          //      presence "enable auto-discovery-mspw";
          //      uses bgp-afi-default;
          //    }
          //    container signaling {
          //      description "Include Layer 2 VPN and VPLS signaling NLRI";
          //      presence "enable signaling";
          //      uses bgp-afi-l2vpn;
          //    }
          //  }
          //  container evpn {
          //    description "EVPN NLRI parameters";
          //    // uses apply-advanced;
          //    container signaling {
          //      description "Include EVPN signaling NLRI";
          //      presence "enable signaling";
          //      uses bgp-afi-default;
          //    }
          //  }
          //  container inet-mvpn {
          //    description "IPv4 MVPN NLRI parameters";
          //    // uses apply-advanced;
          //    container signaling {
          //      description "Include IPv4 multicast VPN signaling NLRI";
          //      presence "enable signaling";
          //      uses bgp-afi-default;
          //    }
          //  }
          //  container inet6-mvpn {
          //    description "IPv6 MVPN NLRI parameters";
          //    // uses apply-advanced;
          //    container signaling {
          //      description "Include IPv6 multicast VPN signaling NLRI";
          //      presence "enable signaling";
          //      uses bgp-afi-default;
          //    }
          //  }
          //  container inet-mdt {
          //    description "IPv4 Multicast Distribution Tree (MDT) NLRI parameters";
          //    // uses apply-advanced;
          //    container signaling {
          //      description "Include IPv4 multicast VPN auto-discovery NLRI";
          //      presence "enable signaling";
          //      uses bgp-afi-default;
          //    }
          //  }
           container traffic-engineering {
             description "Traffic Engineering (BGP-TE) NLRI parameters";
             // uses apply-advanced;
             container unicast {
               description "Include BGP-TE NLRI";
               presence "enable unicast";
               uses bgp-afi-default;
             }
           }
           container route-target {
             presence "enable route-target";
             description "Route target NLRI used for VPN route filtering";
             // uses apply-advanced;
             container prefix-limit {
               description "Limit maximum number of prefixes from a peer";
               uses bgpaf-prefix-limit;
             }
             container accepted-prefix-limit {
               description "Limit maximum number of prefixes accepted from a peer";
               uses bgpaf-accepted-prefix-limit;
             }
             container proxy-generate {
               presence "enable proxy-generate";
               description "Generate route target NLRI for peers that don't support it";
               // uses apply-advanced;
               leaf-list route-target-policy {
                 ordered-by user;
                 description "Limit VPN routes that are used to generate proxy route-target filters";
                 type jt:policy-algebra;
               }
             }
             leaf external-paths {
               description "Number of external paths accepted for route filtering";
               type union {
                 type string {
                   pattern "<.*>|$.*";
                 }
                 type uint32 {
                   range "1 .. 256";
                 }
               }
             }
             leaf advertise-default {
               description "Advertise default and suppress more specific routes";
               type empty;
             }
             leaf damping {
               description "Enable route flap damping";
               type empty;
             }
             container graceful-restart {
               description "BGP graceful restart options";
               uses bgp-af-gr;
             }
             leaf local-ipv4-address {
               description "Local IPv4 address";
               type jt:ipv4addr;
             }
             container nexthop-resolution {
               description "Configure nexthop resolution properties";
               // uses apply-advanced;
               leaf no-resolution {
                 description "Consider nexthop good without resolution attempt";
                 type empty;
               }
             }
            //  container output-queue-priority {
            //    description "Default output-queue to assign updates to";
            //    uses bgp-output-queue-priority-class;
            //  }
            //  container route-refresh-priority {
            //    description "Default output-queue to assign route refreshes to";
            //    uses bgp-output-queue-priority-class;
            //  }
            //  container withdraw-priority {
            //    description "Default output-queue to assign withdrawn routes to";
            //    uses bgp-output-queue-priority-class;
            //  }
           }
          //  container fabric {
          //    description "Fabric NLRI parameters";
          //    status deprecated;
          //    // uses apply-advanced;
          //    container unicast {
          //      description "Include unicast NLRI";
          //      presence "enable unicast";
          //      uses bgp-afi-default;
          //    }
          //  }
          //  container bridge {
          //    description "Bridge NLRI parameters";
          //    status deprecated;
          //    // uses apply-advanced;
          //    container unicast {
          //      description "Include unicast NLRI";
          //      presence "enable unicast";
          //      uses bgp-afi-default;
          //    }
          //  }
          //  container bridge-vpn {
          //    description "Bridge VPN NLRI parameters";
          //    status deprecated;
          //    // uses apply-advanced;
          //    container unicast {
          //      description "Include unicast NLRI";
          //      presence "enable unicast";
          //      uses bgp-afi-vpn;
          //    }
          //  }
          //  container fabric-vpn {
          //    description "Fabric VPN NLRI parameters";
          //    status deprecated;
          //    // uses apply-advanced;
          //    container unicast {
          //      description "Include unicast NLRI";
          //      presence "enable unicast";
          //      uses bgp-afi-vpn;
          //    }
          //  }
          //  container inet-bgpmcast {
          //    description "IPv4 BGPMCAST NLRI parameters";
          //    // uses apply-advanced;
          //    container signaling {
          //      description "Include IPv4 BGP multicast signaling NLRI";
          //      presence "enable signaling";
          //      uses bgp-afi-default;
          //    }
          //  }
          //  container inet6-bgpmcast {
          //    description "IPv6 BGPMCAST NLRI parameters";
          //    // uses apply-advanced;
          //    container signaling {
          //      description "Include IPv6 BGP multicast signaling NLRI";
          //      presence "enable signaling";
          //      uses bgp-afi-default;
          //    }
          //  }
         }
         leaf authentication-key {
           description "MD5 authentication key";
           type string {
             length "1 .. 126";
           }
         }
         leaf authentication-algorithm {
           description "Authentication algorithm name";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
        //  leaf tcpao-auth-mismatch {
        //    description "Continue without TCP-AO if any one TCP endpoint does not have TCP-AO configured";
        //    type enumeration {
        //      enum "allow-without-tcpao" {
        //        description "Allow the connection establishment without TCP-AO";
        //      }
        //    }
        //  }
        //  leaf authentication-key-chain {
        //    description "Key chain name";
        //    type string {
        //      length "1 .. 128";
        //    }
        //  }
         leaf-list export {
           ordered-by user;
           description "Export policy";
           type jt:policy-algebra;
         }
         container remove-private {
           presence "enable remove-private";
           description "Remove well-known private AS numbers";
           // uses apply-advanced;
           container all {
             presence "enable all";
             description "Remove all private AS numbers and do not stop at the first public AS number";
             container replace {
               presence "enable replace";
               description "Replace private AS numbers with the BGP Group's local AS number";
               leaf nearest {
                 description "Use closest public AS number to replace a private AS number";
                 type empty;
               }
             }
           }
           leaf no-peer-loop-check {
             description "Remove peer loop-check";
             type empty;
           }
         }
         leaf cluster {
           description "Cluster identifier";
           type jt:areaid;
         }
         leaf no-client-reflect {
           description "Disable intracluster route redistribution";
           type empty;
         }
         leaf peer-as {
           description " Autonomous system number in plain number or 'higher 16bits'.'Lower 16 bits' (asdot notation) format";
           type string {
           }
         }
         container local-as {
           description "Local autonomous system number";
           leaf as-number {
             description " Autonomous system number in plain number or 'higher 16bits'.'Lower 16 bits' (asdot notation) format";
             type string {
             }
           }
           leaf loops {
             description "Maximum number of times this AS can be in an AS path";
             type union {
               type string {
                 pattern "<.*>|$.*";
               }
               type int32 {
                 range "1 .. 10";
               }
             }
           }
           leaf private {
             description "Hide this local AS in paths learned from this peering";
             type empty;
           }
           leaf alias {
             description "Treat this AS as an alias to the system AS";
             type empty;
           }
           leaf no-prepend-global-as {
             description "Do not prepend global autonomous-system number in advertised paths";
             type empty;
           }
         }
         leaf ipsec-sa {
           description "IPSec SA name";
           type string {
             length "1 .. 32";
           }
         }
         container graceful-shutdown {
           description "BGP peer graceful shutdown option";
           // uses apply-advanced;
           container receiver {
             presence "enable receiver";
             description "BGP peer graceful-shutdown receiver";
             // uses apply-advanced;
             leaf disable {
               description "Disable graceful-shutdown receiver";
               type empty;
             }
             leaf local-preference {
               description "Value of receiver LOCAL_PREF path attribute";
               type union {
                 type uint32;
                 type string {
                   pattern "<.*>|$.*";
                 }
               }
             }
           }
           container sender {
             presence "enable sender";
             description "BGP peer graceful-shutdown sender";
             // uses apply-advanced;
             leaf local-preference {
               description "Value of sender LOCAL_PREF path attribute";
               type union {
                 type uint32;
                 type string {
                   pattern "<.*>|$.*";
                 }
               }
             }
           }
         }
         container shutdown {
           presence "enable shutdown";
           description "Shutdown";
           // uses apply-advanced;
           leaf notify-message {
             description "Notification message";
             type string;
           }
         }
         leaf unconfigured-peer-graceful-restart {
           description "BGP unconfigured peer graceful restart options";
           type empty;
         }
         container graceful-restart {
           presence "enable graceful-restart";
           description "BGP graceful restart options";
           // uses apply-advanced;
           choice enable-disable {
             case case_1 {
               leaf disable {
                 description "Disable graceful restart";
                 type empty;
               }
             }
           }
           leaf restart-time {
             description "Restart time used when negotiating with a peer";
             type union {
               type string {
                 pattern "<.*>|$.*";
               }
               type uint32 {
                 range "1 .. 1800";
               }
             }
           }
           leaf stale-routes-time {
             description "Maximum time for which stale routes are kept";
             type union {
               type string {
                 pattern "<.*>|$.*";
               }
               type uint32 {
                 range "1 .. 1800";
               }
             }
           }
           container long-lived {
             description "Long-lived graceful restart options";
             // uses apply-advanced;
             container receiver {
               description "Long-lived graceful restart receiver (helper) options";
               // uses apply-advanced;
               choice enable-disable {
                 case case_1 {
                   leaf disable {
                     description "Disable receiver (helper) functionality";
                     type empty;
                   }
                 }
               }
             }
             container advertise-to-non-llgr-neighbor {
               presence "enable advertise-to-non-llgr-neighbor";
               description "Advertise stale routes to non-LLGR neighbors";
               // uses apply-advanced;
               leaf omit-no-export {
                 description "Do not attach no-export community to stale routes";
                 type empty;
               }
             }
           }
           leaf disable-notification-extensions {
             description "Disable notification extensions";
             type empty;
           }
           leaf forwarding-state-bit {
             description "Control forwarding-state flag negotiation";
             type enumeration {
               enum "as-rr-client" {
                 description "As for a route reflector client";
               }
               enum "from-fib" {
                 description "Always use state of associated FIB(s)";
               }
             }
           }
           leaf dont-help-shared-fate-bfd-down {
             description "Honor BFD-Down(C=0) if GR-restart not in progress";
             type empty;
           }
         }
         leaf include-mp-next-hop {
           description "Include NEXT-HOP attribute in multiprotocol updates";
           type empty;
         }
         leaf disable-4byte-as {
           description "Disable 4 byte AS capability advertisement";
           type empty;
         }
         container idle-after-switch-over {
           description "Stop peer session from coming up after nonstop-routing switch-over";
           choice idle-interval {
             case case_1 {
               leaf forever {
                 description "Idle the peer until the user intervenes";
                 type empty;
               }
             }
             case case_2 {
               leaf timeout {
                 description "Timeout value, in seconds, for starting peer after switch over";
                 type union {
                   type string {
                     pattern "<.*>|$.*";
                   }
                   type uint32 {
                     range "1 .. 4294967295";
                   }
                 }
               }
             }
           }
         }
         container outbound-route-filter {
           description "Dynamically negotiated cooperative route filtering";
           // uses apply-advanced;
           leaf bgp-orf-cisco-mode {
             description "Using BGP ORF capability code 130 and Prefix ORF type 128";
             type empty;
           }
           container extended-community {
             description "Extended community filtering";
             status deprecated;
             // uses apply-advanced;
             choice accept-choice {
               leaf accept {
                 description "Honor remote requests for extended community ORF";
                 type empty;
               }
               leaf no-accept {
                 description "Don't honor remote requests for extended community ORF";
                 type empty;
               }
             }
             leaf vrf-filter {
               description "Request remote filtering using locally configured VRF import targets";
               type empty;
             }
           }
           container prefix-based {
             presence "enable prefix-based";
             description "Prefix-based outbound route filtering";
             // uses apply-advanced;
             container accept {
               presence "enable accept";
               description "Honor Prefix-based ORFs from remote peers";
               // uses apply-advanced;
               leaf inet {
                 description "Honor IPv4 prefix filters";
                 type empty;
               }
               leaf inet6 {
                 description "Honor IPv6 prefix filters";
                 type empty;
               }
             }
           }
         }
         container message-batching {
           description "DEPRECATED - Batching of outgoing messages";
           status deprecated;
           // uses apply-advanced;
           choice enable-disable {
             case case_1 {
               leaf enable {
                 description "Enable parameter";
                 type empty;
               }
             }
             case case_2 {
               leaf disable {
                 description "Disable parameter";
                 type empty;
               }
             }
           }
           leaf interval {
             description "DEPRECATED - Interval over which to batch messages";
             default "250";
             units "milliseconds";
             type union {
               type string {
                 pattern "<.*>|$.*";
               }
               type uint32 {
                 range "100 .. 1000";
               }
             }
           }
         }
         container multipath {
           presence "enable multipath";
           description "Allow load sharing among multiple BGP paths";
           // uses apply-advanced;
           leaf disable {
             description "Disable Multipath";
             type empty;
           }
           leaf multiple-as {
             description "Use paths received from different ASs";
             type empty;
           }
           leaf allow-protection {
             description "Allow protection for multipath legs";
             type empty;
           }
           leaf pause-computation-during-churn {
             description "Pause multipath job to absorb churn";
             type empty;
           }
           leaf list-nexthop {
             description "Use List-NH for homogenous nexthop-set also";
             type empty;
           }
           container allow-external-internal {
             presence "enable allow-external-internal";
             description "Allow multipath to mix EBGP and IBGP routes";
             // uses apply-advanced;
             leaf-list prefix-policy {
               ordered-by user;
               description "Policy to constrain prefixes that apply";
               type jt:policy-algebra;
             }
           }
         }
         leaf tcp-mss {
           description "Maximum TCP segment size";
           type union {
             type string {
               pattern "<.*>|$.*";
             }
             type uint32 {
               range "1 .. 4096";
             }
           }
         }
         leaf bgp-identifier {
           description "BGP Identifier";
           type jt:ipv4addr;
         }
         leaf tcp-aggressive-transmission {
           description "Enable aggressive transmission of pure TCP ACKs and retransmissions";
           type empty;
         }
        //  container bmp {
        //    description "Specific settings to override the routing-options settings";
        //    // uses apply-advanced;
        //    leaf monitor {
        //      description "Enable/Disable monitoring";
        //      type enumeration {
        //        enum "enable" {
        //          description "Enable monitoring of BGP peer(s)";
        //        }
        //        enum "disable" {
        //          description "Disable monitoring of BGP peer(s)";
        //        }
        //      }
        //    }
        //    container route-monitoring {
        //      description "Control route monitoring settings";
        //      // uses apply-advanced;
        //      leaf none {
        //        description "Do not send route monitoring messages";
        //        type empty;
        //      }
        //      container pre-policy {
        //        presence "enable pre-policy";
        //        description "Send pre-policy route monitoring messages";
        //        leaf exclude-non-feasible {
        //          description "Exclude looped routes, etc";
        //          type empty;
        //        }
        //      }
        //      container post-policy {
        //        presence "enable post-policy";
        //        description "Send post-policy route monitoring messages";
        //        leaf exclude-non-eligible {
        //          description "Exclude unresolved routes, etc.";
        //          type empty;
        //        }
        //      }
        //      container rib-out {
        //        presence "enable rib-out";
        //        description "Send adj-ribs-out route monitoring messages";
        //        leaf pre-policy {
        //          description "Send pre-policy adj-ribs-out route monitoring messages";
        //          type empty;
        //        }
        //        leaf post-policy {
        //          description "Send post-policy adj-ribs-out route monitoring messages";
        //          type empty;
        //        }
        //      }
        //    }
        //  }
         container advertise-bgp-static {
           presence "enable advertise-bgp-static";
           description "Advertise bgp-static routes";
           // uses apply-advanced;
           leaf-list policy {
             ordered-by user;
             description "Static route advertisement policy";
             type jt:policy-algebra;
           }
         }
         leaf add-path-display-ipv4-address {
           description "Display add-path path-id in IPv4 address format";
           type empty;
         }
         container domain-path-id {
           description "Domain path id attribute";
           // uses apply-advanced;
           leaf send {
             description "Allow sending domain path id attribute";
             type empty;
           }
           leaf receive {
             description "Allow receiving domain path id attribute";
             type empty;
           }
         }
         container bfd-liveness-detection {
           description "Bidirectional Forwarding Detection (BFD) options";
           // uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 9000";
               }
             }
           }
           choice adaptation-choice {
             case case_1 {
               leaf no-adaptation {
                 description "Disable adaptation";
                 type empty;
               }
             }
           }
           container transmit-interval {
             description "Transmit-interval options";
             // uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             // uses apply-advanced;
             leaf threshold {
               description "High detection-time triggering a trap";
               units "milliseconds";
               type union {
                 type uint32;
                 type string {
                   pattern "<.*>|$.*";
                 }
               }
             }
           }
           container authentication {
             description "Authentication options";
             // uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf session-mode {
             description "BFD single-hop or multihop session-mode";
             default "automatic";
             type enumeration {
               enum "automatic" {
                 description "Choose session-mode automatically";
               }
               enum "single-hop" {
                 description "Use single-hop";
               }
               enum "multihop" {
                 description "Use multihop";
               }
             }
           }
           container echo {
             description "Echo mode parameters";
             // uses apply-advanced;
             leaf minimum-interval {
               description "Minimum transmit and receive interval";
               units "milliseconds";
               type union {
                 type string {
                   pattern "<.*>|$.*";
                 }
                 type uint32 {
                   range "100 .. 255000";
                 }
               }
             }
           }
           container echo-lite {
             description "Echo-lite more parameters";
             // uses apply-advanced;
             leaf minimum-interval {
               description "Minimum transmit and receive interval";
               units "milliseconds";
               type union {
                 type string {
                   pattern "<.*>|$.*";
                 }
                 type uint32 {
                   range "100 .. 255000";
                 }
               }
             }
           }
           container strict-bfd {
             presence "enable strict-bfd";
             description "Bgp session waits for bfd";
             // uses apply-advanced;
             leaf bfd-up-wait-interval {
               description "Time to wait for bfd to come up";
               units "seconds";
               type union {
                 type string {
                   pattern "<.*>|$.*";
                 }
                 type uint32 {
                   range "10 .. 255";
                 }
               }
             }
           }
           leaf holddown-interval {
             description "Time to hold the session-UP notification to the client";
             units "milliseconds";
             type union {
               type string {
                 pattern "<.*>|$.*";
               }
               type uint32 {
                 range "0 .. 255000";
               }
             }
           }
         }
         leaf as-override {
           description "Replace neighbor AS number with our AS number";
           type empty;
         }
         container link-bandwidth {
           description "Configure link-bandwidth options";
           // uses apply-advanced;
           container auto-sense {
             presence "enable auto-sense";
             // uses apply-advanced;
             leaf hold-down {
               description "Hold down in secs for link bandwidth auto-sense";
               type union {
                 type string {
                   pattern "<.*>|$.*";
                 }
                 type uint32 {
                   range "0 .. 3600";
                 }
               }
             }
           }
         }
         leaf no-global-load-balancing {
           description "Disable glabl load balancing";
           type empty;
         }
         container egress-te-node-segment {
           description "Configure BGP-Peer-Node segment";
           // uses apply-advanced;
           container label {
             description "BGP-Peer-Node SID label from static label pool";
             // uses apply-advanced;
             leaf label-value {
               description "BGP-Peer-Node SID label value from static label pool";
               type union {
                 type string {
                   pattern "<.*>|$.*";
                 }
                 type uint32 {
                   range "16 .. 1048575";
                 }
               }
             }
           }
           container egress-te-set {
             description "Configure as a member of a SET segment";
             // uses apply-advanced;
             leaf set-name {
               description "Set name";
               type string {
               }
             }
             leaf weight {
               description "Weight for set segment";
               type union {
                 type string {
                   pattern "<.*>|$.*";
                 }
                 type uint32 {
                   range "1 .. 255";
                 }
               }
             }
           }
           container egress-te-backup-segment {
             description "Backup segment for FRR";
             // uses apply-advanced;
             container label {
               description "Backup segment label from static label pool";
               // uses apply-advanced;
               leaf label-value {
                 description "Backup segment label value from static label pool";
                 type union {
                   type string {
                     pattern "<.*>|$.*";
                   }
                   type uint32 {
                     range "16 .. 1048575";
                   }
                 }
               }
             }
           }
           container egress-te-backup-ip-forward {
             presence "enable egress-te-backup-ip-forward";
             description "Use IP-forward backup path for Egress TE";
             // uses apply-advanced;
             leaf instance-name {
               description "Routing-instance to use as IP forward backup-path";
               type string {
               }
             }
           }
         }
         list egress-te-adj-segment {
           key name;
           description "Configure BGP-Peer-Adj segment";
           leaf name {
             description "The BGP-Adj-Set segment name";
             type string {
             }
           }
           // uses apply-advanced;
           container label {
             description "BGP-Peer-Adj SID label from static label pool";
             // uses apply-advanced;
             leaf label-value {
               description "BGP-Peer-Adj SID label value from static label pool";
               type union {
                 type string {
                   pattern "<.*>|$.*";
                 }
                 type uint32 {
                   range "16 .. 1048575";
                 }
               }
             }
           }
           container next-hop {
             description "Address of directly connected next-hop to use";
             // uses apply-advanced;
             leaf next-hop-addr {
               description "Address of directly connected next-hop";
               type jt:ipaddr;
             }
           }
          //  container egress-te-set {
          //    description "Configure as a member of a SET segment";
          //    // uses apply-advanced;
          //    leaf set-name {
          //      description "Set name";
          //      type string {
          //      }
          //    }
          //    leaf weight {
          //      description "Weight for set segment";
          //      type union {
          //        type string {
          //          pattern "<.*>|$.*";
          //        }
          //        type uint32 {
          //          range "1 .. 255";
          //        }
          //      }
          //    }
          //  }
          //  container egress-te-backup-segment {
          //    description "Backup segment for FRR";
          //    // uses apply-advanced;
          //    container label {
          //      description "Backup segment label from static label pool";
          //      // uses apply-advanced;
          //      leaf label-value {
          //        description "Backup segment label value from static label pool";
          //        type union {
          //          type string {
          //            pattern "<.*>|$.*";
          //          }
          //          type uint32 {
          //            range "16 .. 1048575";
          //          }
          //        }
          //      }
          //    }
          //  }
          //  container egress-te-backup-ip-forward {
          //    presence "enable egress-te-backup-ip-forward";
          //    description "Use IP-forward backup path for Egress TE";
          //    // uses apply-advanced;
          //    leaf instance-name {
          //      description "Routing-instance to use as IP forward backup-path";
          //      type string {
          //      }
          //    }
          //  }
          //  container te-link-attribute {
          //    presence "enable te-link-attribute";
          //    description "Link attribute";
          //    // uses apply-advanced;
          //    leaf te-metric {
          //      description "TE Metric value";
          //      default "1";
          //      type union {
          //        type string {
          //          pattern "<.*>|$.*";
          //        }
          //        type uint32 {
          //          range "1 .. 4294967295";
          //        }
          //      }
          //    }
          //    leaf igp-metric {
          //      description "IGP Metric value";
          //      default "1";
          //      type union {
          //        type string {
          //          pattern "<.*>|$.*";
          //        }
          //        type uint32 {
          //          range "1 .. 16777215";
          //        }
          //      }
          //    }
          //    leaf delay-metric {
          //      description "Delay Metric";
          //      units "microseconds";
          //      type union {
          //        type string {
          //          pattern "<.*>|$.*";
          //        }
          //        type uint32 {
          //          range "1 .. 16777215";
          //        }
          //      }
          //    }
          //    leaf-list admin-group {
          //      ordered-by user;
          //      description "Administrative groups";
          //      type string;
          //      max-elements 16;
          //    }
          //  }
         }
         leaf vpn-apply-export {
           description "Apply BGP export policy when exporting VPN routes";
           type empty;
         }
        //  container egress-te {
        //    presence "enable egress-te";
        //    description "Use Egress Peering traffic engineering";
        //    // uses apply-advanced;
        //    leaf install-address {
        //      description "Address to use in egress-te created inet route";
        //      type jt:ipaddr;
        //    }
        //    container rib {
        //      description "Select primary table for Egress-TE routes";
        //      // uses apply-advanced;
        //      leaf inet.0 {
        //        description "Install Egress-TE routes in inet.0";
        //        type empty;
        //      }
        //      leaf inet6.0 {
        //        description "Install Egress-TE routes in inet6.0";
        //        type empty;
        //      }
        //    }
        //    leaf no-install {
        //      description "Avoid installation to FIB or resolving over";
        //      type empty;
        //    }
        //    leaf-list import {
        //      ordered-by user;
        //      description "Import policy to set attributes";
        //      type jt:policy-algebra;
        //    }
        //    leaf backup-path {
        //      description "The 'egress-te-backup-paths template' to use for this peer";
        //      type string {
        //      }
        //    }
        //  }
        //  leaf advertise-prefix-sid {
        //    description "Advertise prefix sid to E-BGP peers";
        //    type empty;
        //  }
        //  leaf accept-prefix-sid {
        //    description "Accept prefix sid from E-BGP peers";
        //    type empty;
        //  }
        //  leaf advertise-srgb {
        //    description "Advertise SRGB TLV";
        //    type empty;
        //  }
        //  leaf tcp-connect-port {
        //    description "TCP port number to connect with peer on";
        //    type union {
        //      type string {
        //        pattern "<.*>|$.*";
        //      }
        //      type uint16 {
        //        range "1 .. 65535";
        //      }
        //    }
        //  }
       }
       leaf vpn-apply-export {
         description "Apply BGP export policy when exporting VPN routes";
         type empty;
       }
      //  container egress-te {
      //    presence "enable egress-te";
      //    description "Use Egress Peering traffic engineering";
      //    // uses apply-advanced;
      //    leaf install-address {
      //      description "Address to use in egress-te created inet route";
      //      type jt:ipaddr;
      //    }
      //    container rib {
      //      description "Select primary table for Egress-TE routes";
      //      // uses apply-advanced;
      //      leaf inet.0 {
      //        description "Install Egress-TE routes in inet.0";
      //        type empty;
      //      }
      //      leaf inet6.0 {
      //        description "Install Egress-TE routes in inet6.0";
      //        type empty;
      //      }
      //    }
      //    leaf no-install {
      //      description "Avoid installation to FIB or resolving over";
      //      type empty;
      //    }
      //    leaf-list import {
      //      ordered-by user;
      //      description "Import policy to set attributes";
      //      type jt:policy-algebra;
      //    }
      //    leaf backup-path {
      //      description "The 'egress-te-backup-paths template' to use for this peer";
      //      type string {
      //      }
      //    }
      //  }
      //  leaf advertise-prefix-sid {
      //    description "Advertise prefix sid to E-BGP peers";
      //    type empty;
      //  }
      //  leaf accept-prefix-sid {
      //    description "Accept prefix sid from E-BGP peers";
      //    type empty;
      //  }
      //  leaf advertise-srgb {
      //    description "Advertise SRGB TLV";
      //    type empty;
      //  }
      //  leaf tcp-connect-port {
      //    description "TCP port number to connect with peer on";
      //    type union {
      //      type string {
      //        pattern "<.*>|$.*";
      //      }
      //      type uint16 {
      //        range "1 .. 65535";
      //      }
      //    }
      //  }
      //  leaf no-global-load-balancing {
      //    description "Disable glabl load balancing";
      //    type empty;
      //  }
     }
     container traffic-statistics-labeled-path {
       presence "enable traffic-statistics-labeled-path";
       description "Collect periodic ingress labeled statistics for BGP label-switched paths ";
       // uses apply-advanced;
       container file {
         description "Statistics file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time interval to collect statistics";
         units "seconds";
         type union {
           type string {
             pattern "<.*>|$.*";
           }
           type int32 {
             range "60 .. 65535";
           }
         }
       }
     }
     container source-packet-routing {
       description "Enable Source Packet Routing (SPRING)";
       // uses apply-advanced;
       container srgb {
         description "Set the SRGB global block in SPRING";
         leaf start-label {
           description "Start range for SRGB label block";
           type union {
             type string {
               pattern "<.*>|$.*";
             }
             type uint32;
           }
         }
         leaf index-range {
           description "Index to the SRGB start label block";
           type union {
             type string {
               pattern "<.*>|$.*";
             }
             type uint32;
           }
         }
       }
       container srv6 {
         description "Enable IPv6 Segment Routing (SRv6)";
         // uses apply-advanced;
         list locator {
           key name;
           ordered-by user;
           description "SRv6 Locator";
           leaf name {
             description "Locator name";
             type string;
           }
           // uses apply-advanced;
           container end-dt4-sid {
             presence "enable end-dt4-sid";
             description "End dt4 sid with 128 bit address";
             // uses apply-advanced;
             leaf sid {
               description "Sid value";
               type jt:ipv6addr;
             }
             leaf non-default {
               description "Non default sid for policy usage";
               type empty;
             }
           }
           container end-dt6-sid {
             presence "enable end-dt6-sid";
             description "End dt6 sid with 128 bit address";
             // uses apply-advanced;
             leaf sid {
               description "Sid value";
               type jt:ipv6addr;
             }
             leaf non-default {
               description "Non default sid for policy usage";
               type empty;
             }
           }
           container end-dt46-sid {
             presence "enable end-dt46-sid";
             description "End dt46 sid with 128 bit address";
             // uses apply-advanced;
             leaf sid {
               description "Sid value";
               type jt:ipv6addr;
             }
             leaf non-default {
               description "Non default sid for policy usage";
               type empty;
             }
           }
           container micro-dt4-sid {
             presence "enable micro-dt4-sid";
             description "Micro dt4 sid";
             // uses apply-advanced;
             leaf micro-sid-value {
               description "Static micro sid value 16-bit or 32-bit";
               type union {
                 type uint32;
                 type string {
                   pattern "<.*>|$.*";
                 }
               }
             }
             leaf non-default {
               description "Non default micro dt4 sid for policy usage";
               type empty;
             }
           }
           container micro-dt6-sid {
             presence "enable micro-dt6-sid";
             description "Micro dt6 sid";
             // uses apply-advanced;
             leaf micro-sid-value {
               description "Static micro sid value 16-bit or 32-bit";
               type union {
                 type uint32;
                 type string {
                   pattern "<.*>|$.*";
                 }
               }
             }
             leaf non-default {
               description "Non default micro dt6 sid for policy usage";
               type empty;
             }
           }
           container micro-dt46-sid {
             presence "enable micro-dt46-sid";
             description "Micro dt46 sid";
             // uses apply-advanced;
             leaf micro-sid-value {
               description "Static micro sid value 16-bit or 32-bit";
               type union {
                 type uint32;
                 type string {
                   pattern "<.*>|$.*";
                 }
               }
             }
             leaf non-default {
               description "Non default micro dt46 sid for policy usage";
               type empty;
             }
           }
         }
       }
     }
     choice enable-disable {
       case case_1 {
         leaf disable {
           description "Disable BGP";
           type empty;
         }
       }
     }
     leaf protocol-instance-name {
       description "Name of protocol instance under routing instance";
       type string;
     }
     choice precision-timers-choice {
       leaf precision-timers {
         description "Use precision timers for scheduling keepalives";
         type empty;
       }
       leaf no-precision-timers {
         description "Don't use precision timers for scheduling keepalives";
         type empty;
       }
     }
     container snmp-options {
       description "Customize SNMP behaviors specifically for BGP MIBs";
       // uses apply-advanced;
       leaf backward-traps-only-from-established {
         description "Limit traps for backward transitions to only those moving from Established state.";
         type empty;
       }
       leaf emit-inet-address-length-in-oid {
         description "Emit Length in OID for InetAddress MIB type.";
         type empty;
       }
     }
     leaf route-age-bgp-view {
       description "Maintain BGP route's age based on Update messages only";
       type empty;
     }
     leaf prioritize-route-queueing {
       description "Let route-queue building happen without getting throttled";
       type empty;
     }
     container traceoptions {
       description "Trace options for BGP";
       // uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "damping" {
               description "Trace BGP damping information";
             }
             enum "packets" {
               description "Trace all BGP protocol packets";
             }
             enum "open" {
               description "Trace BGP open packets";
             }
             enum "update" {
               description "Trace BGP update packets";
             }
             enum "keepalive" {
               description "Trace BGP keepalive packets";
             }
             enum "refresh" {
               description "Trace BGP refresh packets";
             }
             enum "nsr-synchronization" {
               description "Trace NSR synchronization events";
             }
             enum "bfd" {
               description "Trace BFD events";
             }
             enum "4byte-as" {
               description "Trace 4 byte AS events";
             }
             enum "add-path" {
               description "Trace add-path events";
             }
             enum "graceful-restart" {
               description "Trace Graceful Restart events";
             }
             enum "egress-te" {
               description "Egress Peering Traffic-Engineering events";
             }
             enum "thread-io" {
               description "Trace threaded I/O processing";
             }
             enum "sharding" {
               description "Trace BGP rib sharding";
             }
             enum "glb" {
               description "Trace BGP global-load-balancing";
             }
             enum "thread-update-io" {
               description "Trace threaded update I/O processing";
             }
             enum "route-validation" {
               description "Trace route validation";
             }
             enum "ipsec" {
               description "Trace ipsec";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses bgp_filter_obj;
         }
       }
     }
     leaf description {
       description "Text description";
       type string {
         length "1 .. 255";
       }
     }
     container metric-out {
       description "Route metric sent in MED";
       choice metric_param {
         case case_1 {
           leaf metric-value {
             description "Metric value";
             type union {
               type string {
                 pattern "<.*>|$.*";
               }
               type uint32 {
                 range "0 .. 4294967295";
               }
             }
           }
         }
         case case_2 {
           container minimum-igp {
             presence "enable minimum-igp";
             description "Track the minimum IGP metric";
             leaf metric-offset {
               description "Metric offset for MED";
               type union {
                 type int32;
                 type string {
                   pattern "<.*>|$.*";
                 }
               }
             }
           }
         }
         case case_3 {
           container igp {
             presence "enable igp";
             description "Track the IGP metric";
             leaf metric-offset {
               description "Metric offset for MED";
               type union {
                 type int32;
                 type string {
                   pattern "<.*>|$.*";
                 }
               }
             }
             leaf delay-med-update {
               description "Delay updating MED when IGP metric increases";
               type empty;
             }
           }
         }
         case case_4 {
           container effective-aigp {
             presence "enable effective-aigp";
             description "Track the effective AIGP metric";
             leaf metric-offset {
               description "Metric offset for MED";
               type union {
                 type int32;
                 type string {
                   pattern "<.*>|$.*";
                 }
               }
             }
           }
         }
         case case_5 {
           container minimum-effective-aigp {
             presence "enable minimum-effective-aigp";
             description "Track the minimum effective AIGP metric";
             leaf metric-offset {
               description "Metric offset for MED";
               type union {
                 type int32;
                 type string {
                   pattern "<.*>|$.*";
                 }
               }
             }
           }
         }
       }
     }
     container multihop {
       presence "enable multihop";
       description "Configure an EBGP multihop session";
       // uses apply-advanced;
       leaf ttl {
         description "TTL value for the session";
         type union {
           type string {
             pattern "<.*>|$.*";
           }
           type uint8 {
             range "1 .. 255";
           }
         }
       }
       leaf no-nexthop-change {
         description "Do not change next hop to self in advertisements";
         type empty;
       }
     }
     container ebgp-community-cleanup {
       presence "enable ebgp-community-cleanup";
       description "Community specific cleanup for eBGP peers";
       // uses apply-advanced;
       leaf origin-validation {
         description "Origin Validation State receive behavior";
         type enumeration {
           enum "accept" {
             description "Accept Origin Validation State Community";
           }
           enum "reject" {
             description "Reject Origin Validation State Community";
           }
         }
       }
     }
     leaf route-server-client {
       description "Enable route server client behavior";
       type empty;
     }
     leaf accept-remote-nexthop {
       description "Allow import policy to specify a non-directly connected next-hop";
       type empty;
     }
     leaf preference {
       description "Preference value";
       type union {
         type uint32;
         type string {
           pattern "<.*>|$.*";
         }
       }
     }
     leaf local-preference {
       description "Value of LOCAL_PREF path attribute";
       type union {
         type uint32;
         type string {
           pattern "<.*>|$.*";
         }
       }
     }
     leaf local-address {
       description "Address of local end of BGP session";
       type jt:ipaddr;
     }
     leaf local-interface {
       description "Local interface for IPv6 link local EBGP peering";
       type union {
         type jt:interface-name;
         type string {
           pattern "<.*>|$.*";
         }
       }
     }
     leaf forwarding-context {
       description "Routing-instance used for data-forwarding and transport-session";
       type string {
       }
     }
     leaf hold-time {
       description "Hold time used when negotiating with a peer";
       type union {
         type string {
           pattern "<.*>|$.*";
         }
         type uint32 {
           range "0 .. 65535";
         }
       }
     }
     leaf minimum-hold-time {
       description "Minimum hold time accepted from the peer";
       type union {
         type string {
           pattern "<.*>|$.*";
         }
         type uint32 {
           range "3 .. 65535";
         }
       }
     }
     leaf passive {
       description "Do not send open messages to a peer";
       type empty;
     }
     leaf advertise-inactive {
       description "Advertise inactive routes";
       type empty;
     }
     choice advertise-peer-as-choice {
       leaf advertise-peer-as {
         description "Advertise routes received from the same autonomous system";
         type empty;
       }
       leaf no-advertise-peer-as {
         description "Don't advertise routes received from the same autonomous system";
         type empty;
       }
     }
     container advertise-external {
       presence "enable advertise-external";
       description "Advertise best external routes";
       leaf conditional {
         description "Route matches active route upto med-comparison rule";
         type empty;
       }
     }
     leaf keep {
       description "How to retain routes in the routing table";
       type enumeration {
         enum "all" {
           description "Retain all routes";
         }
         enum "none" {
           description "Retain no routes";
         }
       }
     }
     leaf rfc6514-compliant-safi129 {
       description "Compliant with RFC6514 SAFI129 format";
       type empty;
     }
     leaf no-aggregator-id {
       description "Set router ID in aggregator path attribute to 0";
       type empty;
     }
     leaf mtu-discovery {
       description "Enable TCP path MTU discovery";
       type empty;
     }
     leaf enforce-first-as {
       description "Enforce first AS in AS-path is the neighbor's AS";
       type empty;
     }
     leaf out-delay {
       description "How long before exporting routes from routing table";
       type union {
         type string {
           pattern "<.*>|$.*";
         }
         type uint32 {
           range "0 .. 65535";
         }
       }
     }
     leaf ttl {
       description "TTL value for the single-hop peer";
       type enumeration {
         enum "1" {
         }
         enum "255" {
         }
       }
     }
     leaf log-updown {
       description "Log a message for peer state transitions";
       type empty;
     }
     leaf damping {
       description "Enable route flap damping";
       type empty;
     }
     leaf-list import {
       ordered-by user;
       description "Import policy";
       type jt:policy-algebra;
     }
     leaf-list nlri {
       ordered-by user;
       description "NLRI type to include in updates";
       status deprecated;
       type enumeration {
         enum "unicast" {
           description "Include unicast NLRI";
           status deprecated;
         }
         enum "multicast" {
           description "Include multicast NLRI";
           status deprecated;
         }
         enum "any" {
           description "Include any kind of NLRI";
           status deprecated;
         }
       }
     }
     container bgp-error-tolerance {
       presence "enable bgp-error-tolerance";
       description "Handle BGP malformed updates softly";
       // uses apply-advanced;
       leaf malformed-update-log-interval {
         description "Time used when logging malformed update";
         default "300";
         units "seconds";
         type union {
           type string {
             pattern "<.*>|$.*";
           }
           type uint32 {
             range "10 .. 65535";
           }
         }
       }
       choice malformed-routes-limit-choice {
         case case_1 {
           leaf malformed-route-limit {
             description "Maximum number of malformed routes from a peer";
             default "1000";
             type union {
               type string {
                 pattern "<.*>|$.*";
               }
               type uint32 {
                 range "0 .. 4294967295";
               }
             }
           }
         }
         case case_2 {
           leaf no-malformed-route-limit {
             description "No malformed route limit";
             type empty;
           }
         }
       }
     }
     leaf authentication-key {
       description "MD5 authentication key";
       type string {
         length "1 .. 126";
       }
     }
     leaf authentication-algorithm {
       description "Authentication algorithm name";
       default "hmac-sha-1-96";
       type enumeration {
         enum "md5" {
           description "Message Digest 5";
         }
         enum "hmac-sha-1-96" {
           description "Hash-based Message Authentication Code (SHA1) (96 bits)";
         }
         enum "aes-128-cmac-96" {
           description "Cipher-based Message Authentication Code (AES128) (96 bits)";
         }
         enum "ao" {
           description "TCP Authentication Option";
         }
       }
     }
     leaf tcpao-auth-mismatch {
       description "Continue without TCP-AO if any one TCP endpoint does not have TCP-AO configured";
       type enumeration {
         enum "allow-without-tcpao" {
           description "Allow the connection establishment without TCP-AO";
         }
       }
     }
     leaf authentication-key-chain {
       description "Key chain name";
       type string {
         length "1 .. 128";
       }
     }
     leaf-list export {
       ordered-by user;
       description "Export policy";
       type jt:policy-algebra;
     }
     container remove-private {
       presence "enable remove-private";
       description "Remove well-known private AS numbers";
       // uses apply-advanced;
       container all {
         presence "enable all";
         description "Remove all private AS numbers and do not stop at the first public AS number";
         container replace {
           presence "enable replace";
           description "Replace private AS numbers with the BGP Group's local AS number";
           leaf nearest {
             description "Use closest public AS number to replace a private AS number";
             type empty;
           }
         }
       }
       leaf no-peer-loop-check {
         description "Remove peer loop-check";
         type empty;
       }
     }
     leaf cluster {
       description "Cluster identifier";
       type jt:areaid;
     }
     leaf no-client-reflect {
       description "Disable intracluster route redistribution";
       type empty;
     }
     leaf peer-as {
       description " Autonomous system number in plain number or 'higher 16bits'.'Lower 16 bits' (asdot notation) format";
       type string {
       }
     }
     container local-as {
       description "Local autonomous system number";
       leaf as-number {
         description " Autonomous system number in plain number or 'higher 16bits'.'Lower 16 bits' (asdot notation) format";
         type string {
         }
       }
       leaf loops {
         description "Maximum number of times this AS can be in an AS path";
         type union {
           type string {
             pattern "<.*>|$.*";
           }
           type int32 {
             range "1 .. 10";
           }
         }
       }
       leaf private {
         description "Hide this local AS in paths learned from this peering";
         type empty;
       }
       leaf alias {
         description "Treat this AS as an alias to the system AS";
         type empty;
       }
       leaf no-prepend-global-as {
         description "Do not prepend global autonomous-system number in advertised paths";
         type empty;
       }
     }
     leaf ipsec-sa {
       description "IPSec SA name";
       type string {
         length "1 .. 32";
       }
     }
     container graceful-shutdown {
       description "BGP peer graceful shutdown option";
       // uses apply-advanced;
       container receiver {
         presence "enable receiver";
         description "BGP peer graceful-shutdown receiver";
         // uses apply-advanced;
         leaf disable {
           description "Disable graceful-shutdown receiver";
           type empty;
         }
         leaf local-preference {
           description "Value of receiver LOCAL_PREF path attribute";
           type union {
             type uint32;
             type string {
               pattern "<.*>|$.*";
             }
           }
         }
       }
       container sender {
         presence "enable sender";
         description "BGP peer graceful-shutdown sender";
         // uses apply-advanced;
         leaf local-preference {
           description "Value of sender LOCAL_PREF path attribute";
           type union {
             type uint32;
             type string {
               pattern "<.*>|$.*";
             }
           }
         }
       }
     }
     container shutdown {
       presence "enable shutdown";
       description "Shutdown";
       // uses apply-advanced;
       leaf notify-message {
         description "Notification message";
         type string;
       }
     }
     leaf unconfigured-peer-graceful-restart {
       description "BGP unconfigured peer graceful restart options";
       type empty;
     }
     container graceful-restart {
       presence "enable graceful-restart";
       description "BGP graceful restart options";
       // uses apply-advanced;
       choice enable-disable {
         case case_1 {
           leaf disable {
             description "Disable graceful restart";
             type empty;
           }
         }
       }
       leaf restart-time {
         description "Restart time used when negotiating with a peer";
         type union {
           type string {
             pattern "<.*>|$.*";
           }
           type uint32 {
             range "1 .. 1800";
           }
         }
       }
       leaf stale-routes-time {
         description "Maximum time for which stale routes are kept";
         type union {
           type string {
             pattern "<.*>|$.*";
           }
           type uint32 {
             range "1 .. 1800";
           }
         }
       }
       container long-lived {
         description "Long-lived graceful restart options";
         // uses apply-advanced;
         container receiver {
           description "Long-lived graceful restart receiver (helper) options";
           // uses apply-advanced;
           choice enable-disable {
             case case_1 {
               leaf disable {
                 description "Disable receiver (helper) functionality";
                 type empty;
               }
             }
           }
         }
         container advertise-to-non-llgr-neighbor {
           presence "enable advertise-to-non-llgr-neighbor";
           description "Advertise stale routes to non-LLGR neighbors";
           // uses apply-advanced;
           leaf omit-no-export {
             description "Do not attach no-export community to stale routes";
             type empty;
           }
         }
       }
       leaf disable-notification-extensions {
         description "Disable notification extensions";
         type empty;
       }
       leaf forwarding-state-bit {
         description "Control forwarding-state flag negotiation";
         type enumeration {
           enum "as-rr-client" {
             description "As for a route reflector client";
           }
           enum "from-fib" {
             description "Always use state of associated FIB(s)";
           }
         }
       }
       leaf dont-help-shared-fate-bfd-down {
         description "Honor BFD-Down(C=0) if GR-restart not in progress";
         type empty;
       }
     }
     leaf include-mp-next-hop {
       description "Include NEXT-HOP attribute in multiprotocol updates";
       type empty;
     }
     leaf disable-4byte-as {
       description "Disable 4 byte AS capability advertisement";
       type empty;
     }
     container idle-after-switch-over {
       description "Stop peer session from coming up after nonstop-routing switch-over";
       choice idle-interval {
         case case_1 {
           leaf forever {
             description "Idle the peer until the user intervenes";
             type empty;
           }
         }
         case case_2 {
           leaf timeout {
             description "Timeout value, in seconds, for starting peer after switch over";
             type union {
               type string {
                 pattern "<.*>|$.*";
               }
               type uint32 {
                 range "1 .. 4294967295";
               }
             }
           }
         }
       }
     }
     container outbound-route-filter {
       description "Dynamically negotiated cooperative route filtering";
       // uses apply-advanced;
       leaf bgp-orf-cisco-mode {
         description "Using BGP ORF capability code 130 and Prefix ORF type 128";
         type empty;
       }
       container extended-community {
         description "Extended community filtering";
         status deprecated;
         // uses apply-advanced;
         choice accept-choice {
           leaf accept {
             description "Honor remote requests for extended community ORF";
             type empty;
           }
           leaf no-accept {
             description "Don't honor remote requests for extended community ORF";
             type empty;
           }
         }
         leaf vrf-filter {
           description "Request remote filtering using locally configured VRF import targets";
           type empty;
         }
       }
       container prefix-based {
         presence "enable prefix-based";
         description "Prefix-based outbound route filtering";
         // uses apply-advanced;
         container accept {
           presence "enable accept";
           description "Honor Prefix-based ORFs from remote peers";
           // uses apply-advanced;
           leaf inet {
             description "Honor IPv4 prefix filters";
             type empty;
           }
           leaf inet6 {
             description "Honor IPv6 prefix filters";
             type empty;
           }
         }
       }
     }
     container message-batching {
       description "DEPRECATED - Batching of outgoing messages";
       status deprecated;
       // uses apply-advanced;
       choice enable-disable {
         case case_1 {
           leaf enable {
             description "Enable parameter";
             type empty;
           }
         }
         case case_2 {
           leaf disable {
             description "Disable parameter";
             type empty;
           }
         }
       }
       leaf interval {
         description "DEPRECATED - Interval over which to batch messages";
         default "250";
         units "milliseconds";
         type union {
           type string {
             pattern "<.*>|$.*";
           }
           type uint32 {
             range "100 .. 1000";
           }
         }
       }
     }
     container multipath {
       presence "enable multipath";
       description "Allow load sharing among multiple BGP paths";
       // uses apply-advanced;
       leaf disable {
         description "Disable Multipath";
         type empty;
       }
       leaf multiple-as {
         description "Use paths received from different ASs";
         type empty;
       }
       leaf allow-protection {
         description "Allow protection for multipath legs";
         type empty;
       }
       leaf pause-computation-during-churn {
         description "Pause multipath job to absorb churn";
         type empty;
       }
       leaf list-nexthop {
         description "Use List-NH for homogenous nexthop-set also";
         type empty;
       }
       container allow-external-internal {
         presence "enable allow-external-internal";
         description "Allow multipath to mix EBGP and IBGP routes";
         // uses apply-advanced;
         leaf-list prefix-policy {
           ordered-by user;
           description "Policy to constrain prefixes that apply";
           type jt:policy-algebra;
         }
       }
     }
     leaf tcp-mss {
       description "Maximum TCP segment size";
       type union {
         type string {
           pattern "<.*>|$.*";
         }
         type uint32 {
           range "1 .. 4096";
         }
       }
     }
     leaf bgp-identifier {
       description "BGP Identifier";
       type jt:ipv4addr;
     }
    //  leaf tcp-aggressive-transmission {
    //    description "Enable aggressive transmission of pure TCP ACKs and retransmissions";
    //    type empty;
    //  }
    //  container bmp {
    //    description "Specific settings to override the routing-options settings";
    //    // uses apply-advanced;
    //    leaf monitor {
    //      description "Enable/Disable monitoring";
    //      type enumeration {
    //        enum "enable" {
    //          description "Enable monitoring of BGP peer(s)";
    //        }
    //        enum "disable" {
    //          description "Disable monitoring of BGP peer(s)";
    //        }
    //      }
    //    }
    //    container route-monitoring {
    //      description "Control route monitoring settings";
    //      // uses apply-advanced;
    //      leaf none {
    //        description "Do not send route monitoring messages";
    //        type empty;
    //      }
    //      container pre-policy {
    //        presence "enable pre-policy";
    //        description "Send pre-policy route monitoring messages";
    //        leaf exclude-non-feasible {
    //          description "Exclude looped routes, etc";
    //          type empty;
    //        }
    //      }
    //      container post-policy {
    //        presence "enable post-policy";
    //        description "Send post-policy route monitoring messages";
    //        leaf exclude-non-eligible {
    //          description "Exclude unresolved routes, etc.";
    //          type empty;
    //        }
    //      }
    //      container rib-out {
    //        presence "enable rib-out";
    //        description "Send adj-ribs-out route monitoring messages";
    //        leaf pre-policy {
    //          description "Send pre-policy adj-ribs-out route monitoring messages";
    //          type empty;
    //        }
    //        leaf post-policy {
    //          description "Send post-policy adj-ribs-out route monitoring messages";
    //          type empty;
    //        }
    //      }
    //    }
    //  }
     container advertise-bgp-static {
       presence "enable advertise-bgp-static";
       description "Advertise bgp-static routes";
       // uses apply-advanced;
       leaf-list policy {
         ordered-by user;
         description "Static route advertisement policy";
         type jt:policy-algebra;
       }
     }
     leaf add-path-display-ipv4-address {
       description "Display add-path path-id in IPv4 address format";
       type empty;
     }
     container domain-path-id {
       description "Domain path id attribute";
       // uses apply-advanced;
       leaf send {
         description "Allow sending domain path id attribute";
         type empty;
       }
       leaf receive {
         description "Allow receiving domain path id attribute";
         type empty;
       }
     }
     container bfd-liveness-detection {
       description "Bidirectional Forwarding Detection (BFD) options";
       // uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       leaf inline-disable {
         description "Disable inline mode for this BFD session";
         type empty;
       }
       leaf pdu-size {
         description "BFD transport protocol payload size";
         default "24";
         type union {
           type string {
             pattern "<.*>|$.*";
           }
           type uint32 {
             range "24 .. 9000";
           }
         }
       }
       choice adaptation-choice {
         case case_1 {
           leaf no-adaptation {
             description "Disable adaptation";
             type empty;
           }
         }
       }
       container transmit-interval {
         description "Transmit-interval options";
         // uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         // uses apply-advanced;
         leaf threshold {
           description "High detection-time triggering a trap";
           units "milliseconds";
           type union {
             type uint32;
             type string {
               pattern "<.*>|$.*";
             }
           }
         }
       }
       container authentication {
         description "Authentication options";
         // uses apply-advanced;
         leaf key-chain {
           description "Key chain name";
           type string;
         }
         leaf algorithm {
           description "Algorithm name";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       leaf session-mode {
         description "BFD single-hop or multihop session-mode";
         default "automatic";
         type enumeration {
           enum "automatic" {
             description "Choose session-mode automatically";
           }
           enum "single-hop" {
             description "Use single-hop";
           }
           enum "multihop" {
             description "Use multihop";
           }
         }
       }
       container echo {
         description "Echo mode parameters";
         // uses apply-advanced;
         leaf minimum-interval {
           description "Minimum transmit and receive interval";
           units "milliseconds";
           type union {
             type string {
               pattern "<.*>|$.*";
             }
             type uint32 {
               range "100 .. 255000";
             }
           }
         }
       }
       container echo-lite {
         description "Echo-lite more parameters";
         // uses apply-advanced;
         leaf minimum-interval {
           description "Minimum transmit and receive interval";
           units "milliseconds";
           type union {
             type string {
               pattern "<.*>|$.*";
             }
             type uint32 {
               range "100 .. 255000";
             }
           }
         }
       }
       container strict-bfd {
         presence "enable strict-bfd";
         description "Bgp session waits for bfd";
         // uses apply-advanced;
         leaf bfd-up-wait-interval {
           description "Time to wait for bfd to come up";
           units "seconds";
           type union {
             type string {
               pattern "<.*>|$.*";
             }
             type uint32 {
               range "10 .. 255";
             }
           }
         }
       }
       leaf holddown-interval {
         description "Time to hold the session-UP notification to the client";
         units "milliseconds";
         type union {
           type string {
             pattern "<.*>|$.*";
           }
           type uint32 {
             range "0 .. 255000";
           }
         }
       }
     }
     container output-queue-priority {
       description "BGP output queue priority scheduler for updates";
       // uses apply-advanced;
       container expedited {
         presence "enable expedited";
         description "Expedited queue; highest priority";
         leaf update-tokens {
           description "Number of tokens";
           type union {
             type string {
               pattern "<.*>|$.*";
             }
             type uint32 {
               range "1 .. 100";
             }
           }
         }
       }
       list priority {
         key name;
         description "Output queue priority 1..16; higher is better";
         leaf name {
           description "Output queue priority; higher is better";
           type union {
             type string {
               pattern "<.*>|$.*";
             }
             type uint32 {
               range "1 .. 16";
             }
           }
         }
         leaf update-tokens {
           description "Number of tokens";
           type union {
             type string {
               pattern "<.*>|$.*";
             }
             type uint32 {
               range "1 .. 100";
             }
           }
         }
       }
      //  container defaults {
      //    description "Map policy's priority class and BGP output-queue";
      //    // uses apply-advanced;
      //    container low {
      //      description "Assign the 'low' priority class to this output-queue";
      //      uses bgp-output-queue-priority-class;
      //    }
      //    container medium {
      //      description "Assign the 'medium' priority class to this output-queue";
      //      uses bgp-output-queue-priority-class;
      //    }
      //    container high {
      //      description "Assign the 'high' priority class to this output-queue";
      //      uses bgp-output-queue-priority-class;
      //    }
      //  }
     }
     container multipath-build-priority {
       description "Configure the multipath build priority";
       // uses apply-advanced;
       choice multipath-priority {
         case case_1 {
           leaf low {
             description "Do multipath build with low priority";
             type empty;
           }
         }
         case case_2 {
           leaf medium {
             description "Do multipath build with medium priority";
             type empty;
           }
         }
       }
     }
     leaf send-addpath-optimization {
       description "Enable BGP addpath advertisement optimization";
       type empty;
     }
     container defaults {
       // uses apply-advanced;
       container ebgp {
         description "Options impacting external BGP default behaviors";
         // uses apply-advanced;
         container no-policy {
           description "Default ebgp behaviors in the absence of configured policy";
           // uses apply-advanced;
           leaf receive {
             description "Default ebgp receive behavior";
             type enumeration {
               enum "accept" {
                 description "By default, accept routes from all address families";
               }
               enum "reject" {
                 description "By default, reject routes from IPv4/IPv6 unicast address families";
               }
               enum "reject-always" {
                 description "By default, reject routes from all address families";
               }
             }
           }
           leaf advertise {
             description "Default ebgp advertise behavior";
             type enumeration {
               enum "accept" {
                 description "By default, advertise routes for all address families";
               }
               enum "reject" {
                 description "By default, do not advertise routes from IPv4/IPv6 unicast address families";
               }
               enum "reject-always" {
                 description "By default, do not advertise routes from any address families";
               }
             }
           }
         }
       }
     }
   }
   grouping bgp-af-gr {
     // uses apply-advanced;
     container long-lived {
       description "Long-lived graceful restart options";
       // uses apply-advanced;
       container restarter {
         description "Long-lived graceful restart restarter options";
         // uses apply-advanced;
         choice enable-disable {
           case case_1 {
             leaf disable {
               description "Disable restarter functionality";
               type empty;
             }
           }
         }
         leaf stale-time {
           description "Stale time in seconds or dhms notation (1..16777215)";
           type string;
         }
       }
       container extended-route-retention {
         description "Extended route retention (LLGR-helper extended) options";
         // uses apply-advanced;
         choice enable-disable {
           case case_1 {
             leaf disable {
               description "Disable extended-route-retention (LLGR-helper) functionality";
               type empty;
             }
           }
         }
         leaf retention-time {
           description "Retention time in seconds or dhms notation (1..16777215)";
           type string;
         }
         leaf-list retention-policy {
           ordered-by user;
           description "Retention policy for Extended Route Retention";
           type jt:policy-algebra;
         }
       }
     }
     leaf forwarding-state-bit {
       description "Control forwarding-state flag negotiation";
       type enumeration {
         enum "set" {
           description "Always set";
         }
         enum "from-fib" {
           description "Use state of associated FIB(s)";
         }
       }
     }
   }
   grouping bgp-afi-default {
     // uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
    //  container aigp {
    //    description "Allow sending and receiving of AIGP attribute";
    //    presence "enable aigp";
    //    uses bgpaf-aigp-options;
    //  }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       // uses apply-advanced;
       leaf always-wait-for-krt-drain {
         description "Wait for KRT-queue drain for more-specific prefixes";
         type empty;
       }
       container minimum-delay {
         description "Minimum-delay to ensure KRT sees the route flash";
         // uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         // uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       // uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       // uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
    //  leaf extended-nexthop-color {
    //    description "Resolve using extended color nexthop";
    //    type empty;
    //  }
    //  leaf extended-nexthop-tunnel {
    //    description "Use BGP tunnel attribute";
    //    type empty;
    //  }
    //  leaf no-install {
    //    description "Dont install received routes in forwarding";
    //    type empty;
    //  }
    //  leaf route-age-bgp-view {
    //    description "Maintain BGP route's age based on Update messages only";
    //    type empty;
    //  }
    //  container output-queue-priority {
    //    description "Default output-queue to assign updates to";
    //    uses bgp-output-queue-priority-class;
    //  }
    //  container route-refresh-priority {
    //    description "Default output-queue to assign route refreshes to";
    //    uses bgp-output-queue-priority-class;
    //  }
    //  container withdraw-priority {
    //    description "Default output-queue to assign withdrawn routes to";
    //    uses bgp-output-queue-priority-class;
    //  }
    //  leaf advertise-srv6-service {
    //    description "Advertise SRv6 service";
    //    type empty;
    //  }
    //  leaf accept-srv6-service {
    //    description "Accept SRv6 service";
    //    type empty;
    //  }
   }
   grouping apath-options {
     description "Number of paths to advertise";
     // uses apply-advanced;
     leaf receive {
       description "Receive multiple paths from peer";
       type empty;
     }
     container send {
       presence "enable send";
       description "Send multiple paths to peer";
       // uses apply-advanced;
       container path-selection-mode {
         description "Configure how to select add-path routes";
         // uses apply-advanced;
         choice mode {
           case case_1 {
             leaf all-paths {
               description "Advertise all paths allowed by path count";
               type empty;
             }
           }
           case case_2 {
             leaf equal-cost-paths {
               description "Advertise equal cost paths";
               type empty;
             }
           }
         }
       }
       leaf-list prefix-policy {
         ordered-by user;
         description "Perform add-path only for prefixes that match policy";
         type jt:policy-algebra;
       }
       leaf path-count {
         description "Number of paths to advertise";
         type union {
           type string {
             pattern "<.*>|$.*";
           }
           type int32 {
             range "2 .. 64";
           }
         }
       }
       leaf include-backup-path {
         description "Number of backup paths to advertise";
         type union {
           type string {
             pattern "<.*>|$.*";
           }
           type int32 {
             range "1 .. 2";
           }
         }
       }
       leaf multipath {
         description "Include only multipath contributor routes";
         type empty;
       }
     }
   }
  //  grouping bgp-afi-flow {
  //    // uses apply-advanced;
  //    container prefix-limit {
  //      description "Limit maximum number of prefixes from a peer";
  //      uses bgpaf-prefix-limit;
  //    }
  //    container accepted-prefix-limit {
  //      description "Limit maximum number of prefixes accepted from a peer";
  //      uses bgpaf-accepted-prefix-limit;
  //    }
  //    container rib-group {
  //      description "Routing table group";
  //      uses rib_group_inet_type;
  //    }
  //    container add-path {
  //      description "Advertise multiple paths to peer";
  //      uses apath-options;
  //    }
  //    container aigp {
  //      description "Allow sending and receiving of AIGP attribute";
  //      presence "enable aigp";
  //      uses bgpaf-aigp-options;
  //    }
  //    leaf damping {
  //      description "Enable route flap damping";
  //      type empty;
  //    }
  //    leaf local-ipv4-address {
  //      description "Local IPv4 address";
  //      type jt:ipv4addr;
  //    }
  //    container loops {
  //      description "Allow local AS in received AS paths";
  //      uses bgpaf-loops;
  //    }
  //    container delay-route-advertisements {
  //      presence "enable delay-route-advertisements";
  //      description "Delay route updates for this family until FIB-sync";
  //      // uses apply-advanced;
  //      leaf always-wait-for-krt-drain {
  //        description "Wait for KRT-queue drain for more-specific prefixes";
  //        type empty;
  //      }
  //      container minimum-delay {
  //        description "Minimum-delay to ensure KRT sees the route flash";
  //        // uses apply-advanced;
  //        leaf routing-uptime {
  //          description "Min delay(sec) advertisement after RPD start";
  //          type union {
  //            type string {
  //              pattern "<.*>|$.*";
  //            }
  //            type uint32 {
  //              range "1 .. 36000";
  //            }
  //          }
  //        }
  //        leaf inbound-convergence {
  //          description "Min delay(sec) advertisement after source-peer sent all routes";
  //          type union {
  //            type string {
  //              pattern "<.*>|$.*";
  //            }
  //            type uint32 {
  //              range "1 .. 36000";
  //            }
  //          }
  //        }
  //      }
  //      container maximum-delay {
  //        description "Maximum delay deferring routes";
  //        // uses apply-advanced;
  //        leaf route-age {
  //          description "Max delay(sec) advertisement route age";
  //          type union {
  //            type string {
  //              pattern "<.*>|$.*";
  //            }
  //            type uint32 {
  //              range "1 .. 36000";
  //            }
  //          }
  //        }
  //        leaf routing-uptime {
  //          description "Max delay(sec) advertisement after RPD start";
  //          type union {
  //            type string {
  //              pattern "<.*>|$.*";
  //            }
  //            type uint32 {
  //              range "1 .. 36000";
  //            }
  //          }
  //        }
  //      }
  //    }
  //    container nexthop-resolution {
  //      description "Configure nexthop resolution properties";
  //      // uses apply-advanced;
  //      leaf no-resolution {
  //        description "Consider nexthop good without resolution attempt";
  //        type empty;
  //      }
  //      leaf preserve-nexthop-hierarchy {
  //        description "Attempt preserving resolved nexthop chain in forwarding";
  //        type empty;
  //      }
  //    }
  //    container defer-initial-multipath-build {
  //      presence "enable defer-initial-multipath-build";
  //      description "Defer initial multipath build until EOR is received";
  //      // uses apply-advanced;
  //      leaf maximum-delay {
  //        description "Max delay(sec) multipath build after peer is up";
  //        type union {
  //          type string {
  //            pattern "<.*>|$.*";
  //          }
  //          type uint32 {
  //            range "1 .. 3600";
  //          }
  //        }
  //      }
  //    }
  //    container graceful-restart {
  //      description "BGP graceful restart options";
  //      uses bgp-af-gr;
  //    }
  //    leaf extended-nexthop {
  //      description "Extended nexthop encoding";
  //      type empty;
  //    }
  //    leaf extended-nexthop-color {
  //      description "Resolve using extended color nexthop";
  //      type empty;
  //    }
  //    leaf extended-nexthop-tunnel {
  //      description "Use BGP tunnel attribute";
  //      type empty;
  //    }
  //    leaf no-install {
  //      description "Dont install received routes in forwarding";
  //      type empty;
  //    }
  //    leaf route-age-bgp-view {
  //      description "Maintain BGP route's age based on Update messages only";
  //      type empty;
  //    }
  //    container output-queue-priority {
  //      description "Default output-queue to assign updates to";
  //      uses bgp-output-queue-priority-class;
  //    }
  //    container route-refresh-priority {
  //      description "Default output-queue to assign route refreshes to";
  //      uses bgp-output-queue-priority-class;
  //    }
  //    container withdraw-priority {
  //      description "Default output-queue to assign withdrawn routes to";
  //      uses bgp-output-queue-priority-class;
  //    }
  //    leaf advertise-srv6-service {
  //      description "Advertise SRv6 service";
  //      type empty;
  //    }
  //    leaf accept-srv6-service {
  //      description "Accept SRv6 service";
  //      type empty;
  //    }
  //    leaf-list no-validate {
  //      ordered-by user;
  //      description "Bypass validation procedure for routes that match policy";
  //      type jt:policy-algebra;
  //    }
  //    leaf strip-nexthop {
  //      description "Strip the next-hop from the outgoing flow update";
  //      type empty;
  //    }
  //    leaf allow-policy-add-nexthop {
  //      description "Allow policy to add nexthop to a route without nexthop";
  //      status deprecated;
  //      type empty;
  //    }
  //  }
  //  grouping bgp-afi-flow-with-redirect-ip-action {
  //    // uses apply-advanced;
  //    container prefix-limit {
  //      description "Limit maximum number of prefixes from a peer";
  //      uses bgpaf-prefix-limit;
  //    }
  //    container accepted-prefix-limit {
  //      description "Limit maximum number of prefixes accepted from a peer";
  //      uses bgpaf-accepted-prefix-limit;
  //    }
  //    container rib-group {
  //      description "Routing table group";
  //      uses rib_group_inet_type;
  //    }
  //    container add-path {
  //      description "Advertise multiple paths to peer";
  //      uses apath-options;
  //    }
  //    container aigp {
  //      description "Allow sending and receiving of AIGP attribute";
  //      presence "enable aigp";
  //      uses bgpaf-aigp-options;
  //    }
  //    leaf damping {
  //      description "Enable route flap damping";
  //      type empty;
  //    }
  //    leaf local-ipv4-address {
  //      description "Local IPv4 address";
  //      type jt:ipv4addr;
  //    }
  //    container loops {
  //      description "Allow local AS in received AS paths";
  //      uses bgpaf-loops;
  //    }
  //    container delay-route-advertisements {
  //      presence "enable delay-route-advertisements";
  //      description "Delay route updates for this family until FIB-sync";
  //      // uses apply-advanced;
  //      leaf always-wait-for-krt-drain {
  //        description "Wait for KRT-queue drain for more-specific prefixes";
  //        type empty;
  //      }
  //      container minimum-delay {
  //        description "Minimum-delay to ensure KRT sees the route flash";
  //        // uses apply-advanced;
  //        leaf routing-uptime {
  //          description "Min delay(sec) advertisement after RPD start";
  //          type union {
  //            type string {
  //              pattern "<.*>|$.*";
  //            }
  //            type uint32 {
  //              range "1 .. 36000";
  //            }
  //          }
  //        }
  //        leaf inbound-convergence {
  //          description "Min delay(sec) advertisement after source-peer sent all routes";
  //          type union {
  //            type string {
  //              pattern "<.*>|$.*";
  //            }
  //            type uint32 {
  //              range "1 .. 36000";
  //            }
  //          }
  //        }
  //      }
  //      container maximum-delay {
  //        description "Maximum delay deferring routes";
  //        // uses apply-advanced;
  //        leaf route-age {
  //          description "Max delay(sec) advertisement route age";
  //          type union {
  //            type string {
  //              pattern "<.*>|$.*";
  //            }
  //            type uint32 {
  //              range "1 .. 36000";
  //            }
  //          }
  //        }
  //        leaf routing-uptime {
  //          description "Max delay(sec) advertisement after RPD start";
  //          type union {
  //            type string {
  //              pattern "<.*>|$.*";
  //            }
  //            type uint32 {
  //              range "1 .. 36000";
  //            }
  //          }
  //        }
  //      }
  //    }
  //    container nexthop-resolution {
  //      description "Configure nexthop resolution properties";
  //      // uses apply-advanced;
  //      leaf no-resolution {
  //        description "Consider nexthop good without resolution attempt";
  //        type empty;
  //      }
  //      leaf preserve-nexthop-hierarchy {
  //        description "Attempt preserving resolved nexthop chain in forwarding";
  //        type empty;
  //      }
  //    }
  //    container defer-initial-multipath-build {
  //      presence "enable defer-initial-multipath-build";
  //      description "Defer initial multipath build until EOR is received";
  //      // uses apply-advanced;
  //      leaf maximum-delay {
  //        description "Max delay(sec) multipath build after peer is up";
  //        type union {
  //          type string {
  //            pattern "<.*>|$.*";
  //          }
  //          type uint32 {
  //            range "1 .. 3600";
  //          }
  //        }
  //      }
  //    }
  //    container graceful-restart {
  //      description "BGP graceful restart options";
  //      uses bgp-af-gr;
  //    }
  //    leaf extended-nexthop {
  //      description "Extended nexthop encoding";
  //      type empty;
  //    }
  //    leaf extended-nexthop-color {
  //      description "Resolve using extended color nexthop";
  //      type empty;
  //    }
  //    leaf extended-nexthop-tunnel {
  //      description "Use BGP tunnel attribute";
  //      type empty;
  //    }
  //    leaf no-install {
  //      description "Dont install received routes in forwarding";
  //      type empty;
  //    }
  //    leaf route-age-bgp-view {
  //      description "Maintain BGP route's age based on Update messages only";
  //      type empty;
  //    }
  //    container output-queue-priority {
  //      description "Default output-queue to assign updates to";
  //      uses bgp-output-queue-priority-class;
  //    }
  //    container route-refresh-priority {
  //      description "Default output-queue to assign route refreshes to";
  //      uses bgp-output-queue-priority-class;
  //    }
  //    container withdraw-priority {
  //      description "Default output-queue to assign withdrawn routes to";
  //      uses bgp-output-queue-priority-class;
  //    }
  //    leaf advertise-srv6-service {
  //      description "Advertise SRv6 service";
  //      type empty;
  //    }
  //    leaf accept-srv6-service {
  //      description "Accept SRv6 service";
  //      type empty;
  //    }
  //    leaf-list no-validate {
  //      ordered-by user;
  //      description "Bypass validation procedure for routes that match policy";
  //      type jt:policy-algebra;
  //    }
  //    leaf strip-nexthop {
  //      description "Strip the next-hop from the outgoing flow update";
  //      type empty;
  //    }
  //    container legacy-redirect-ip-action {
  //      presence "enable legacy-redirect-ip-action";
  //      description "Configure legacy redirect to IP support";
  //      // uses apply-advanced;
  //      leaf receive {
  //        description "Accept legacy encoded redirect-to-ip action attribute";
  //        type empty;
  //      }
  //      leaf send {
  //        description "Advertise Redirect action as legacy redirect attribute";
  //        type empty;
  //      }
  //    }
  //    leaf secondary-independent-resolution {
  //      description "Resolve FLOW routes in VRF table independent of VPN FLOW route";
  //      type empty;
  //    }
  //  }
   grouping bgp-afi-inet-transport {
     // uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
    //  container aigp {
    //    description "Allow sending and receiving of AIGP attribute";
    //    presence "enable aigp";
    //    uses bgpaf-aigp-options;
    //  }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       // uses apply-advanced;
       leaf always-wait-for-krt-drain {
         description "Wait for KRT-queue drain for more-specific prefixes";
         type empty;
       }
       container minimum-delay {
         description "Minimum-delay to ensure KRT sees the route flash";
         // uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         // uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       // uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       // uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
    //  leaf extended-nexthop-color {
    //    description "Resolve using extended color nexthop";
    //    type empty;
    //  }
    //  leaf extended-nexthop-tunnel {
    //    description "Use BGP tunnel attribute";
    //    type empty;
    //  }
    //  leaf no-install {
    //    description "Dont install received routes in forwarding";
    //    type empty;
    //  }
    //  leaf route-age-bgp-view {
    //    description "Maintain BGP route's age based on Update messages only";
    //    type empty;
    //  }
    //  container output-queue-priority {
    //    description "Default output-queue to assign updates to";
    //    uses bgp-output-queue-priority-class;
    //  }
    //  container route-refresh-priority {
    //    description "Default output-queue to assign route refreshes to";
    //    uses bgp-output-queue-priority-class;
    //  }
    //  container withdraw-priority {
    //    description "Default output-queue to assign withdrawn routes to";
    //    uses bgp-output-queue-priority-class;
    //  }
    //  leaf advertise-srv6-service {
    //    description "Advertise SRv6 service";
    //    type empty;
    //  }
    //  leaf accept-srv6-service {
    //    description "Accept SRv6 service";
    //    type empty;
    //  }
    //  container aggregate-label {
    //    presence "enable aggregate-label";
    //    description "Aggregate labels of incoming routes with the same FEC";
    //    // uses apply-advanced;
    //    leaf community {
    //      description "Community to identify the FEC of incoming routes";
    //      type string;
    //    }
    //  }
    //  leaf per-prefix-label {
    //    description "Allocate a unique label to each advertised prefix";
    //    type empty;
    //  }
    //  leaf per-group-label {
    //    description "Advertise prefixes with unique labels per group";
    //    type empty;
    //  }
    //  container traffic-statistics {
    //    description "Collect statistics for BGP label-switched paths";
    //    presence "enable traffic-statistics";
    //    uses bgpaf-traffic-statistics;
    //  }
    //  container protection {
    //    presence "enable protection";
    //    description "Compute backup path for active nexthop failure";
    //  }
   }
  //  grouping bgp-afi-inet6-labeled {
  //    // uses apply-advanced;
  //    container prefix-limit {
  //      description "Limit maximum number of prefixes from a peer";
  //      uses bgpaf-prefix-limit;
  //    }
  //    container accepted-prefix-limit {
  //      description "Limit maximum number of prefixes accepted from a peer";
  //      uses bgpaf-accepted-prefix-limit;
  //    }
  //    container rib-group {
  //      description "Routing table group";
  //      uses rib_group_inet_type;
  //    }
  //    container add-path {
  //      description "Advertise multiple paths to peer";
  //      uses apath-options;
  //    }
  //    container aigp {
  //      description "Allow sending and receiving of AIGP attribute";
  //      presence "enable aigp";
  //      uses bgpaf-aigp-options;
  //    }
  //    leaf damping {
  //      description "Enable route flap damping";
  //      type empty;
  //    }
  //    leaf local-ipv4-address {
  //      description "Local IPv4 address";
  //      type jt:ipv4addr;
  //    }
  //    container loops {
  //      description "Allow local AS in received AS paths";
  //      uses bgpaf-loops;
  //    }
  //    container delay-route-advertisements {
  //      presence "enable delay-route-advertisements";
  //      description "Delay route updates for this family until FIB-sync";
  //      // uses apply-advanced;
  //      leaf always-wait-for-krt-drain {
  //        description "Wait for KRT-queue drain for more-specific prefixes";
  //        type empty;
  //      }
  //      container minimum-delay {
  //        description "Minimum-delay to ensure KRT sees the route flash";
  //        // uses apply-advanced;
  //        leaf routing-uptime {
  //          description "Min delay(sec) advertisement after RPD start";
  //          type union {
  //            type string {
  //              pattern "<.*>|$.*";
  //            }
  //            type uint32 {
  //              range "1 .. 36000";
  //            }
  //          }
  //        }
  //        leaf inbound-convergence {
  //          description "Min delay(sec) advertisement after source-peer sent all routes";
  //          type union {
  //            type string {
  //              pattern "<.*>|$.*";
  //            }
  //            type uint32 {
  //              range "1 .. 36000";
  //            }
  //          }
  //        }
  //      }
  //      container maximum-delay {
  //        description "Maximum delay deferring routes";
  //        // uses apply-advanced;
  //        leaf route-age {
  //          description "Max delay(sec) advertisement route age";
  //          type union {
  //            type string {
  //              pattern "<.*>|$.*";
  //            }
  //            type uint32 {
  //              range "1 .. 36000";
  //            }
  //          }
  //        }
  //        leaf routing-uptime {
  //          description "Max delay(sec) advertisement after RPD start";
  //          type union {
  //            type string {
  //              pattern "<.*>|$.*";
  //            }
  //            type uint32 {
  //              range "1 .. 36000";
  //            }
  //          }
  //        }
  //      }
  //    }
  //    container nexthop-resolution {
  //      description "Configure nexthop resolution properties";
  //      // uses apply-advanced;
  //      leaf no-resolution {
  //        description "Consider nexthop good without resolution attempt";
  //        type empty;
  //      }
  //      leaf preserve-nexthop-hierarchy {
  //        description "Attempt preserving resolved nexthop chain in forwarding";
  //        type empty;
  //      }
  //    }
  //    container defer-initial-multipath-build {
  //      presence "enable defer-initial-multipath-build";
  //      description "Defer initial multipath build until EOR is received";
  //      // uses apply-advanced;
  //      leaf maximum-delay {
  //        description "Max delay(sec) multipath build after peer is up";
  //        type union {
  //          type string {
  //            pattern "<.*>|$.*";
  //          }
  //          type uint32 {
  //            range "1 .. 3600";
  //          }
  //        }
  //      }
  //    }
  //    container graceful-restart {
  //      description "BGP graceful restart options";
  //      uses bgp-af-gr;
  //    }
  //    leaf extended-nexthop {
  //      description "Extended nexthop encoding";
  //      type empty;
  //    }
  //    leaf extended-nexthop-color {
  //      description "Resolve using extended color nexthop";
  //      type empty;
  //    }
  //    leaf extended-nexthop-tunnel {
  //      description "Use BGP tunnel attribute";
  //      type empty;
  //    }
  //    leaf no-install {
  //      description "Dont install received routes in forwarding";
  //      type empty;
  //    }
  //    leaf route-age-bgp-view {
  //      description "Maintain BGP route's age based on Update messages only";
  //      type empty;
  //    }
  //    container output-queue-priority {
  //      description "Default output-queue to assign updates to";
  //      uses bgp-output-queue-priority-class;
  //    }
  //    container route-refresh-priority {
  //      description "Default output-queue to assign route refreshes to";
  //      uses bgp-output-queue-priority-class;
  //    }
  //    container withdraw-priority {
  //      description "Default output-queue to assign withdrawn routes to";
  //      uses bgp-output-queue-priority-class;
  //    }
  //    leaf advertise-srv6-service {
  //      description "Advertise SRv6 service";
  //      type empty;
  //    }
  //    leaf accept-srv6-service {
  //      description "Accept SRv6 service";
  //      type empty;
  //    }
  //    container aggregate-label {
  //      presence "enable aggregate-label";
  //      description "Aggregate labels of incoming routes with the same FEC";
  //      // uses apply-advanced;
  //      leaf community {
  //        description "Community to identify the FEC of incoming routes";
  //        type string;
  //      }
  //    }
  //    leaf per-group-label {
  //      description "Advertise prefixes with unique labels per group";
  //      type empty;
  //    }
  //    container traffic-statistics {
  //      description "Collect statistics for BGP label-switched paths";
  //      presence "enable traffic-statistics";
  //      uses bgpaf-traffic-statistics;
  //    }
  //    container rib {
  //      description "Select table used by labeled unicast routes";
  //      // uses apply-advanced;
  //      leaf inet6.3 {
  //        description "Use inet6.3 to exchange labeled unicast routes";
  //        type empty;
  //      }
  //    }
  //    container explicit-null {
  //      presence "enable explicit-null";
  //      description "Advertise explicit null";
  //      leaf connected-only {
  //        description "Advertise explicit null only for connected routes";
  //        type empty;
  //      }
  //    }
  //    container protection {
  //      presence "enable protection";
  //      description "Compute backup path for active nexthop failure";
  //    }
  //    list topology {
  //      key name;
  //      ordered-by user;
  //      description "Multi topology routing tables";
  //      leaf name {
  //        description "Topology name";
  //        type string {
  //        }
  //      }
  //      // uses apply-advanced;
  //      leaf community {
  //        description "Community to identify multi topology routes";
  //        type string;
  //      }
  //    }
  //  }
  //  grouping bgp-afi-inet6-transport {
  //    // uses apply-advanced;
  //    container prefix-limit {
  //      description "Limit maximum number of prefixes from a peer";
  //      uses bgpaf-prefix-limit;
  //    }
  //    container accepted-prefix-limit {
  //      description "Limit maximum number of prefixes accepted from a peer";
  //      uses bgpaf-accepted-prefix-limit;
  //    }
  //    container rib-group {
  //      description "Routing table group";
  //      uses rib_group_inet_type;
  //    }
  //    container add-path {
  //      description "Advertise multiple paths to peer";
  //      uses apath-options;
  //    }
  //    container aigp {
  //      description "Allow sending and receiving of AIGP attribute";
  //      presence "enable aigp";
  //      uses bgpaf-aigp-options;
  //    }
  //    leaf damping {
  //      description "Enable route flap damping";
  //      type empty;
  //    }
  //    leaf local-ipv4-address {
  //      description "Local IPv4 address";
  //      type jt:ipv4addr;
  //    }
  //    container loops {
  //      description "Allow local AS in received AS paths";
  //      uses bgpaf-loops;
  //    }
  //    container delay-route-advertisements {
  //      presence "enable delay-route-advertisements";
  //      description "Delay route updates for this family until FIB-sync";
  //      // uses apply-advanced;
  //      leaf always-wait-for-krt-drain {
  //        description "Wait for KRT-queue drain for more-specific prefixes";
  //        type empty;
  //      }
  //      container minimum-delay {
  //        description "Minimum-delay to ensure KRT sees the route flash";
  //        // uses apply-advanced;
  //        leaf routing-uptime {
  //          description "Min delay(sec) advertisement after RPD start";
  //          type union {
  //            type string {
  //              pattern "<.*>|$.*";
  //            }
  //            type uint32 {
  //              range "1 .. 36000";
  //            }
  //          }
  //        }
  //        leaf inbound-convergence {
  //          description "Min delay(sec) advertisement after source-peer sent all routes";
  //          type union {
  //            type string {
  //              pattern "<.*>|$.*";
  //            }
  //            type uint32 {
  //              range "1 .. 36000";
  //            }
  //          }
  //        }
  //      }
  //      container maximum-delay {
  //        description "Maximum delay deferring routes";
  //        // uses apply-advanced;
  //        leaf route-age {
  //          description "Max delay(sec) advertisement route age";
  //          type union {
  //            type string {
  //              pattern "<.*>|$.*";
  //            }
  //            type uint32 {
  //              range "1 .. 36000";
  //            }
  //          }
  //        }
  //        leaf routing-uptime {
  //          description "Max delay(sec) advertisement after RPD start";
  //          type union {
  //            type string {
  //              pattern "<.*>|$.*";
  //            }
  //            type uint32 {
  //              range "1 .. 36000";
  //            }
  //          }
  //        }
  //      }
  //    }
  //    container nexthop-resolution {
  //      description "Configure nexthop resolution properties";
  //      // uses apply-advanced;
  //      leaf no-resolution {
  //        description "Consider nexthop good without resolution attempt";
  //        type empty;
  //      }
  //      leaf preserve-nexthop-hierarchy {
  //        description "Attempt preserving resolved nexthop chain in forwarding";
  //        type empty;
  //      }
  //    }
  //    container defer-initial-multipath-build {
  //      presence "enable defer-initial-multipath-build";
  //      description "Defer initial multipath build until EOR is received";
  //      // uses apply-advanced;
  //      leaf maximum-delay {
  //        description "Max delay(sec) multipath build after peer is up";
  //        type union {
  //          type string {
  //            pattern "<.*>|$.*";
  //          }
  //          type uint32 {
  //            range "1 .. 3600";
  //          }
  //        }
  //      }
  //    }
  //    container graceful-restart {
  //      description "BGP graceful restart options";
  //      uses bgp-af-gr;
  //    }
  //    leaf extended-nexthop {
  //      description "Extended nexthop encoding";
  //      type empty;
  //    }
  //    leaf extended-nexthop-color {
  //      description "Resolve using extended color nexthop";
  //      type empty;
  //    }
  //    leaf extended-nexthop-tunnel {
  //      description "Use BGP tunnel attribute";
  //      type empty;
  //    }
  //    leaf no-install {
  //      description "Dont install received routes in forwarding";
  //      type empty;
  //    }
  //    leaf route-age-bgp-view {
  //      description "Maintain BGP route's age based on Update messages only";
  //      type empty;
  //    }
  //    container output-queue-priority {
  //      description "Default output-queue to assign updates to";
  //      uses bgp-output-queue-priority-class;
  //    }
  //    container route-refresh-priority {
  //      description "Default output-queue to assign route refreshes to";
  //      uses bgp-output-queue-priority-class;
  //    }
  //    container withdraw-priority {
  //      description "Default output-queue to assign withdrawn routes to";
  //      uses bgp-output-queue-priority-class;
  //    }
  //    leaf advertise-srv6-service {
  //      description "Advertise SRv6 service";
  //      type empty;
  //    }
  //    leaf accept-srv6-service {
  //      description "Accept SRv6 service";
  //      type empty;
  //    }
  //    container aggregate-label {
  //      presence "enable aggregate-label";
  //      description "Aggregate labels of incoming routes with the same FEC";
  //      // uses apply-advanced;
  //      leaf community {
  //        description "Community to identify the FEC of incoming routes";
  //        type string;
  //      }
  //    }
  //    leaf per-prefix-label {
  //      description "Allocate a unique label to each advertised prefix";
  //      type empty;
  //    }
  //    leaf per-group-label {
  //      description "Advertise prefixes with unique labels per group";
  //      type empty;
  //    }
  //    container traffic-statistics {
  //      description "Collect statistics for BGP label-switched paths";
  //      presence "enable traffic-statistics";
  //      uses bgpaf-traffic-statistics;
  //    }
  //    container lu-export {
  //      presence "enable lu-export";
  //      description "Install Classful Transport routes in inet6.3";
  //      // uses apply-advanced;
  //    }
  //    container protection {
  //      presence "enable protection";
  //      description "Compute backup path for active nexthop failure";
  //    }
  //  }
  //  grouping bgp-afi-l2vpn {
  //    // uses apply-advanced;
  //    container prefix-limit {
  //      description "Limit maximum number of prefixes from a peer";
  //      uses bgpaf-prefix-limit;
  //    }
  //    container accepted-prefix-limit {
  //      description "Limit maximum number of prefixes accepted from a peer";
  //      uses bgpaf-accepted-prefix-limit;
  //    }
  //    container rib-group {
  //      description "Routing table group";
  //      uses rib_group_inet_type;
  //    }
  //    container add-path {
  //      description "Advertise multiple paths to peer";
  //      uses apath-options;
  //    }
  //    container aigp {
  //      description "Allow sending and receiving of AIGP attribute";
  //      presence "enable aigp";
  //      uses bgpaf-aigp-options;
  //    }
  //    leaf damping {
  //      description "Enable route flap damping";
  //      type empty;
  //    }
  //    leaf local-ipv4-address {
  //      description "Local IPv4 address";
  //      type jt:ipv4addr;
  //    }
  //    container loops {
  //      description "Allow local AS in received AS paths";
  //      uses bgpaf-loops;
  //    }
  //    container delay-route-advertisements {
  //      presence "enable delay-route-advertisements";
  //      description "Delay route updates for this family until FIB-sync";
  //      // uses apply-advanced;
  //      leaf always-wait-for-krt-drain {
  //        description "Wait for KRT-queue drain for more-specific prefixes";
  //        type empty;
  //      }
  //      container minimum-delay {
  //        description "Minimum-delay to ensure KRT sees the route flash";
  //        // uses apply-advanced;
  //        leaf routing-uptime {
  //          description "Min delay(sec) advertisement after RPD start";
  //          type union {
  //            type string {
  //              pattern "<.*>|$.*";
  //            }
  //            type uint32 {
  //              range "1 .. 36000";
  //            }
  //          }
  //        }
  //        leaf inbound-convergence {
  //          description "Min delay(sec) advertisement after source-peer sent all routes";
  //          type union {
  //            type string {
  //              pattern "<.*>|$.*";
  //            }
  //            type uint32 {
  //              range "1 .. 36000";
  //            }
  //          }
  //        }
  //      }
  //      container maximum-delay {
  //        description "Maximum delay deferring routes";
  //        // uses apply-advanced;
  //        leaf route-age {
  //          description "Max delay(sec) advertisement route age";
  //          type union {
  //            type string {
  //              pattern "<.*>|$.*";
  //            }
  //            type uint32 {
  //              range "1 .. 36000";
  //            }
  //          }
  //        }
  //        leaf routing-uptime {
  //          description "Max delay(sec) advertisement after RPD start";
  //          type union {
  //            type string {
  //              pattern "<.*>|$.*";
  //            }
  //            type uint32 {
  //              range "1 .. 36000";
  //            }
  //          }
  //        }
  //      }
  //    }
  //    container nexthop-resolution {
  //      description "Configure nexthop resolution properties";
  //      // uses apply-advanced;
  //      leaf no-resolution {
  //        description "Consider nexthop good without resolution attempt";
  //        type empty;
  //      }
  //      leaf preserve-nexthop-hierarchy {
  //        description "Attempt preserving resolved nexthop chain in forwarding";
  //        type empty;
  //      }
  //    }
  //    container defer-initial-multipath-build {
  //      presence "enable defer-initial-multipath-build";
  //      description "Defer initial multipath build until EOR is received";
  //      // uses apply-advanced;
  //      leaf maximum-delay {
  //        description "Max delay(sec) multipath build after peer is up";
  //        type union {
  //          type string {
  //            pattern "<.*>|$.*";
  //          }
  //          type uint32 {
  //            range "1 .. 3600";
  //          }
  //        }
  //      }
  //    }
  //    container graceful-restart {
  //      description "BGP graceful restart options";
  //      uses bgp-af-gr;
  //    }
  //    leaf extended-nexthop {
  //      description "Extended nexthop encoding";
  //      type empty;
  //    }
  //    leaf extended-nexthop-color {
  //      description "Resolve using extended color nexthop";
  //      type empty;
  //    }
  //    leaf extended-nexthop-tunnel {
  //      description "Use BGP tunnel attribute";
  //      type empty;
  //    }
  //    leaf no-install {
  //      description "Dont install received routes in forwarding";
  //      type empty;
  //    }
  //    leaf route-age-bgp-view {
  //      description "Maintain BGP route's age based on Update messages only";
  //      type empty;
  //    }
  //    container output-queue-priority {
  //      description "Default output-queue to assign updates to";
  //      uses bgp-output-queue-priority-class;
  //    }
  //    container route-refresh-priority {
  //      description "Default output-queue to assign route refreshes to";
  //      uses bgp-output-queue-priority-class;
  //    }
  //    container withdraw-priority {
  //      description "Default output-queue to assign withdrawn routes to";
  //      uses bgp-output-queue-priority-class;
  //    }
  //    leaf advertise-srv6-service {
  //      description "Advertise SRv6 service";
  //      type empty;
  //    }
  //    leaf accept-srv6-service {
  //      description "Accept SRv6 service";
  //      type empty;
  //    }
  //    container egress-protection {
  //      presence "enable egress-protection";
  //      description "Egress router protection";
  //      // uses apply-advanced;
  //      container context-identifier {
  //        description "Context identifier";
  //        // uses apply-advanced;
  //        leaf context-id {
  //          description "IP address";
  //          type jt:ipv4addr;
  //        }
  //      }
  //      leaf-list keep-import {
  //        ordered-by user;
  //        description "Import policy";
  //        type jt:policy-algebra;
  //      }
  //    }
  //  }
   grouping bgp-afi-l3vpn {
     // uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
    //  container aigp {
    //    description "Allow sending and receiving of AIGP attribute";
    //    presence "enable aigp";
    //    uses bgpaf-aigp-options;
    //  }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       // uses apply-advanced;
       leaf always-wait-for-krt-drain {
         description "Wait for KRT-queue drain for more-specific prefixes";
         type empty;
       }
       container minimum-delay {
         description "Minimum-delay to ensure KRT sees the route flash";
         // uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         // uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       // uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       // uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
    //  leaf extended-nexthop-color {
    //    description "Resolve using extended color nexthop";
    //    type empty;
    //  }
    //  leaf extended-nexthop-tunnel {
    //    description "Use BGP tunnel attribute";
    //    type empty;
    //  }
    //  leaf no-install {
    //    description "Dont install received routes in forwarding";
    //    type empty;
    //  }
    //  leaf route-age-bgp-view {
    //    description "Maintain BGP route's age based on Update messages only";
    //    type empty;
    //  }
    //  container output-queue-priority {
    //    description "Default output-queue to assign updates to";
    //    uses bgp-output-queue-priority-class;
    //  }
    //  container route-refresh-priority {
    //    description "Default output-queue to assign route refreshes to";
    //    uses bgp-output-queue-priority-class;
    //  }
    //  container withdraw-priority {
    //    description "Default output-queue to assign withdrawn routes to";
    //    uses bgp-output-queue-priority-class;
    //  }
    //  leaf advertise-srv6-service {
    //    description "Advertise SRv6 service";
    //    type empty;
    //  }
    //  leaf accept-srv6-service {
    //    description "Accept SRv6 service";
    //    type empty;
    //  }
    //  container aggregate-label {
    //    presence "enable aggregate-label";
    //    description "Aggregate labels of incoming routes with the same FEC";
    //    // uses apply-advanced;
    //    leaf community {
    //      description "Community to identify the FEC of incoming routes";
    //      type string;
    //    }
    //  }
    //  container egress-protection {
    //    presence "enable egress-protection";
    //    description "Egress router protection";
    //    // uses apply-advanced;
    //    container context-identifier {
    //      description "Context identifier";
    //      // uses apply-advanced;
    //      leaf context-id {
    //        description "IP address";
    //        type jt:ipv4addr;
    //      }
    //    }
    //    leaf-list keep-import {
    //      ordered-by user;
    //      description "Import policy";
    //      type jt:policy-algebra;
    //    }
    //  }
    //  leaf accept-local-nexthop {
    //    description "Enable processing of routes with own nexthop";
    //    type empty;
    //  }
    //  leaf accept-own {
    //    description "Enable processing of routes with own originator-id or nexthop";
    //    type empty;
    //  }
   }
   grouping bgp-afi-labeled {
     // uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
    //  container aigp {
    //    description "Allow sending and receiving of AIGP attribute";
    //    presence "enable aigp";
    //    uses bgpaf-aigp-options;
    //  }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       // uses apply-advanced;
       leaf always-wait-for-krt-drain {
         description "Wait for KRT-queue drain for more-specific prefixes";
         type empty;
       }
       container minimum-delay {
         description "Minimum-delay to ensure KRT sees the route flash";
         // uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         // uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       // uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       // uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
    //  leaf extended-nexthop-color {
    //    description "Resolve using extended color nexthop";
    //    type empty;
    //  }
    //  leaf extended-nexthop-tunnel {
    //    description "Use BGP tunnel attribute";
    //    type empty;
    //  }
    //  leaf no-install {
    //    description "Dont install received routes in forwarding";
    //    type empty;
    //  }
    //  leaf route-age-bgp-view {
    //    description "Maintain BGP route's age based on Update messages only";
    //    type empty;
    //  }
    //  container output-queue-priority {
    //    description "Default output-queue to assign updates to";
    //    uses bgp-output-queue-priority-class;
    //  }
    //  container route-refresh-priority {
    //    description "Default output-queue to assign route refreshes to";
    //    uses bgp-output-queue-priority-class;
    //  }
    //  container withdraw-priority {
    //    description "Default output-queue to assign withdrawn routes to";
    //    uses bgp-output-queue-priority-class;
    //  }
    //  leaf advertise-srv6-service {
    //    description "Advertise SRv6 service";
    //    type empty;
    //  }
    //  leaf accept-srv6-service {
    //    description "Accept SRv6 service";
    //    type empty;
    //  }
    //  container aggregate-label {
    //    presence "enable aggregate-label";
    //    description "Aggregate labels of incoming routes with the same FEC";
    //    // uses apply-advanced;
    //    leaf community {
    //      description "Community to identify the FEC of incoming routes";
    //      type string;
    //    }
    //  }
    //  leaf per-prefix-label {
    //    description "Allocate a unique label to each advertised prefix";
    //    type empty;
    //  }
    //  leaf per-group-label {
    //    description "Advertise prefixes with unique labels per group";
    //    type empty;
    //  }
    //  container traffic-statistics {
    //    description "Collect statistics for BGP label-switched paths";
    //    presence "enable traffic-statistics";
    //    uses bgpaf-traffic-statistics;
    //  }
    //  list topology {
    //    key name;
    //    ordered-by user;
    //    description "Multi topology routing tables";
    //    leaf name {
    //      description "Topology name";
    //      type string {
    //      }
    //    }
    //    // uses apply-advanced;
    //    leaf community {
    //      description "Community to identify multi topology routes";
    //      type string;
    //    }
    //  }
    //  container rib {
    //    description "Select table used by labeled unicast routes";
    //    uses rib-inet3;
    //  }
    //  container explicit-null {
    //    presence "enable explicit-null";
    //    description "Advertise explicit null";
    //    leaf connected-only {
    //      description "Advertise explicit null only for connected routes";
    //      type empty;
    //    }
    //  }
    //  container protection {
    //    presence "enable protection";
    //    description "Compute backup path for active nexthop failure";
    //    // uses apply-advanced;
    //  }
    //  container egress-protection {
    //    presence "enable egress-protection";
    //    description "Egress router protection";
    //    // uses apply-advanced;
    //    container context-identifier {
    //      description "Context identifier";
    //      // uses apply-advanced;
    //      leaf context-id {
    //        description "IP address";
    //        type jt:ipv4addr;
    //      }
    //    }
    //    leaf-list keep-import {
    //      ordered-by user;
    //      description "Import policy";
    //      type jt:policy-algebra;
    //    }
    //  }
    //  leaf resolve-vpn {
    //    description "Install received NLRI in inet.3 also";
    //    type empty;
    //  }
    //  container entropy-label {
    //    presence "enable entropy-label";
    //    description "Use entropy label for entropy label capable BGP LSPs";
    //    // uses apply-advanced;
    //    leaf-list import {
    //      ordered-by user;
    //      description "Policy to select BGP LSPs to use entropy label";
    //      type jt:policy-algebra;
    //    }
    //    leaf no-next-hop-validation {
    //      description "Don't validate next hop field against route next hop";
    //      type empty;
    //    }
    //    leaf elc-v2-compatible {
    //      description "Send and accept ELCv2 in addition to ELCv3";
    //      type empty;
    //    }
    //  }
   }
  //  grouping bgp-afi-srte {
  //    // uses apply-advanced;
  //    container prefix-limit {
  //      description "Limit maximum number of prefixes from a peer";
  //      uses bgpaf-prefix-limit;
  //    }
  //    container accepted-prefix-limit {
  //      description "Limit maximum number of prefixes accepted from a peer";
  //      uses bgpaf-accepted-prefix-limit;
  //    }
  //    leaf damping {
  //      description "Enable route flap damping";
  //      type empty;
  //    }
  //    container loops {
  //      description "Allow local AS in received AS paths";
  //      uses bgpaf-loops;
  //    }
  //    container graceful-restart {
  //      description "BGP graceful restart options";
  //      uses bgp-af-gr;
  //    }
  //    leaf no-install {
  //      description "Dont install received routes in forwarding";
  //      type empty;
  //    }
  //    container output-queue-priority {
  //      description "Default output-queue to assign updates to";
  //      uses bgp-output-queue-priority-class;
  //    }
  //    container route-refresh-priority {
  //      description "Default output-queue to assign route refreshes to";
  //      uses bgp-output-queue-priority-class;
  //    }
  //    container withdraw-priority {
  //      description "Default output-queue to assign withdrawn routes to";
  //      uses bgp-output-queue-priority-class;
  //    }
  //  }
   grouping bgp-afi-topo {
     // uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
    //  container aigp {
    //    description "Allow sending and receiving of AIGP attribute";
    //    presence "enable aigp";
    //    uses bgpaf-aigp-options;
    //  }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       // uses apply-advanced;
       leaf always-wait-for-krt-drain {
         description "Wait for KRT-queue drain for more-specific prefixes";
         type empty;
       }
       container minimum-delay {
         description "Minimum-delay to ensure KRT sees the route flash";
         // uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         // uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       // uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       // uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
    //  leaf extended-nexthop-color {
    //    description "Resolve using extended color nexthop";
    //    type empty;
    //  }
    //  leaf extended-nexthop-tunnel {
    //    description "Use BGP tunnel attribute";
    //    type empty;
    //  }
    //  leaf no-install {
    //    description "Dont install received routes in forwarding";
    //    type empty;
    //  }
    //  leaf route-age-bgp-view {
    //    description "Maintain BGP route's age based on Update messages only";
    //    type empty;
    //  }
    //  container output-queue-priority {
    //    description "Default output-queue to assign updates to";
    //    uses bgp-output-queue-priority-class;
    //  }
    //  container route-refresh-priority {
    //    description "Default output-queue to assign route refreshes to";
    //    uses bgp-output-queue-priority-class;
    //  }
    //  container withdraw-priority {
    //    description "Default output-queue to assign withdrawn routes to";
    //    uses bgp-output-queue-priority-class;
    //  }
    //  leaf advertise-srv6-service {
    //    description "Advertise SRv6 service";
    //    type empty;
    //  }
    //  leaf accept-srv6-service {
    //    description "Accept SRv6 service";
    //    type empty;
    //  }
    //  container protection {
    //    presence "enable protection";
    //    description "Compute backup path for active nexthop failure";
    //  }
    //  list topology {
    //    key name;
    //    ordered-by user;
    //    description "Multi topology routing tables";
    //    leaf name {
    //      description "Topology name";
    //      type string {
    //      }
    //    }
    //    // uses apply-advanced;
    //    leaf community {
    //      description "Community to identify multi topology routes";
    //      type string;
    //    }
    //  }
   }
   grouping bgp-afi-vpn {
     // uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
    //  container aigp {
    //    description "Allow sending and receiving of AIGP attribute";
    //    presence "enable aigp";
    //    uses bgpaf-aigp-options;
    //  }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       // uses apply-advanced;
       leaf always-wait-for-krt-drain {
         description "Wait for KRT-queue drain for more-specific prefixes";
         type empty;
       }
       container minimum-delay {
         description "Minimum-delay to ensure KRT sees the route flash";
         // uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         // uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       // uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       // uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
    //  leaf extended-nexthop-color {
    //    description "Resolve using extended color nexthop";
    //    type empty;
    //  }
    //  leaf extended-nexthop-tunnel {
    //    description "Use BGP tunnel attribute";
    //    type empty;
    //  }
    //  leaf no-install {
    //    description "Dont install received routes in forwarding";
    //    type empty;
    //  }
    //  leaf route-age-bgp-view {
    //    description "Maintain BGP route's age based on Update messages only";
    //    type empty;
    //  }
    //  container output-queue-priority {
    //    description "Default output-queue to assign updates to";
    //    uses bgp-output-queue-priority-class;
    //  }
    //  container route-refresh-priority {
    //    description "Default output-queue to assign route refreshes to";
    //    uses bgp-output-queue-priority-class;
    //  }
    //  container withdraw-priority {
    //    description "Default output-queue to assign withdrawn routes to";
    //    uses bgp-output-queue-priority-class;
    //  }
    //  leaf advertise-srv6-service {
    //    description "Advertise SRv6 service";
    //    type empty;
    //  }
    //  leaf accept-srv6-service {
    //    description "Accept SRv6 service";
    //    type empty;
    //  }
    //  container aggregate-label {
    //    presence "enable aggregate-label";
    //    description "Aggregate labels of incoming routes with the same FEC";
    //    // uses apply-advanced;
    //    leaf community {
    //      description "Community to identify the FEC of incoming routes";
    //      type string;
    //    }
    //  }
   }
  //  grouping bgp-afi-vpn-protection {
  //    // uses apply-advanced;
  //    container prefix-limit {
  //      description "Limit maximum number of prefixes from a peer";
  //      uses bgpaf-prefix-limit;
  //    }
  //    container accepted-prefix-limit {
  //      description "Limit maximum number of prefixes accepted from a peer";
  //      uses bgpaf-accepted-prefix-limit;
  //    }
  //    container rib-group {
  //      description "Routing table group";
  //      uses rib_group_inet_type;
  //    }
  //    container add-path {
  //      description "Advertise multiple paths to peer";
  //      uses apath-options;
  //    }
  //    container aigp {
  //      description "Allow sending and receiving of AIGP attribute";
  //      presence "enable aigp";
  //      uses bgpaf-aigp-options;
  //    }
  //    leaf damping {
  //      description "Enable route flap damping";
  //      type empty;
  //    }
  //    leaf local-ipv4-address {
  //      description "Local IPv4 address";
  //      type jt:ipv4addr;
  //    }
  //    container loops {
  //      description "Allow local AS in received AS paths";
  //      uses bgpaf-loops;
  //    }
  //    container delay-route-advertisements {
  //      presence "enable delay-route-advertisements";
  //      description "Delay route updates for this family until FIB-sync";
  //      // uses apply-advanced;
  //      leaf always-wait-for-krt-drain {
  //        description "Wait for KRT-queue drain for more-specific prefixes";
  //        type empty;
  //      }
  //      container minimum-delay {
  //        description "Minimum-delay to ensure KRT sees the route flash";
  //        // uses apply-advanced;
  //        leaf routing-uptime {
  //          description "Min delay(sec) advertisement after RPD start";
  //          type union {
  //            type string {
  //              pattern "<.*>|$.*";
  //            }
  //            type uint32 {
  //              range "1 .. 36000";
  //            }
  //          }
  //        }
  //        leaf inbound-convergence {
  //          description "Min delay(sec) advertisement after source-peer sent all routes";
  //          type union {
  //            type string {
  //              pattern "<.*>|$.*";
  //            }
  //            type uint32 {
  //              range "1 .. 36000";
  //            }
  //          }
  //        }
  //      }
  //      container maximum-delay {
  //        description "Maximum delay deferring routes";
  //        // uses apply-advanced;
  //        leaf route-age {
  //          description "Max delay(sec) advertisement route age";
  //          type union {
  //            type string {
  //              pattern "<.*>|$.*";
  //            }
  //            type uint32 {
  //              range "1 .. 36000";
  //            }
  //          }
  //        }
  //        leaf routing-uptime {
  //          description "Max delay(sec) advertisement after RPD start";
  //          type union {
  //            type string {
  //              pattern "<.*>|$.*";
  //            }
  //            type uint32 {
  //              range "1 .. 36000";
  //            }
  //          }
  //        }
  //      }
  //    }
  //    container nexthop-resolution {
  //      description "Configure nexthop resolution properties";
  //      // uses apply-advanced;
  //      leaf no-resolution {
  //        description "Consider nexthop good without resolution attempt";
  //        type empty;
  //      }
  //      leaf preserve-nexthop-hierarchy {
  //        description "Attempt preserving resolved nexthop chain in forwarding";
  //        type empty;
  //      }
  //    }
  //    container defer-initial-multipath-build {
  //      presence "enable defer-initial-multipath-build";
  //      description "Defer initial multipath build until EOR is received";
  //      // uses apply-advanced;
  //      leaf maximum-delay {
  //        description "Max delay(sec) multipath build after peer is up";
  //        type union {
  //          type string {
  //            pattern "<.*>|$.*";
  //          }
  //          type uint32 {
  //            range "1 .. 3600";
  //          }
  //        }
  //      }
  //    }
  //    container graceful-restart {
  //      description "BGP graceful restart options";
  //      uses bgp-af-gr;
  //    }
  //    leaf extended-nexthop {
  //      description "Extended nexthop encoding";
  //      type empty;
  //    }
  //    leaf extended-nexthop-color {
  //      description "Resolve using extended color nexthop";
  //      type empty;
  //    }
  //    leaf extended-nexthop-tunnel {
  //      description "Use BGP tunnel attribute";
  //      type empty;
  //    }
  //    leaf no-install {
  //      description "Dont install received routes in forwarding";
  //      type empty;
  //    }
  //    leaf route-age-bgp-view {
  //      description "Maintain BGP route's age based on Update messages only";
  //      type empty;
  //    }
  //    container output-queue-priority {
  //      description "Default output-queue to assign updates to";
  //      uses bgp-output-queue-priority-class;
  //    }
  //    container route-refresh-priority {
  //      description "Default output-queue to assign route refreshes to";
  //      uses bgp-output-queue-priority-class;
  //    }
  //    container withdraw-priority {
  //      description "Default output-queue to assign withdrawn routes to";
  //      uses bgp-output-queue-priority-class;
  //    }
  //    leaf advertise-srv6-service {
  //      description "Advertise SRv6 service";
  //      type empty;
  //    }
  //    leaf accept-srv6-service {
  //      description "Accept SRv6 service";
  //      type empty;
  //    }
  //    container aggregate-label {
  //      presence "enable aggregate-label";
  //      description "Aggregate labels of incoming routes with the same FEC";
  //      // uses apply-advanced;
  //      leaf community {
  //        description "Community to identify the FEC of incoming routes";
  //        type string;
  //      }
  //    }
  //    container egress-protection {
  //      presence "enable egress-protection";
  //      description "Egress router protection";
  //      // uses apply-advanced;
  //      container context-identifier {
  //        description "Context identifier";
  //        // uses apply-advanced;
  //        leaf context-id {
  //          description "IP address";
  //          type jt:ipv4addr;
  //        }
  //      }
  //      leaf-list keep-import {
  //        ordered-by user;
  //        description "Import policy";
  //        type jt:policy-algebra;
  //      }
  //    }
  //  }
  //  grouping bgp-output-queue-priority-class {
  //    choice class {
  //      case case_1 {
  //        leaf priority {
  //          description "Output queue priority; higher is better";
  //          type union {
  //            type string {
  //              pattern "<.*>|$.*";
  //            }
  //            type uint32 {
  //              range "1 .. 16";
  //            }
  //          }
  //        }
  //      }
  //      case case_2 {
  //        leaf expedited {
  //          description "Expedited queue; highest priority";
  //          type empty;
  //        }
  //      }
  //    }
  //  }
   grouping bgp_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping bgpaf-accepted-prefix-limit {
     // uses apply-advanced;
     leaf maximum {
       description "Maximum number of prefixes accepted from a peer";
       type union {
         type string {
           pattern "<.*>|$.*";
         }
         type uint32 {
           range "1 .. 4294967295";
         }
       }
     }
     container teardown {
       presence "enable teardown";
       description "Clear peer connection on reaching limit";
       // uses apply-advanced;
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
     container drop-excess {
       presence "enable drop-excess";
       description "Drop routes from peer on reaching limit";
       // uses apply-advanced;
       leaf limit-threshold {
         description "Percentage of prefix-limit to start warnings";
         type union {
           type string {
             pattern "<.*>|$.*";
           }
           type uint32 {
             range "1 .. 100";
           }
         }
       }
     }
     container hide-excess {
       presence "enable hide-excess";
       description "Hide routes from peer on reaching limit";
       // uses apply-advanced;
       leaf limit-threshold {
         description "Percentage of prefix-limit to start warnings";
         type union {
           type string {
             pattern "<.*>|$.*";
           }
           type uint32 {
             range "1 .. 100";
           }
         }
       }
     }
   }
  //  grouping bgpaf-aigp-options {
  //    // uses apply-advanced;
  //    leaf disable {
  //      description "Disable sending and receiving of AIGP attribute";
  //      type empty;
  //    }
  //  }
   grouping bgpaf-loops {
     // uses apply-advanced;
     leaf loops {
       description "AS-Path loop count";
       type union {
         type string {
           pattern "<.*>|$.*";
         }
         type int32 {
           range "1 .. 10";
         }
       }
     }
   }
   grouping bgpaf-prefix-limit {
     // uses apply-advanced;
     leaf maximum {
       description "Maximum number of prefixes from a peer";
       type union {
         type string {
           pattern "<.*>|$.*";
         }
         type uint32 {
           range "1 .. 4294967295";
         }
       }
     }
     container teardown {
       presence "enable teardown";
       description "Clear peer connection on reaching limit";
       // uses apply-advanced;
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
     container drop-excess {
       presence "enable drop-excess";
       description "Drop routes from peer on reaching limit";
       // uses apply-advanced;
       leaf limit-threshold {
         description "Percentage of prefix-limit to start warnings";
         type union {
           type string {
             pattern "<.*>|$.*";
           }
           type uint32 {
             range "1 .. 100";
           }
         }
       }
     }
     container hide-excess {
       presence "enable hide-excess";
       description "Hide routes from peer on reaching limit";
       // uses apply-advanced;
       leaf limit-threshold {
         description "Percentage of prefix-limit to start warnings";
         type union {
           type string {
             pattern "<.*>|$.*";
           }
           type uint32 {
             range "1 .. 100";
           }
         }
       }
     }
   }
  //  grouping bgpaf-traffic-statistics {
  //    // uses apply-advanced;
  //    leaf labeled-path {
  //      description "Ingress labeled path statistics";
  //      type empty;
  //    }
  //    container file {
  //      description "Statistics file options";
  //      leaf filename {
  //        description "Name of file in which to write trace information";
  //        type string {
  //          length "1 .. 1024";
  //        }
  //      }
  //      leaf replace {
  //        description "Replace trace file rather than appending to it";
  //        status deprecated;
  //        type empty;
  //      }
  //      leaf size {
  //        description "Maximum trace file size";
  //        type string;
  //      }
  //      leaf files {
  //        description "Maximum number of trace files";
  //        default "10";
  //        type union {
  //          type string {
  //            pattern "<.*>|$.*";
  //          }
  //          type uint32 {
  //            range "2 .. 1000";
  //          }
  //        }
  //      }
  //      leaf no-stamp {
  //        description "Do not timestamp trace file";
  //        status deprecated;
  //        type empty;
  //      }
  //      choice world-readable-choice {
  //        leaf world-readable {
  //          description "Allow any user to read the log file";
  //          type empty;
  //        }
  //        leaf no-world-readable {
  //          description "Don't allow any user to read the log file";
  //          type empty;
  //        }
  //      }
  //    }
  //    leaf interval {
  //      description "Time to collect statistics (seconds)";
  //      type union {
  //        type string {
  //          pattern "<.*>|$.*";
  //        }
  //        type int32 {
  //          range "60 .. 65535";
  //        }
  //      }
  //    }
  //  }
  //  grouping juniper-protocols-esis {
  //    // uses apply-advanced;
  //    choice enable-disable {
  //      case case_1 {
  //        leaf disable {
  //          description "Disable ES-IS";
  //          type empty;
  //        }
  //      }
  //    }
  //    container traceoptions {
  //      description "Trace options for ES-IS";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "error" {
  //              description "Trace errored packets";
  //            }
  //            enum "esh" {
  //              description "Trace end system hello packets";
  //            }
  //            enum "ish" {
  //              description "Trace intermediate system hello packets";
  //            }
  //            enum "graceful-restart" {
  //              description "Trace graceful restart events";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    leaf preference {
  //      description "Preference of routes";
  //      type union {
  //        type uint32;
  //        type string {
  //          pattern "<.*>|$.*";
  //        }
  //      }
  //    }
  //    container graceful-restart {
  //      description "ES-IS graceful restart options";
  //      choice enable-disable {
  //        case case_1 {
  //          leaf disable {
  //            description "Disable graceful restart";
  //            type empty;
  //          }
  //        }
  //      }
  //      leaf restart-duration {
  //        description "Maximum time for graceful restart to finish";
  //        units "seconds";
  //        type union {
  //          type string {
  //            pattern "<.*>|$.*";
  //          }
  //          type uint32 {
  //            range "30 .. 300";
  //          }
  //        }
  //      }
  //    }
  //    list interface {
  //      key name;
  //      description "Interface configuration";
  //      leaf name {
  //        description "Interface name";
  //        type union {
  //          type jt:interface-name;
  //          type string {
  //            pattern "<.*>|$.*";
  //          }
  //        }
  //      }
  //      // uses apply-advanced;
  //      leaf hold-time {
  //        description "Time after which neighbors think the interface is down";
  //        units "seconds";
  //        type union {
  //          type string {
  //            pattern "<.*>|$.*";
  //          }
  //          type uint32 {
  //            range "1 .. 65535";
  //          }
  //        }
  //      }
  //      leaf end-system-configuration-timer {
  //        description "Suggested end system configuration timer";
  //        units "seconds";
  //        type union {
  //          type string {
  //            pattern "<.*>|$.*";
  //          }
  //          type uint32 {
  //            range "1 .. 65535";
  //          }
  //        }
  //      }
  //      choice enable-disable {
  //        case case_1 {
  //          leaf disable {
  //            description "Disable ES-IS on this interface";
  //            type empty;
  //          }
  //        }
  //      }
  //    }
  //  }
  //  grouping juniper-protocols-isis {
  //    // uses apply-advanced;
  //    list interface {
  //      key name;
  //      description "Interface configuration";
  //      leaf name {
  //        description "Interface name";
  //        type union {
  //          type jt:interface-name;
  //          type string {
  //            pattern "<.*>|$.*";
  //          }
  //        }
  //      }
  //      // uses apply-advanced;
  //      container ldp-synchronization {
  //        description "Advertise maximum metric until LDP is operational";
  //        presence "enable ldp-synchronization";
  //        uses ldp-sync-obj;
  //      }
  //      list level {
  //        key name;
  //        ordered-by user;
  //        description "Configure levels on this interface";
  //        leaf name {
  //          description "IS-IS level number";
  //          type union {
  //            type string {
  //              pattern "<.*>|$.*";
  //            }
  //            type uint32 {
  //              range "1 .. 2";
  //            }
  //          }
  //        }
  //        // uses apply-advanced;
  //        leaf te-metric {
  //          description "Traffic engineering metric";
  //          type union {
  //            type string {
  //              pattern "<.*>|$.*";
  //            }
  //            type uint32 {
  //              range "0 .. 16777215";
  //            }
  //          }
  //        }
  //        leaf no-advertise-adjacency-segment {
  //          description "Do not advertise an adjacency segment for this level";
  //          type empty;
  //        }
  //        container ipv4-adjacency-segment {
  //          description "Configure ipv4 adjacency segment";
  //          // uses apply-advanced;
  //          container protected {
  //            description "Adjacency SID is eligible for protection";
  //            choice adjsid-type {
  //              case case_1 {
  //                container index {
  //                  description "Adjacency SID indexed from SRGB";
  //                  leaf index-number {
  //                    type union {
  //                      type string {
  //                        pattern "<.*>|$.*";
  //                      }
  //                      type uint32 {
  //                        range "0 .. 199999";
  //                      }
  //                    }
  //                  }
  //                }
  //              }
  //              case case_2 {
  //                leaf label {
  //                  description "Adjacency SID from static label pool";
  //                  type union {
  //                    type string {
  //                      pattern "<.*>|$.*";
  //                    }
  //                    type uint32 {
  //                      range "16 .. 1048575";
  //                    }
  //                  }
  //                }
  //              }
  //              case case_3 {
  //                leaf dynamic {
  //                  description "Dynamically allocate an adjacency segment";
  //                  type empty;
  //                }
  //              }
  //            }
  //          }
  //          container unprotected {
  //            description "Adjacency SID uneligible for protection";
  //            choice adjsid-type {
  //              case case_1 {
  //                container index {
  //                  description "Adjacency SID indexed from SRGB";
  //                  leaf index-number {
  //                    type union {
  //                      type string {
  //                        pattern "<.*>|$.*";
  //                      }
  //                      type uint32 {
  //                        range "0 .. 199999";
  //                      }
  //                    }
  //                  }
  //                }
  //              }
  //              case case_2 {
  //                leaf label {
  //                  description "Adjacency SID from static label pool";
  //                  type union {
  //                    type string {
  //                      pattern "<.*>|$.*";
  //                    }
  //                    type uint32 {
  //                      range "16 .. 1048575";
  //                    }
  //                  }
  //                }
  //              }
  //              case case_3 {
  //                leaf dynamic {
  //                  description "Dynamically allocate an adjacency segment";
  //                  type empty;
  //                }
  //              }
  //            }
  //          }
  //        }
  //        container ipv6-adjacency-segment {
  //          description "Configure ipv6 adjacency segment";
  //          // uses apply-advanced;
  //          container protected {
  //            description "Adjacency SID is eligible for protection";
  //            choice adjsid-type {
  //              case case_1 {
  //                container index {
  //                  description "Adjacency SID indexed from SRGB";
  //                  leaf index-number {
  //                    type union {
  //                      type string {
  //                        pattern "<.*>|$.*";
  //                      }
  //                      type uint32 {
  //                        range "0 .. 199999";
  //                      }
  //                    }
  //                  }
  //                }
  //              }
  //              case case_2 {
  //                leaf label {
  //                  description "Adjacency SID from static label pool";
  //                  type union {
  //                    type string {
  //                      pattern "<.*>|$.*";
  //                    }
  //                    type uint32 {
  //                      range "16 .. 1048575";
  //                    }
  //                  }
  //                }
  //              }
  //              case case_3 {
  //                leaf dynamic {
  //                  description "Dynamically allocate an adjacency segment";
  //                  type empty;
  //                }
  //              }
  //            }
  //          }
  //          container unprotected {
  //            description "Adjacency SID uneligible for protection";
  //            choice adjsid-type {
  //              case case_1 {
  //                container index {
  //                  description "Adjacency SID indexed from SRGB";
  //                  leaf index-number {
  //                    type union {
  //                      type string {
  //                        pattern "<.*>|$.*";
  //                      }
  //                      type uint32 {
  //                        range "0 .. 199999";
  //                      }
  //                    }
  //                  }
  //                }
  //              }
  //              case case_2 {
  //                leaf label {
  //                  description "Adjacency SID from static label pool";
  //                  type union {
  //                    type string {
  //                      pattern "<.*>|$.*";
  //                    }
  //                    type uint32 {
  //                      range "16 .. 1048575";
  //                    }
  //                  }
  //                }
  //              }
  //              case case_3 {
  //                leaf dynamic {
  //                  description "Dynamically allocate an adjacency segment";
  //                  type empty;
  //                }
  //              }
  //            }
  //          }
  //        }
  //        container srm6-adjacency-segment {
  //          description "Configure srm6 adjacency segment";
  //          // uses apply-advanced;
  //          container unprotected {
  //            description "Adjacency SID uneligible for protection";
  //            leaf sid {
  //              description "Set Adjacency SID Value";
  //              type union {
  //                type string {
  //                  pattern "<.*>|$.*";
  //                }
  //                type uint32 {
  //                  range "1 .. 65535";
  //                }
  //              }
  //            }
  //          }
  //        }
  //        container srv6-adjacency-segment {
  //          description "Configure srv6 adjacency segment";
  //          // uses apply-advanced;
  //          container protected {
  //            presence "enable protected";
  //            description "SRv6 Adjacency segment is eligible for protection";
  //            // uses apply-advanced;
  //            list locator {
  //              key name;
  //              ordered-by user;
  //              description "Locator to bind SRv6 adjacency segment";
  //              leaf name {
  //                description "Locator name";
  //                type string;
  //              }
  //              // uses apply-advanced;
  //              list end-x-sid {
  //                key name;
  //                ordered-by user;
  //                description "Endpoint 128 bit address";
  //                leaf name {
  //                  type jt:ipv6addr;
  //                }
  //                // uses apply-advanced;
  //                container flavor {
  //                  presence "enable flavor";
  //                  description "Configure end-x-SID flavor";
  //                  // uses apply-advanced;
  //                  leaf psp {
  //                    description "Penultimate segment pop of the SRH";
  //                    type empty;
  //                  }
  //                  leaf usp {
  //                    description "Ultimate segment pop of the SRH";
  //                    type empty;
  //                  }
  //                  leaf usd {
  //                    description "Ultimate segment decapsulation";
  //                    type empty;
  //                  }
  //                }
  //              }
  //              container micro-adjacency-sid {
  //                presence "enable micro-adjacency-sid";
  //                description "Micro-adjacency-SID";
  //                // uses apply-advanced;
  //                leaf static-sid {
  //                  description "Static micro-adjacency-SID";
  //                  type union {
  //                    type uint32;
  //                    type string {
  //                      pattern "<.*>|$.*";
  //                    }
  //                  }
  //                }
  //              }
  //              container dynamic-end-x-sid {
  //                presence "enable dynamic-end-x-sid";
  //                description "Allocate end-x-SID dynamically";
  //                // uses apply-advanced;
  //                container flavor {
  //                  presence "enable flavor";
  //                  description "Configure end-x-SID flavor";
  //                  // uses apply-advanced;
  //                  leaf psp {
  //                    description "Penultimate segment pop of the SRH";
  //                    type empty;
  //                  }
  //                  leaf usp {
  //                    description "Ultimate segment pop of the SRH";
  //                    type empty;
  //                  }
  //                  leaf usd {
  //                    description "Ultimate segment decapsulation";
  //                    type empty;
  //                  }
  //                }
  //              }
  //            }
  //          }
  //          container unprotected {
  //            presence "enable unprotected";
  //            description "SRv6 Adjacency segment is uneligible for protection";
  //            // uses apply-advanced;
  //            list locator {
  //              key name;
  //              ordered-by user;
  //              description "Locator to bind SRv6 adjacency segment";
  //              leaf name {
  //                description "Locator name";
  //                type string;
  //              }
  //              // uses apply-advanced;
  //              list end-x-sid {
  //                key name;
  //                ordered-by user;
  //                description "Endpoint 128 bit address";
  //                leaf name {
  //                  type jt:ipv6addr;
  //                }
  //                // uses apply-advanced;
  //                container flavor {
  //                  presence "enable flavor";
  //                  description "Configure end-x-SID flavor";
  //                  // uses apply-advanced;
  //                  leaf psp {
  //                    description "Penultimate segment pop of the SRH";
  //                    type empty;
  //                  }
  //                  leaf usp {
  //                    description "Ultimate segment pop of the SRH";
  //                    type empty;
  //                  }
  //                  leaf usd {
  //                    description "Ultimate segment decapsulation";
  //                    type empty;
  //                  }
  //                }
  //              }
  //              container micro-adjacency-sid {
  //                presence "enable micro-adjacency-sid";
  //                description "Micro-adjacency-SID";
  //                // uses apply-advanced;
  //                leaf static-sid {
  //                  description "Static micro-adjacency-SID";
  //                  type union {
  //                    type uint32;
  //                    type string {
  //                      pattern "<.*>|$.*";
  //                    }
  //                  }
  //                }
  //              }
  //              container dynamic-end-x-sid {
  //                presence "enable dynamic-end-x-sid";
  //                description "Allocate end-x-SID dynamically";
  //                // uses apply-advanced;
  //                container flavor {
  //                  presence "enable flavor";
  //                  description "Configure end-x-SID flavor";
  //                  // uses apply-advanced;
  //                  leaf psp {
  //                    description "Penultimate segment pop of the SRH";
  //                    type empty;
  //                  }
  //                  leaf usp {
  //                    description "Ultimate segment pop of the SRH";
  //                    type empty;
  //                  }
  //                  leaf usd {
  //                    description "Ultimate segment decapsulation";
  //                    type empty;
  //                  }
  //                }
  //              }
  //            }
  //          }
  //        }
  //        list lan-neighbor {
  //          key name;
  //          ordered-by user;
  //          description "Configuration specific to a LAN neighbor";
  //          leaf name {
  //            description "Neighbor's sysid";
  //            type jt:sysid;
  //          }
  //          // uses apply-advanced;
  //          container ipv4-adjacency-segment {
  //            description "Configure ipv4 adjacency segment";
  //            // uses apply-advanced;
  //            container protected {
  //              description "Adjacency SID is eligible for protection";
  //              choice adjsid-type {
  //                case case_1 {
  //                  container index {
  //                    description "Adjacency SID indexed from SRGB";
  //                    leaf index-number {
  //                      type union {
  //                        type string {
  //                          pattern "<.*>|$.*";
  //                        }
  //                        type uint32 {
  //                          range "0 .. 199999";
  //                        }
  //                      }
  //                    }
  //                  }
  //                }
  //                case case_2 {
  //                  leaf label {
  //                    description "Adjacency SID from static label pool";
  //                    type union {
  //                      type string {
  //                        pattern "<.*>|$.*";
  //                      }
  //                      type uint32 {
  //                        range "16 .. 1048575";
  //                      }
  //                    }
  //                  }
  //                }
  //                case case_3 {
  //                  leaf dynamic {
  //                    description "Dynamically allocate an adjacency segment";
  //                    type empty;
  //                  }
  //                }
  //              }
  //            }
  //            container unprotected {
  //              description "Adjacency SID uneligible for protection";
  //              choice adjsid-type {
  //                case case_1 {
  //                  container index {
  //                    description "Adjacency SID indexed from SRGB";
  //                    leaf index-number {
  //                      type union {
  //                        type string {
  //                          pattern "<.*>|$.*";
  //                        }
  //                        type uint32 {
  //                          range "0 .. 199999";
  //                        }
  //                      }
  //                    }
  //                  }
  //                }
  //                case case_2 {
  //                  leaf label {
  //                    description "Adjacency SID from static label pool";
  //                    type union {
  //                      type string {
  //                        pattern "<.*>|$.*";
  //                      }
  //                      type uint32 {
  //                        range "16 .. 1048575";
  //                      }
  //                    }
  //                  }
  //                }
  //                case case_3 {
  //                  leaf dynamic {
  //                    description "Dynamically allocate an adjacency segment";
  //                    type empty;
  //                  }
  //                }
  //              }
  //            }
  //          }
  //          container ipv6-adjacency-segment {
  //            description "Configure ipv6 adjacency segment";
  //            // uses apply-advanced;
  //            container protected {
  //              description "Adjacency SID is eligible for protection";
  //              choice adjsid-type {
  //                case case_1 {
  //                  container index {
  //                    description "Adjacency SID indexed from SRGB";
  //                    leaf index-number {
  //                      type union {
  //                        type string {
  //                          pattern "<.*>|$.*";
  //                        }
  //                        type uint32 {
  //                          range "0 .. 199999";
  //                        }
  //                      }
  //                    }
  //                  }
  //                }
  //                case case_2 {
  //                  leaf label {
  //                    description "Adjacency SID from static label pool";
  //                    type union {
  //                      type string {
  //                        pattern "<.*>|$.*";
  //                      }
  //                      type uint32 {
  //                        range "16 .. 1048575";
  //                      }
  //                    }
  //                  }
  //                }
  //                case case_3 {
  //                  leaf dynamic {
  //                    description "Dynamically allocate an adjacency segment";
  //                    type empty;
  //                  }
  //                }
  //              }
  //            }
  //            container unprotected {
  //              description "Adjacency SID uneligible for protection";
  //              choice adjsid-type {
  //                case case_1 {
  //                  container index {
  //                    description "Adjacency SID indexed from SRGB";
  //                    leaf index-number {
  //                      type union {
  //                        type string {
  //                          pattern "<.*>|$.*";
  //                        }
  //                        type uint32 {
  //                          range "0 .. 199999";
  //                        }
  //                      }
  //                    }
  //                  }
  //                }
  //                case case_2 {
  //                  leaf label {
  //                    description "Adjacency SID from static label pool";
  //                    type union {
  //                      type string {
  //                        pattern "<.*>|$.*";
  //                      }
  //                      type uint32 {
  //                        range "16 .. 1048575";
  //                      }
  //                    }
  //                  }
  //                }
  //                case case_3 {
  //                  leaf dynamic {
  //                    description "Dynamically allocate an adjacency segment";
  //                    type empty;
  //                  }
  //                }
  //              }
  //            }
  //          }
  //          container srm6-adjacency-segment {
  //            description "Configure srm6 adjacency segment";
  //            // uses apply-advanced;
  //            container unprotected {
  //              description "Adjacency SID uneligible for protection";
  //              leaf sid {
  //                description "Set Adjacency SID Value";
  //                type union {
  //                  type string {
  //                    pattern "<.*>|$.*";
  //                  }
  //                  type uint32 {
  //                    range "1 .. 65535";
  //                  }
  //                }
  //              }
  //            }
  //          }
  //          container srv6-adjacency-segment {
  //            description "Configure srv6 adjacency segment";
  //            // uses apply-advanced;
  //            container protected {
  //              presence "enable protected";
  //              description "SRv6 Adjacency segment is eligible for protection";
  //              // uses apply-advanced;
  //              list locator {
  //                key name;
  //                ordered-by user;
  //                description "Locator to bind SRv6 adjacency segment";
  //                leaf name {
  //                  description "Locator name";
  //                  type string;
  //                }
  //                // uses apply-advanced;
  //                list end-x-sid {
  //                  key name;
  //                  ordered-by user;
  //                  description "Endpoint 128 bit address";
  //                  leaf name {
  //                    type jt:ipv6addr;
  //                  }
  //                  // uses apply-advanced;
  //                  container flavor {
  //                    presence "enable flavor";
  //                    description "Configure end-x-SID flavor";
  //                    // uses apply-advanced;
  //                    leaf psp {
  //                      description "Penultimate segment pop of the SRH";
  //                      type empty;
  //                    }
  //                    leaf usp {
  //                      description "Ultimate segment pop of the SRH";
  //                      type empty;
  //                    }
  //                    leaf usd {
  //                      description "Ultimate segment decapsulation";
  //                      type empty;
  //                    }
  //                  }
  //                }
  //                container micro-adjacency-sid {
  //                  presence "enable micro-adjacency-sid";
  //                  description "Micro-adjacency-SID";
  //                  // uses apply-advanced;
  //                  leaf static-sid {
  //                    description "Static micro-adjacency-SID";
  //                    type union {
  //                      type uint32;
  //                      type string {
  //                        pattern "<.*>|$.*";
  //                      }
  //                    }
  //                  }
  //                }
  //                container dynamic-end-x-sid {
  //                  presence "enable dynamic-end-x-sid";
  //                  description "Allocate end-x-SID dynamically";
  //                  // uses apply-advanced;
  //                  container flavor {
  //                    presence "enable flavor";
  //                    description "Configure end-x-SID flavor";
  //                    // uses apply-advanced;
  //                    leaf psp {
  //                      description "Penultimate segment pop of the SRH";
  //                      type empty;
  //                    }
  //                    leaf usp {
  //                      description "Ultimate segment pop of the SRH";
  //                      type empty;
  //                    }
  //                    leaf usd {
  //                      description "Ultimate segment decapsulation";
  //                      type empty;
  //                    }
  //                  }
  //                }
  //              }
  //            }
  //            container unprotected {
  //              presence "enable unprotected";
  //              description "SRv6 Adjacency segment is uneligible for protection";
  //              // uses apply-advanced;
  //              list locator {
  //                key name;
  //                ordered-by user;
  //                description "Locator to bind SRv6 adjacency segment";
  //                leaf name {
  //                  description "Locator name";
  //                  type string;
  //                }
  //                // uses apply-advanced;
  //                list end-x-sid {
  //                  key name;
  //                  ordered-by user;
  //                  description "Endpoint 128 bit address";
  //                  leaf name {
  //                    type jt:ipv6addr;
  //                  }
  //                  // uses apply-advanced;
  //                  container flavor {
  //                    presence "enable flavor";
  //                    description "Configure end-x-SID flavor";
  //                    // uses apply-advanced;
  //                    leaf psp {
  //                      description "Penultimate segment pop of the SRH";
  //                      type empty;
  //                    }
  //                    leaf usp {
  //                      description "Ultimate segment pop of the SRH";
  //                      type empty;
  //                    }
  //                    leaf usd {
  //                      description "Ultimate segment decapsulation";
  //                      type empty;
  //                    }
  //                  }
  //                }
  //                container micro-adjacency-sid {
  //                  presence "enable micro-adjacency-sid";
  //                  description "Micro-adjacency-SID";
  //                  // uses apply-advanced;
  //                  leaf static-sid {
  //                    description "Static micro-adjacency-SID";
  //                    type union {
  //                      type uint32;
  //                      type string {
  //                        pattern "<.*>|$.*";
  //                      }
  //                    }
  //                  }
  //                }
  //                container dynamic-end-x-sid {
  //                  presence "enable dynamic-end-x-sid";
  //                  description "Allocate end-x-SID dynamically";
  //                  // uses apply-advanced;
  //                  container flavor {
  //                    presence "enable flavor";
  //                    description "Configure end-x-SID flavor";
  //                    // uses apply-advanced;
  //                    leaf psp {
  //                      description "Penultimate segment pop of the SRH";
  //                      type empty;
  //                    }
  //                    leaf usp {
  //                      description "Ultimate segment pop of the SRH";
  //                      type empty;
  //                    }
  //                    leaf usd {
  //                      description "Ultimate segment decapsulation";
  //                      type empty;
  //                    }
  //                  }
  //                }
  //              }
  //            }
  //          }
  //        }
  //        container post-convergence-lfa {
  //          presence "enable post-convergence-lfa";
  //          description "Configure backup along post convergence on this interface";
  //          // uses apply-advanced;
  //          container node-protection {
  //            presence "enable node-protection";
  //            description "Enable node protection";
  //            // uses apply-advanced;
  //            leaf cost {
  //              description "Cost for node protection";
  //              type union {
  //                type string {
  //                  pattern "<.*>|$.*";
  //                }
  //                type uint32 {
  //                  range "0 .. 16777215";
  //                }
  //              }
  //            }
  //          }
  //          leaf srlg-protection {
  //            description "Enable srlg protection";
  //            type empty;
  //          }
  //          leaf fate-sharing-protection {
  //            description "Enable fate-sharing protection";
  //            type empty;
  //          }
  //        }
  //        container application-specific {
  //          description "Advertise application-specific TE attributes";
  //          // uses apply-advanced;
  //          list attribute-group {
  //            key name;
  //            ordered-by user;
  //            description "Link attribute group name";
  //            max-elements 1;
  //            leaf name {
  //              description "Link attribute group name";
  //              type string;
  //            }
  //            // uses apply-advanced;
  //            leaf advertise-delay-metric {
  //              description "Advertise delay metric as per interface config";
  //              type empty;
  //            }
  //            leaf te-metric {
  //              description "Traffic engineering metric for this attribute group";
  //              type union {
  //                type string {
  //                  pattern "<.*>|$.*";
  //                }
  //                type uint32 {
  //                  range "0 .. 16777215";
  //                }
  //              }
  //            }
  //            leaf-list admin-group {
  //              ordered-by user;
  //              description "Administrative groups for this attribute-group";
  //              type string;
  //              max-elements 16;
  //            }
  //            container application {
  //              description "Standard Applications part of this attribute-group";
  //              // uses apply-advanced;
  //              leaf flex-algorithm {
  //                description "Set X flag in standard application bit mask";
  //                type empty;
  //              }
  //            }
  //          }
  //        }
  //        choice enable-disable {
  //          case case_1 {
  //            leaf disable {
  //              description "Disable IS-IS for this level";
  //              type empty;
  //            }
  //          }
  //        }
  //        leaf metric {
  //          description "Metric for this level";
  //          type union {
  //            type string {
  //              pattern "<.*>|$.*";
  //            }
  //            type uint32 {
  //              range "0 .. 16777215";
  //            }
  //          }
  //        }
  //        leaf ipv4-multicast-metric {
  //          description "IPv4 multicast metric for this level";
  //          type union {
  //            type string {
  //              pattern "<.*>|$.*";
  //            }
  //            type uint32 {
  //              range "0 .. 16777215";
  //            }
  //          }
  //        }
  //        leaf ipv6-unicast-metric {
  //          description "IPv6 unicast metric for this level";
  //          type union {
  //            type string {
  //              pattern "<.*>|$.*";
  //            }
  //            type uint32 {
  //              range "0 .. 16777215";
  //            }
  //          }
  //        }
  //        leaf ipv6-multicast-metric {
  //          description "IPv6 multicast metric for this level";
  //          type union {
  //            type string {
  //              pattern "<.*>|$.*";
  //            }
  //            type uint32 {
  //              range "0 .. 16777215";
  //            }
  //          }
  //        }
  //        list topology {
  //          key name;
  //          ordered-by user;
  //          description "Topology specific attributes";
  //          leaf name {
  //            description "Topology name";
  //            type enumeration {
  //              enum "default" {
  //                description "Default topology";
  //              }
  //              enum "ipv4-multicast" {
  //                description "IPv4 multicast topology";
  //              }
  //              enum "ipv6-unicast" {
  //                description "IPv6 unicast topology";
  //              }
  //              enum "ipv6-multicast" {
  //                description "IPv6 multicast topology";
  //              }
  //            }
  //          }
  //          // uses apply-advanced;
  //          leaf metric {
  //            description "Topology metric";
  //            type union {
  //              type string {
  //                pattern "<.*>|$.*";
  //              }
  //              type uint32 {
  //                range "0 .. 16777215";
  //              }
  //            }
  //          }
  //          container bandwidth-based-metrics {
  //            description "Configure bandwidth based metrics";
  //            // uses apply-advanced;
  //            list bandwidth {
  //              key name;
  //              description "Bandwidth threshold";
  //              leaf name {
  //                type string;
  //              }
  //              leaf metric {
  //                description "Metric associated with specified bandwidth";
  //                type union {
  //                  type string {
  //                    pattern "<.*>|$.*";
  //                  }
  //                  type uint32 {
  //                    range "0 .. 16777215";
  //                  }
  //                }
  //              }
  //            }
  //          }
  //        }
  //        leaf authentication-key {
  //          description "Authentication key (password)";
  //          status deprecated;
  //          type jt:unreadable;
  //        }
  //        leaf authentication-type {
  //          description "Authentication type";
  //          status deprecated;
  //          type enumeration {
  //            enum "md5" {
  //              description "MD5 authentication";
  //              status deprecated;
  //            }
  //            enum "simple" {
  //              description "Simple password authentication";
  //              status deprecated;
  //            }
  //          }
  //        }
  //        leaf hello-authentication-key {
  //          description "Authentication key (password) for hello packets";
  //          type jt:unreadable;
  //        }
  //        leaf hello-authentication-type {
  //          description "Authentication type for hello packets";
  //          type enumeration {
  //            enum "md5" {
  //              description "MD5 authentication";
  //            }
  //            enum "simple" {
  //              description "Simple password authentication";
  //            }
  //          }
  //        }
  //        leaf hello-authentication-key-chain {
  //          description "Key chain name";
  //          type string {
  //            length "1 .. 128";
  //          }
  //        }
  //        leaf hello-interval {
  //          description "Interval between hello packet transmissions";
  //          units "seconds";
  //          type union {
  //            type string {
  //              pattern "<.*>|$.*";
  //            }
  //            type uint32 {
  //              range "1 .. 21845";
  //            }
  //          }
  //        }
  //        leaf hold-time {
  //          description "Time after which neighbors think the interface is down";
  //          units "seconds";
  //          type union {
  //            type string {
  //              pattern "<.*>|$.*";
  //            }
  //            type uint32 {
  //              range "1 .. 65535";
  //            }
  //          }
  //        }
  //        leaf priority {
  //          description "Designated router election priority";
  //          type union {
  //            type string {
  //              pattern "<.*>|$.*";
  //            }
  //            type uint32 {
  //              range "0 .. 127";
  //            }
  //          }
  //        }
  //        container flood-reflector {
  //          presence "enable flood-reflector";
  //          description "Configure interface as flood-reflector";
  //          // uses apply-advanced;
  //          leaf cluster-id {
  //            description "Cluster-ID";
  //            type union {
  //              type string {
  //                pattern "<.*>|$.*";
  //              }
  //              type uint32 {
  //                range "1 .. 4294967295";
  //              }
  //            }
  //          }
  //        }
  //        container passive {
  //          presence "enable passive";
  //          description "Do not run IS-IS at this level, but advertise it";
  //          // uses apply-advanced;
  //          leaf remote-node-iso {
  //            description "ISO System-ID of the remote node";
  //            type jt:sysid;
  //          }
  //          leaf remote-node-id {
  //            description "Remote address of the link";
  //            type jt:ipv4addr;
  //          }
  //        }
  //        leaf strict-bfd-old {
  //          description "Enable strict bfd over this interface";
  //          type empty;
  //        }
  //      }
  //      leaf delay-metric {
  //        description "Delay metric";
  //        units "microseconds";
  //        type union {
  //          type string {
  //            pattern "<.*>|$.*";
  //          }
  //          type uint32 {
  //            range "0 .. 16777215";
  //          }
  //        }
  //      }
  //      container delay-measurement {
  //        presence "enable delay-measurement";
  //        description "Enable delay measurement";
  //        // uses apply-advanced;
  //        leaf probe-interval {
  //          description "Probe interval";
  //          units "seconds";
  //          type union {
  //            type string {
  //              pattern "<.*>|$.*";
  //            }
  //            type uint32 {
  //              range "1 .. 255";
  //            }
  //          }
  //        }
  //        leaf probe-count {
  //          description "Probe count";
  //          units "seconds";
  //          type union {
  //            type string {
  //              pattern "<.*>|$.*";
  //            }
  //            type uint32 {
  //              range "1 .. 15";
  //            }
  //          }
  //        }
  //        container advertisement {
  //          description "Delay advertisement";
  //          // uses apply-advanced;
  //          container periodic {
  //            description "Periodic advertisement parameters";
  //            // uses apply-advanced;
  //            leaf threshold {
  //              description "Threshold";
  //              units "percentage";
  //              type union {
  //                type string {
  //                  pattern "<.*>|$.*";
  //                }
  //                type uint32 {
  //                  range "0 .. 100";
  //                }
  //              }
  //            }
  //            leaf interval {
  //              description "Interval";
  //              units "seconds";
  //              type union {
  //                type string {
  //                  pattern "<.*>|$.*";
  //                }
  //                type uint32 {
  //                  range "30 .. 3600";
  //                }
  //              }
  //            }
  //          }
  //          container accelerated {
  //            presence "enable accelerated";
  //            description "Accelerated advertisement parameters";
  //            // uses apply-advanced;
  //            leaf threshold {
  //              description "Threshold";
  //              units "percentage";
  //              type union {
  //                type string {
  //                  pattern "<.*>|$.*";
  //                }
  //                type uint32 {
  //                  range "0 .. 100";
  //                }
  //              }
  //            }
  //          }
  //        }
  //      }
  //      leaf no-advertise-adjacency-segment {
  //        description "Do not advertise an adjacency segment for this interface";
  //        type empty;
  //      }
  //      container auto-bandwidth {
  //        description "Auto bandwidth configuration";
  //        // uses apply-advanced;
  //        leaf template-name {
  //          description "Auto bandwidth template name";
  //          type string;
  //        }
  //        choice enable-disable {
  //          case case_1 {
  //            leaf disable {
  //              description "Disable Auto bandwidth on this interface";
  //              type empty;
  //            }
  //          }
  //        }
  //      }
  //      choice protection-type {
  //        case case_1 {
  //          leaf link-protection {
  //            description "Protect interface from link faults only";
  //            type empty;
  //          }
  //        }
  //        case case_2 {
  //          leaf node-link-protection {
  //            description "Protect interface from both link and node faults";
  //            type empty;
  //          }
  //        }
  //      }
  //      leaf no-eligible-backup {
  //        description "Not eligible for backup traffic from protected interfaces";
  //        type empty;
  //      }
  //      leaf no-eligible-remote-backup {
  //        description "Not eligible for Remote-LFA backup traffic from protected interfaces";
  //        type empty;
  //      }
  //      container link-degradation-threshold {
  //        presence "enable link-degradation-threshold";
  //        description "Link up and down thresholds (in %) for proactive link protection";
  //        leaf link-down {
  //          description "Signal degradation threshold above which link marked down";
  //          type union {
  //            type string {
  //              pattern "<.*>|$.*";
  //            }
  //            type uint32 {
  //              range "0 .. 100";
  //            }
  //          }
  //        }
  //        leaf link-up {
  //          description "Signal degradation threshold below which link is marked up.";
  //          type union {
  //            type string {
  //              pattern "<.*>|$.*";
  //            }
  //            type uint32 {
  //              range "0 .. 100";
  //            }
  //          }
  //        }
  //      }
  //      choice enable-disable {
  //        case case_1 {
  //          leaf disable {
  //            description "Disable IS-IS on this interface";
  //            type empty;
  //          }
  //        }
  //      }
  //      leaf authentication-key {
  //        description "Authentication key (password)";
  //        status deprecated;
  //        type jt:unreadable;
  //      }
  //      leaf authentication-type {
  //        description "Authentication type";
  //        status deprecated;
  //        type enumeration {
  //          enum "md5" {
  //            description "MD5 authentication";
  //            status deprecated;
  //          }
  //          enum "simple" {
  //            description "Simple password authentication";
  //            status deprecated;
  //          }
  //        }
  //      }
  //      leaf flood-group {
  //        description "ISO Area that this interface should send LSPs to";
  //        type string {
  //        }
  //      }
  //      leaf hello-authentication-key {
  //        description "Authentication key (password) for hello packets";
  //        status deprecated;
  //        type jt:unreadable;
  //      }
  //      leaf hello-authentication-type {
  //        description "Authentication type for hello packets";
  //        status deprecated;
  //        type enumeration {
  //          enum "md5" {
  //            description "MD5 authentication";
  //            status deprecated;
  //          }
  //          enum "simple" {
  //            description "Simple password authentication";
  //            status deprecated;
  //          }
  //        }
  //      }
  //      leaf hello-padding-type {
  //        description "Type of padding for hello packets";
  //        default "loose";
  //        type enumeration {
  //          enum "strict" {
  //            description "Padding for all adjacency states";
  //          }
  //          enum "adaptive" {
  //            description "Padding until state of neighbor adjacency is 'up'";
  //          }
  //          enum "loose" {
  //            description "Padding until state of adjacency is 'initializing'";
  //          }
  //          enum "disable" {
  //            description "Do not add any padding for hello packets";
  //          }
  //        }
  //      }
  //      leaf interface-group-holddown-delay {
  //        description "Time to wait before including in BBM calculation";
  //        units "seconds";
  //        type union {
  //          type string {
  //            pattern "<.*>|$.*";
  //          }
  //          type uint32 {
  //            range "0 .. 60";
  //          }
  //        }
  //      }
  //      choice layer2-map-choice {
  //        leaf layer2-map {
  //          description "Kernel ARP/ND creation for nexthops";
  //          type empty;
  //        }
  //        leaf no-layer2-map {
  //          description "Don't kernel ARP/ND creation for nexthops";
  //          type empty;
  //        }
  //      }
  //      leaf max-hello-size {
  //        description "Maximum size allowed for ISIS Hello PDUs";
  //        type union {
  //          type string {
  //            pattern "<.*>|$.*";
  //          }
  //          type uint32 {
  //            range "512 .. 16000";
  //          }
  //        }
  //      }
  //      leaf lsp-interval {
  //        description "Interval between LSP transmissions";
  //        default "100";
  //        units "milliseconds";
  //        type union {
  //          type string {
  //            pattern "<.*>|$.*";
  //          }
  //          type uint32 {
  //            range "1 .. 1000";
  //          }
  //        }
  //      }
  //      container csnp-interval {
  //        description "Rate of CSN packets (for LAN interfaces only)";
  //        choice csnp_interval_option {
  //          case case_1 {
  //            leaf csnp-interval-number {
  //              description "Interval between CSN packets";
  //              units "seconds";
  //              type union {
  //                type string {
  //                  pattern "<.*>|$.*";
  //                }
  //                type uint32 {
  //                  range "1 .. 65535";
  //                }
  //              }
  //            }
  //          }
  //          case case_2 {
  //            leaf disable {
  //              description "Do not send CSN packets on this interface";
  //              type empty;
  //            }
  //          }
  //        }
  //      }
  //      container strict-dual-isis {
  //        presence "enable strict-dual-isis";
  //        description "Enable dual isis if spf computation is required for both ipv4 and ipv6 family";
  //        // uses apply-advanced;
  //        leaf holdown {
  //          description "Time to wait for ipv4 and ipv6 connectivity";
  //          status deprecated;
  //          default "12";
  //          type union {
  //            type string {
  //              pattern "<.*>|$.*";
  //            }
  //            type uint32 {
  //              range "1 .. 65535";
  //            }
  //          }
  //        }
  //        leaf holddown {
  //          description "Time to wait for ipv4 and ipv6 connectivity";
  //          default "12";
  //          type union {
  //            type string {
  //              pattern "<.*>|$.*";
  //            }
  //            type uint32 {
  //              range "1 .. 65535";
  //            }
  //          }
  //        }
  //      }
  //      container mesh-group {
  //        description "Add the interface to a mesh group";
  //        choice mesh_group_option {
  //          case case_1 {
  //            leaf mesh-group-number {
  //              description "Mesh group number for this interface";
  //              type union {
  //                type uint32;
  //                type string {
  //                  pattern "<.*>|$.*";
  //                }
  //              }
  //            }
  //          }
  //          case case_2 {
  //            leaf blocked {
  //              description "Do not flood new LSPs on this interface";
  //              type empty;
  //            }
  //          }
  //        }
  //      }
  //      leaf point-to-point {
  //        description "Treat interface as point to point";
  //        type empty;
  //      }
  //      container passive {
  //        presence "enable passive";
  //        description "Do not run IS-IS, but advertise it";
  //        // uses apply-advanced;
  //        leaf remote-node-iso {
  //          description "ISO System-ID of the remote node";
  //          type jt:sysid;
  //        }
  //        leaf remote-node-id {
  //          description "Remote address of the link";
  //          type jt:ipv4addr;
  //        }
  //      }
  //      leaf checksum {
  //        description "Enable checksum for packets on this interface";
  //        type empty;
  //      }
  //      leaf no-unicast-topology {
  //        description "Do not include this interface in the unicast topology";
  //        type empty;
  //      }
  //      leaf no-ipv4-multicast {
  //        description "Do not include this interface in the IPv4 multicast topology";
  //        type empty;
  //      }
  //      leaf no-ipv6-unicast {
  //        description "Do not include this interface in the IPv6 unicast topology";
  //        type empty;
  //      }
  //      leaf no-ipv6-multicast {
  //        description "Do not include this interface in the IPv6 multicast topology";
  //        type empty;
  //      }
  //      leaf no-adjacency-down-notification {
  //        description "Do not inform other protocols about adjacency down events";
  //        type empty;
  //      }
  //      container bfd-liveness-detection {
  //        description "Bidirectional Forwarding Detection options";
  //        status deprecated;
  //        // uses apply-advanced;
  //        leaf version {
  //          description "BFD protocol version number";
  //          default "automatic";
  //          type enumeration {
  //            enum "0" {
  //              description "BFD version 0 (deprecated)";
  //            }
  //            enum "1" {
  //              description "BFD version 1";
  //            }
  //            enum "automatic" {
  //              description "Choose BFD version automatically";
  //            }
  //          }
  //        }
  //        leaf minimum-interval {
  //          description "Minimum transmit and receive interval";
  //          units "milliseconds";
  //          type union {
  //            type string {
  //              pattern "<.*>|$.*";
  //            }
  //            type uint32 {
  //              range "1 .. 255000";
  //            }
  //          }
  //        }
  //        leaf minimum-transmit-interval {
  //          description "Minimum transmit interval";
  //          status deprecated;
  //          units "milliseconds";
  //          type union {
  //            type string {
  //              pattern "<.*>|$.*";
  //            }
  //            type uint32 {
  //              range "1 .. 255000";
  //            }
  //          }
  //        }
  //        leaf minimum-receive-interval {
  //          description "Minimum receive interval";
  //          units "milliseconds";
  //          type union {
  //            type string {
  //              pattern "<.*>|$.*";
  //            }
  //            type uint32 {
  //              range "1 .. 255000";
  //            }
  //          }
  //        }
  //        leaf multiplier {
  //          description "Detection time multiplier";
  //          default "3";
  //          type union {
  //            type string {
  //              pattern "<.*>|$.*";
  //            }
  //            type uint32 {
  //              range "1 .. 255";
  //            }
  //          }
  //        }
  //        leaf inline-disable {
  //          description "Disable inline mode for this BFD session";
  //          type empty;
  //        }
  //        leaf pdu-size {
  //          description "BFD transport protocol payload size";
  //          default "24";
  //          type union {
  //            type string {
  //              pattern "<.*>|$.*";
  //            }
  //            type uint32 {
  //              range "24 .. 9000";
  //            }
  //          }
  //        }
  //        choice adaptation-choice {
  //          case case_1 {
  //            leaf no-adaptation {
  //              description "Disable adaptation";
  //              type empty;
  //            }
  //          }
  //        }
  //        container transmit-interval {
  //          description "Transmit-interval options";
  //          // uses apply-advanced;
  //          leaf minimum-interval {
  //            description "Minimum transmit interval";
  //            units "milliseconds";
  //            type union {
  //              type string {
  //                pattern "<.*>|$.*";
  //              }
  //              type uint32 {
  //                range "1 .. 255000";
  //              }
  //            }
  //          }
  //          leaf threshold {
  //            description "High transmit interval triggering a trap";
  //            units "milliseconds";
  //            type union {
  //              type uint32;
  //              type string {
  //                pattern "<.*>|$.*";
  //              }
  //            }
  //          }
  //        }
  //        container detection-time {
  //          description "Detection-time options";
  //          // uses apply-advanced;
  //          leaf threshold {
  //            description "High detection-time triggering a trap";
  //            units "milliseconds";
  //            type union {
  //              type uint32;
  //              type string {
  //                pattern "<.*>|$.*";
  //              }
  //            }
  //          }
  //        }
  //        container authentication {
  //          description "Authentication options";
  //          // uses apply-advanced;
  //          leaf key-chain {
  //            description "Key chain name";
  //            type string;
  //          }
  //          leaf algorithm {
  //            description "Algorithm name";
  //            type enumeration {
  //              enum "simple-password" {
  //                description "Simple password";
  //              }
  //              enum "keyed-md5" {
  //                description "Keyed message Digest 5";
  //              }
  //              enum "meticulous-keyed-md5" {
  //                description "Meticulous keyed message Digest 5";
  //              }
  //              enum "keyed-sha-1" {
  //                description "Keyed secure hash algorithm (SHA1) ";
  //              }
  //              enum "meticulous-keyed-sha-1" {
  //                description "Meticulous keyed secure hash algorithm (SHA1) ";
  //              }
  //            }
  //          }
  //          leaf loose-check {
  //            description "Verify authentication only if authentication is negotiated";
  //            type empty;
  //          }
  //        }
  //      }
  //      list family {
  //        key name;
  //        ordered-by user;
  //        description "Address family specific interface attributes";
  //        leaf name {
  //          type enumeration {
  //            enum "inet" {
  //              description "IPv4 family";
  //            }
  //            enum "inet6" {
  //              description "IPv6 family";
  //            }
  //          }
  //        }
  //        // uses apply-advanced;
  //        container bfd-liveness-detection {
  //          description "Bidirectional Forwarding Detection options";
  //          // uses apply-advanced;
  //          leaf version {
  //            description "BFD protocol version number";
  //            default "automatic";
  //            type enumeration {
  //              enum "0" {
  //                description "BFD version 0 (deprecated)";
  //              }
  //              enum "1" {
  //                description "BFD version 1";
  //              }
  //              enum "automatic" {
  //                description "Choose BFD version automatically";
  //              }
  //            }
  //          }
  //          leaf minimum-interval {
  //            description "Minimum transmit and receive interval";
  //            units "milliseconds";
  //            type union {
  //              type string {
  //                pattern "<.*>|$.*";
  //              }
  //              type uint32 {
  //                range "1 .. 255000";
  //              }
  //            }
  //          }
  //          leaf minimum-transmit-interval {
  //            description "Minimum transmit interval";
  //            status deprecated;
  //            units "milliseconds";
  //            type union {
  //              type string {
  //                pattern "<.*>|$.*";
  //              }
  //              type uint32 {
  //                range "1 .. 255000";
  //              }
  //            }
  //          }
  //          leaf minimum-receive-interval {
  //            description "Minimum receive interval";
  //            units "milliseconds";
  //            type union {
  //              type string {
  //                pattern "<.*>|$.*";
  //              }
  //              type uint32 {
  //                range "1 .. 255000";
  //              }
  //            }
  //          }
  //          leaf multiplier {
  //            description "Detection time multiplier";
  //            default "3";
  //            type union {
  //              type string {
  //                pattern "<.*>|$.*";
  //              }
  //              type uint32 {
  //                range "1 .. 255";
  //              }
  //            }
  //          }
  //          leaf inline-disable {
  //            description "Disable inline mode for this BFD session";
  //            type empty;
  //          }
  //          leaf pdu-size {
  //            description "BFD transport protocol payload size";
  //            default "24";
  //            type union {
  //              type string {
  //                pattern "<.*>|$.*";
  //              }
  //              type uint32 {
  //                range "24 .. 9000";
  //              }
  //            }
  //          }
  //          choice adaptation-choice {
  //            case case_1 {
  //              leaf no-adaptation {
  //                description "Disable adaptation";
  //                type empty;
  //              }
  //            }
  //          }
  //          container transmit-interval {
  //            description "Transmit-interval options";
  //            // uses apply-advanced;
  //            leaf minimum-interval {
  //              description "Minimum transmit interval";
  //              units "milliseconds";
  //              type union {
  //                type string {
  //                  pattern "<.*>|$.*";
  //                }
  //                type uint32 {
  //                  range "1 .. 255000";
  //                }
  //              }
  //            }
  //            leaf threshold {
  //              description "High transmit interval triggering a trap";
  //              units "milliseconds";
  //              type union {
  //                type uint32;
  //                type string {
  //                  pattern "<.*>|$.*";
  //                }
  //              }
  //            }
  //          }
  //          container detection-time {
  //            description "Detection-time options";
  //            // uses apply-advanced;
  //            leaf threshold {
  //              description "High detection-time triggering a trap";
  //              units "milliseconds";
  //              type union {
  //                type uint32;
  //                type string {
  //                  pattern "<.*>|$.*";
  //                }
  //              }
  //            }
  //          }
  //          container authentication {
  //            description "Authentication options";
  //            // uses apply-advanced;
  //            leaf key-chain {
  //              description "Key chain name";
  //              type string;
  //            }
  //            leaf algorithm {
  //              description "Algorithm name";
  //              type enumeration {
  //                enum "simple-password" {
  //                  description "Simple password";
  //                }
  //                enum "keyed-md5" {
  //                  description "Keyed message Digest 5";
  //                }
  //                enum "meticulous-keyed-md5" {
  //                  description "Meticulous keyed message Digest 5";
  //                }
  //                enum "keyed-sha-1" {
  //                  description "Keyed secure hash algorithm (SHA1) ";
  //                }
  //                enum "meticulous-keyed-sha-1" {
  //                  description "Meticulous keyed secure hash algorithm (SHA1) ";
  //                }
  //              }
  //            }
  //            leaf loose-check {
  //              description "Verify authentication only if authentication is negotiated";
  //              type empty;
  //            }
  //          }
  //          container echo {
  //            description "Echo mode parameters";
  //            // uses apply-advanced;
  //            leaf minimum-interval {
  //              description "Minimum transmit and receive interval";
  //              units "milliseconds";
  //              type union {
  //                type string {
  //                  pattern "<.*>|$.*";
  //                }
  //                type uint32 {
  //                  range "100 .. 255000";
  //                }
  //              }
  //            }
  //          }
  //          container echo-lite {
  //            description "Echo-lite more parameters";
  //            // uses apply-advanced;
  //            leaf minimum-interval {
  //              description "Minimum transmit and receive interval";
  //              units "milliseconds";
  //              type union {
  //                type string {
  //                  pattern "<.*>|$.*";
  //                }
  //                type uint32 {
  //                  range "100 .. 255000";
  //                }
  //              }
  //            }
  //          }
  //          leaf holddown-interval {
  //            description "Time to hold the session-UP notification to the client";
  //            units "milliseconds";
  //            type union {
  //              type string {
  //                pattern "<.*>|$.*";
  //              }
  //              type uint32 {
  //                range "0 .. 255000";
  //              }
  //            }
  //          }
  //        }
  //      }
  //      leaf strict-bfd {
  //        description "Enable strict bfd over this interface";
  //        type empty;
  //      }
  //    }
  //    list bier-sub-domain {
  //      key name;
  //      description "Configuration of bier subdomain";
  //      leaf name {
  //        description "Enable bier subdomain id";
  //        type union {
  //          type uint8;
  //          type string {
  //            pattern "<.*>|$.*";
  //          }
  //        }
  //      }
  //    }
  //    container source-packet-routing {
  //      presence "enable source-packet-routing";
  //      description "Enable Source Packet Routing (SPRING)";
  //      // uses apply-advanced;
  //      container adjacency-segment {
  //        description "Configure attributes for Adjacency Segments in SPRING";
  //        // uses apply-advanced;
  //        leaf hold-time {
  //          description "Duration(ms) for which adjacency segments will be retained after isolating from an interface";
  //          type union {
  //            type string {
  //              pattern "<.*>|$.*";
  //            }
  //            type uint32 {
  //              range "180000 .. 900000";
  //            }
  //          }
  //        }
  //      }
  //      container udp-tunneling {
  //        description "Enable SR over UDP feature";
  //        // uses apply-advanced;
  //        leaf encapsulation {
  //          description "Enable UDP Tunnel Encapsulation";
  //          type empty;
  //        }
  //        leaf decapsulation {
  //          description "Enable UDP Tunnel decapsulation";
  //          type empty;
  //        }
  //      }
  //      container srgb {
  //        description "Set the SRGB global block in SPRING";
  //        leaf start-label {
  //          description "Start range for SRGB label block";
  //          type union {
  //            type string {
  //              pattern "<.*>|$.*";
  //            }
  //            type uint32;
  //          }
  //        }
  //        leaf index-range {
  //          description "Index to the SRGB start label block";
  //          type union {
  //            type string {
  //              pattern "<.*>|$.*";
  //            }
  //            type uint32;
  //          }
  //        }
  //      }
  //      container node-segment {
  //        description "Enable support for Node segments in SPRING";
  //        // uses apply-advanced;
  //        leaf ipv4-index {
  //          description "Set IPv4 Node Segment index";
  //          type union {
  //            type string {
  //              pattern "<.*>|$.*";
  //            }
  //            type uint32 {
  //              range "0 .. 199999";
  //            }
  //          }
  //        }
  //        leaf ipv6-index {
  //          description "Set IPv6 Node Segment index";
  //          type union {
  //            type string {
  //              pattern "<.*>|$.*";
  //            }
  //            type uint32 {
  //              range "0 .. 199999";
  //            }
  //          }
  //        }
  //        leaf index-range {
  //          description "Set Range of Node Segment indices allowed";
  //          type union {
  //            type string {
  //              pattern "<.*>|$.*";
  //            }
  //            type uint32 {
  //              range "32 .. 16385";
  //            }
  //          }
  //        }
  //      }
  //      leaf-list flex-algorithm {
  //        description "Flex-algorithms we would like to participate in";
  //        type union {
  //          type string {
  //            pattern "<.*>|$.*";
  //          }
  //          type uint32 {
  //            range "128 .. 255";
  //          }
  //        }
  //        max-elements 16;
  //      }
  //      leaf use-flex-algorithm-metric-always {
  //        description "Use flex-algo prefix metric whenever available";
  //        type empty;
  //      }
  //      leaf strict-asla-based-flex-algorithm {
  //        description "Flex-Algorithm to ignore links not having ASLA sub-TLVs";
  //        type empty;
  //      }
  //      leaf new-capability-subtlv {
  //        description "Advertise all ranges in single spring capability subtlv";
  //        type empty;
  //      }
  //      leaf explicit-null {
  //        description "Set E and P bits in all Prefix SID advertisements";
  //        type empty;
  //      }
  //      leaf mapping-server {
  //        description "Mapping server name";
  //        type string;
  //      }
  //      leaf no-strict-spf {
  //        description " Disable strict spf algo 1 advertisement";
  //        type empty;
  //      }
  //      leaf no-binding-sid-leaking {
  //        description " Disable SRMS binding sid leaking";
  //        type empty;
  //      }
  //      leaf ldp-stitching {
  //        description "Enable SR to LDP stitching";
  //        type empty;
  //      }
  //      container srv6 {
  //        presence "enable srv6";
  //        description "Enable IPv6 Segment Routing (SRv6)";
  //        // uses apply-advanced;
  //        list locator {
  //          key name;
  //          ordered-by user;
  //          description "SRv6 Locator";
  //          leaf name {
  //            description "Locator name";
  //            type string;
  //          }
  //          // uses apply-advanced;
  //          leaf anycast {
  //            description "Set A flag in the Prefix-Attribute sub-TLV";
  //            type empty;
  //          }
  //          list end-sid {
  //            key name;
  //            ordered-by user;
  //            leaf name {
  //              type jt:ipv6addr;
  //            }
  //            // uses apply-advanced;
  //            container flavor {
  //              presence "enable flavor";
  //              description "Configure end-SID flavor";
  //              // uses apply-advanced;
  //              leaf psp {
  //                description "Penultimate segment pop of the SRH";
  //                type empty;
  //              }
  //              leaf usp {
  //                description "Ultimate segment pop of the SRH";
  //                type empty;
  //              }
  //              leaf usd {
  //                description "Ultimate segment decapsulation";
  //                type empty;
  //              }
  //            }
  //          }
  //          container dynamic-end-sid {
  //            presence "enable dynamic-end-sid";
  //            description "Allocate end SID dynamically";
  //            // uses apply-advanced;
  //            container flavor {
  //              presence "enable flavor";
  //              description "Configure end-SID flavor";
  //              // uses apply-advanced;
  //              leaf psp {
  //                description "Penultimate segment pop of the SRH";
  //                type empty;
  //              }
  //              leaf usp {
  //                description "Ultimate segment pop of the SRH";
  //                type empty;
  //              }
  //              leaf usd {
  //                description "Ultimate segment decapsulation";
  //                type empty;
  //              }
  //            }
  //          }
  //          leaf micro-node-sid {
  //            description "Program and advertise micro-node-SID";
  //            type empty;
  //          }
  //        }
  //      }
  //      container sensor-based-stats {
  //        description "Configure sensor based stats in SPRING";
  //        // uses apply-advanced;
  //        container per-interface-per-member-link {
  //          description "Configure sensor based stats per nexthop";
  //          leaf ingress {
  //            description "Enable sensor based stats on ingress interface";
  //            type empty;
  //          }
  //          leaf egress {
  //            description "Enable sensor based stats on egress interface";
  //            type empty;
  //          }
  //        }
  //        container per-sid {
  //          description "Configure sensor based stats per spring route";
  //          leaf ingress {
  //            description "Enable sensor based stats for per-sid ingress accounting";
  //            type empty;
  //          }
  //          leaf egress {
  //            description "Enable sensor based stats for IP-MPLS egress accounting";
  //            type empty;
  //          }
  //        }
  //        container subscribe {
  //          presence "enable subscribe";
  //          description "Enable on-box sensor-based statistics collection";
  //          // uses apply-advanced;
  //          leaf interval {
  //            description "Statistics collection interval (seconds)";
  //            type union {
  //              type string {
  //                pattern "<.*>|$.*";
  //              }
  //              type uint32 {
  //                range "30 .. 86400";
  //              }
  //            }
  //          }
  //        }
  //      }
  //      container traffic-statistics {
  //        description "Enable support for traffic statistics in SPRING";
  //        // uses apply-advanced;
  //        container statistics-granularity {
  //          description "Granularity for traffic statistics in SPRING";
  //          // uses apply-advanced;
  //          leaf per-interface {
  //            description "Interface Based traffic statistics in SPRING";
  //            type empty;
  //          }
  //        }
  //        leaf congestion-protection {
  //          description "Enable tactical traffic engineering";
  //          type empty;
  //        }
  //        leaf auto-bandwidth {
  //          description "Auto bandwidth name";
  //          type string;
  //        }
  //      }
  //    }
  //    container srm6 {
  //      presence "enable srm6";
  //      description "Enable SRm6";
  //      // uses apply-advanced;
  //      container sid {
  //        description "Configure attributes for SID in srm6";
  //        // uses apply-advanced;
  //        leaf node-sid {
  //          description "Set Node SID Value";
  //          type union {
  //            type string {
  //              pattern "<.*>|$.*";
  //            }
  //            type uint32 {
  //              range "1 .. 65535";
  //            }
  //          }
  //        }
  //        leaf address {
  //          description "IPv6 address corresponding to SID";
  //          type jt:ipv6addr;
  //        }
  //      }
  //    }
  //    list level {
  //      key name;
  //      ordered-by user;
  //      description "Configure global level attributes";
  //      leaf name {
  //        description "IS-IS level number";
  //        type union {
  //          type string {
  //            pattern "<.*>|$.*";
  //          }
  //          type uint32 {
  //            range "1 .. 2";
  //          }
  //        }
  //      }
  //      // uses apply-advanced;
  //      leaf labeled-preference {
  //        description "Preference of labeled IS-IS routes";
  //        type union {
  //          type uint32;
  //          type string {
  //            pattern "<.*>|$.*";
  //          }
  //        }
  //      }
  //      leaf srv6-preference {
  //        description "Preference of SRV6 IS-IS routes";
  //        type union {
  //          type uint32;
  //          type string {
  //            pattern "<.*>|$.*";
  //          }
  //        }
  //      }
  //      leaf flex-algorithm-preference {
  //        description "Preference of flex-algorithm L-ISIS routes";
  //        type union {
  //          type uint32;
  //          type string {
  //            pattern "<.*>|$.*";
  //          }
  //        }
  //      }
  //      container source-packet-routing {
  //        presence "enable source-packet-routing";
  //        description "Enable Source Packet Routing (SPRING)";
  //        // uses apply-advanced;
  //        choice enable-disable {
  //          case case_1 {
  //            leaf disable {
  //              description "Disable Source Packet Routing on this level";
  //              type empty;
  //            }
  //          }
  //        }
  //        leaf srms-preference {
  //          description "Set SRMS preference value";
  //          type union {
  //            type string {
  //              pattern "<.*>|$.*";
  //            }
  //            type uint32 {
  //              range "0 .. 255";
  //            }
  //          }
  //        }
  //      }
  //      choice enable-disable {
  //        case case_1 {
  //          leaf disable {
  //            description "Disable IS-IS on this level";
  //            type empty;
  //          }
  //        }
  //      }
  //      leaf authentication-key {
  //        description "Authentication key (password)";
  //        type jt:unreadable;
  //      }
  //      leaf authentication-type {
  //        description "Authentication type";
  //        type enumeration {
  //          enum "md5" {
  //            description "MD5 authentication";
  //          }
  //          enum "simple" {
  //            description "Simple password authentication";
  //          }
  //        }
  //      }
  //      leaf purge-originator {
  //        description "Add Purge Originator information";
  //        type enumeration {
  //          enum "self" {
  //            description "Add POI only for self-originated purge LSPs";
  //          }
  //          enum "empty" {
  //            description "Add POI for purge LSPs who do not have POI information";
  //          }
  //        }
  //      }
  //      leaf no-hello-authentication {
  //        description "Disable authentication for hello packets";
  //        type empty;
  //      }
  //      leaf no-csnp-authentication {
  //        description "Disable authentication for CSN packets";
  //        type empty;
  //      }
  //      leaf no-psnp-authentication {
  //        description "Disable authentication for PSN packets";
  //        type empty;
  //      }
  //      leaf no-lsp-authentication {
  //        description "Disable authentication for LSP packets";
  //        type empty;
  //      }
  //      leaf authentication-key-chain {
  //        description "Key chain name";
  //        type string {
  //          length "1 .. 128";
  //        }
  //      }
  //      leaf wide-metrics-only {
  //        description "Generate wide metrics only";
  //        type empty;
  //      }
  //      leaf preference {
  //        description "Preference of internal routes";
  //        type union {
  //          type uint32;
  //          type string {
  //            pattern "<.*>|$.*";
  //          }
  //        }
  //      }
  //      leaf external-preference {
  //        description "Preference of external routes";
  //        type union {
  //          type uint32;
  //          type string {
  //            pattern "<.*>|$.*";
  //          }
  //        }
  //      }
  //      leaf prefix-export-limit {
  //        description "Maximum number of external prefixes that can be exported";
  //        type union {
  //          type string {
  //            pattern "<.*>|$.*";
  //          }
  //          type uint32 {
  //            range "0 .. 4294967295";
  //          }
  //        }
  //      }
  //      leaf max-lsp-size {
  //        description "Maximum size allowed for LSPs";
  //        type union {
  //          type string {
  //            pattern "<.*>|$.*";
  //          }
  //          type uint32 {
  //            range "512 .. 9192";
  //          }
  //        }
  //      }
  //      container flood-reflector {
  //        description "Enable flood-reflector";
  //        // uses apply-advanced;
  //        choice flood-reflector-choice {
  //          case case_1 {
  //            container reflector {
  //              description "Configure this as a flood-reflector";
  //              // uses apply-advanced;
  //              leaf cluster-id {
  //                description "Cluster-ID";
  //                type union {
  //                  type string {
  //                    pattern "<.*>|$.*";
  //                  }
  //                  type uint32 {
  //                    range "1 .. 4294967295";
  //                  }
  //                }
  //              }
  //            }
  //          }
  //          case case_2 {
  //            leaf client {
  //              description "Configure interface as flood-reflector client";
  //              type empty;
  //            }
  //          }
  //        }
  //      }
  //    }
  //    list interface-group {
  //      key name;
  //      description "Interface grouping configuration";
  //      leaf name {
  //        description "Interface group name";
  //        type string;
  //      }
  //      // uses apply-advanced;
  //      list level {
  //        key name;
  //        ordered-by user;
  //        description "Configure levels on this interface-group";
  //        leaf name {
  //          description "IS-IS level number";
  //          type union {
  //            type string {
  //              pattern "<.*>|$.*";
  //            }
  //            type uint32 {
  //              range "1 .. 2";
  //            }
  //          }
  //        }
  //        // uses apply-advanced;
  //        container ipv4-adjacency-segment {
  //          description "Configure ipv4 adjacency segment";
  //          // uses apply-advanced;
  //          container protected {
  //            description "Adjacency SID is eligible for protection";
  //            choice adjsid-type {
  //              case case_1 {
  //                container index {
  //                  description "Adjacency SID indexed from SRGB";
  //                  leaf index-number {
  //                    type union {
  //                      type string {
  //                        pattern "<.*>|$.*";
  //                      }
  //                      type uint32 {
  //                        range "0 .. 199999";
  //                      }
  //                    }
  //                  }
  //                }
  //              }
  //              case case_2 {
  //                leaf label {
  //                  description "Adjacency SID from static label pool";
  //                  type union {
  //                    type string {
  //                      pattern "<.*>|$.*";
  //                    }
  //                    type uint32 {
  //                      range "16 .. 1048575";
  //                    }
  //                  }
  //                }
  //              }
  //              case case_3 {
  //                leaf dynamic {
  //                  description "Dynamically allocate an adjacency segment";
  //                  type empty;
  //                }
  //              }
  //            }
  //          }
  //          container unprotected {
  //            description "Adjacency SID uneligible for protection";
  //            choice adjsid-type {
  //              case case_1 {
  //                container index {
  //                  description "Adjacency SID indexed from SRGB";
  //                  leaf index-number {
  //                    type union {
  //                      type string {
  //                        pattern "<.*>|$.*";
  //                      }
  //                      type uint32 {
  //                        range "0 .. 199999";
  //                      }
  //                    }
  //                  }
  //                }
  //              }
  //              case case_2 {
  //                leaf label {
  //                  description "Adjacency SID from static label pool";
  //                  type union {
  //                    type string {
  //                      pattern "<.*>|$.*";
  //                    }
  //                    type uint32 {
  //                      range "16 .. 1048575";
  //                    }
  //                  }
  //                }
  //              }
  //              case case_3 {
  //                leaf dynamic {
  //                  description "Dynamically allocate an adjacency segment";
  //                  type empty;
  //                }
  //              }
  //            }
  //          }
  //        }
  //        container ipv6-adjacency-segment {
  //          description "Configure ipv6 adjacency segment";
  //          // uses apply-advanced;
  //          container protected {
  //            description "Adjacency SID is eligible for protection";
  //            choice adjsid-type {
  //              case case_1 {
  //                container index {
  //                  description "Adjacency SID indexed from SRGB";
  //                  leaf index-number {
  //                    type union {
  //                      type string {
  //                        pattern "<.*>|$.*";
  //                      }
  //                      type uint32 {
  //                        range "0 .. 199999";
  //                      }
  //                    }
  //                  }
  //                }
  //              }
  //              case case_2 {
  //                leaf label {
  //                  description "Adjacency SID from static label pool";
  //                  type union {
  //                    type string {
  //                      pattern "<.*>|$.*";
  //                    }
  //                    type uint32 {
  //                      range "16 .. 1048575";
  //                    }
  //                  }
  //                }
  //              }
  //              case case_3 {
  //                leaf dynamic {
  //                  description "Dynamically allocate an adjacency segment";
  //                  type empty;
  //                }
  //              }
  //            }
  //          }
  //          container unprotected {
  //            description "Adjacency SID uneligible for protection";
  //            choice adjsid-type {
  //              case case_1 {
  //                container index {
  //                  description "Adjacency SID indexed from SRGB";
  //                  leaf index-number {
  //                    type union {
  //                      type string {
  //                        pattern "<.*>|$.*";
  //                      }
  //                      type uint32 {
  //                        range "0 .. 199999";
  //                      }
  //                    }
  //                  }
  //                }
  //              }
  //              case case_2 {
  //                leaf label {
  //                  description "Adjacency SID from static label pool";
  //                  type union {
  //                    type string {
  //                      pattern "<.*>|$.*";
  //                    }
  //                    type uint32 {
  //                      range "16 .. 1048575";
  //                    }
  //                  }
  //                }
  //              }
  //              case case_3 {
  //                leaf dynamic {
  //                  description "Dynamically allocate an adjacency segment";
  //                  type empty;
  //                }
  //              }
  //            }
  //          }
  //        }
  //        container srm6-adjacency-segment {
  //          description "Configure srm6 adjacency segment";
  //          // uses apply-advanced;
  //          container unprotected {
  //            description "Adjacency SID uneligible for protection";
  //            leaf sid {
  //              description "Set Adjacency SID Value";
  //              type union {
  //                type string {
  //                  pattern "<.*>|$.*";
  //                }
  //                type uint32 {
  //                  range "1 .. 65535";
  //                }
  //              }
  //            }
  //          }
  //        }
  //        list topology {
  //          key name;
  //          ordered-by user;
  //          description "Topology specific attributes";
  //          leaf name {
  //            description "Topology name";
  //            type enumeration {
  //              enum "default" {
  //                description "Default topology";
  //              }
  //              enum "ipv4-multicast" {
  //                description "IPv4 multicast topology";
  //              }
  //              enum "ipv6-unicast" {
  //                description "IPv6 unicast topology";
  //              }
  //              enum "ipv6-multicast" {
  //                description "IPv6 multicast topology";
  //              }
  //            }
  //          }
  //          // uses apply-advanced;
  //          leaf metric {
  //            description "Topology metric";
  //            type union {
  //              type string {
  //                pattern "<.*>|$.*";
  //              }
  //              type uint32 {
  //                range "0 .. 16777215";
  //              }
  //            }
  //          }
  //          container bandwidth-based-metrics {
  //            description "Configure bandwidth based metrics";
  //            // uses apply-advanced;
  //            list bandwidth {
  //              key name;
  //              description "Bandwidth threshold";
  //              leaf name {
  //                type string;
  //              }
  //              leaf metric {
  //                description "Metric associated with specified bandwidth";
  //                type union {
  //                  type string {
  //                    pattern "<.*>|$.*";
  //                  }
  //                  type uint32 {
  //                    range "0 .. 16777215";
  //                  }
  //                }
  //              }
  //            }
  //          }
  //        }
  //      }
  //      container link-group-protection {
  //        description "Configure link group protection";
  //        // uses apply-advanced;
  //        leaf minimum-bandwidth {
  //          description "Minimum bandwidth to carry traffic";
  //          type string;
  //        }
  //        leaf revert-bandwidth {
  //          description "Revert bandwidth to carry traffic";
  //          type string;
  //        }
  //      }
  //      list interface {
  //        key name;
  //        description "List interfaces for this group";
  //        leaf name {
  //          description "Interface name";
  //          type union {
  //            type jt:interface-name;
  //            type string {
  //              pattern "<.*>|$.*";
  //            }
  //          }
  //        }
  //        // uses apply-advanced;
  //        leaf weight {
  //          description "Interface weight for adjacency set";
  //          type union {
  //            type string {
  //              pattern "<.*>|$.*";
  //            }
  //            type uint32 {
  //              range "1 .. 255";
  //            }
  //          }
  //        }
  //      }
  //    }
  //    container spf-options {
  //      description "Configure SPF attributes";
  //      // uses apply-advanced;
  //      container microloop-avoidance {
  //        description "Configure microloop avoidance mechanisms";
  //        // uses apply-advanced;
  //        container post-convergence-path {
  //          presence "enable post-convergence-path";
  //          description "Temporarily install post-convergence path for routes potentially affected by microloops";
  //          // uses apply-advanced;
  //          leaf delay {
  //            description "Time after which temporary post-convergence paths are removed";
  //            units "milliseconds";
  //            type union {
  //              type string {
  //                pattern "<.*>|$.*";
  //              }
  //              type uint32 {
  //                range "500 .. 60000";
  //              }
  //            }
  //          }
  //          leaf maximum-labels {
  //            description "Set maximum number of label supported for Micro-Loop-Avoidance calculations";
  //            type union {
  //              type string {
  //                pattern "<.*>|$.*";
  //              }
  //              type uint32 {
  //                range "2 .. 8";
  //              }
  //            }
  //          }
  //          leaf maximum-srv6-sids {
  //            description "Set maximum number of SRV6 SIDs supported for Micro-Loop-Avoidance calculations";
  //            type union {
  //              type string {
  //                pattern "<.*>|$.*";
  //              }
  //              type uint32 {
  //                range "2 .. 12";
  //              }
  //            }
  //          }
  //        }
  //      }
  //      leaf delay {
  //        description "Time to wait before running an SPF";
  //        units "milliseconds";
  //        type union {
  //          type string {
  //            pattern "<.*>|$.*";
  //          }
  //          type uint32 {
  //            range "50 .. 1000";
  //          }
  //        }
  //      }
  //      leaf holddown {
  //        description "Time to hold down before running an SPF";
  //        units "milliseconds";
  //        type union {
  //          type string {
  //            pattern "<.*>|$.*";
  //          }
  //          type uint32 {
  //            range "2000 .. 10000";
  //          }
  //        }
  //      }
  //      leaf rapid-runs {
  //        description "Number of rapid SPF runs before SPF holddown";
  //        type union {
  //          type string {
  //            pattern "<.*>|$.*";
  //          }
  //          type uint32 {
  //            range "1 .. 5";
  //          }
  //        }
  //      }
  //      container multipath {
  //        description "Configure multipath options";
  //        // uses apply-advanced;
  //        container weighted {
  //          description "Weighted multipath options";
  //          // uses apply-advanced;
  //          leaf one-hop {
  //            description "Enable load balancing on onehop multipath based on interface bandwidth";
  //            type empty;
  //          }
  //        }
  //      }
  //    }
  //    container traceoptions {
  //      description "Trace options for IS-IS";
  //      // uses apply-advanced;
  //      list flag {
  //        key name;
  //        ordered-by user;
  //        description "Tracing parameters";
  //        leaf name {
  //          type enumeration {
  //            enum "traffic-statistics" {
  //              description "Trace traffic-statistics related events";
  //            }
  //            enum "post-convergence-lfa" {
  //              description "Trace post-convergence-lfa related events";
  //            }
  //            enum "error" {
  //              description "Trace errored packets";
  //            }
  //            enum "spf" {
  //              description "Trace SPF events";
  //            }
  //            enum "packets" {
  //              description "Trace IS-IS packets";
  //            }
  //            enum "hello" {
  //              description "Trace hello packets";
  //            }
  //            enum "lsp" {
  //              description "Trace link-state packets";
  //            }
  //            enum "psn" {
  //              description "Trace partial sequence number (PSN) packets";
  //            }
  //            enum "csn" {
  //              description "Trace complete sequence number (CSN) packets";
  //            }
  //            enum "layer2-map" {
  //              description "Trace ARP/ND kernel state manipulation";
  //            }
  //            enum "lsp-generation" {
  //              description "Trace LSP generation";
  //            }
  //            enum "graceful-restart" {
  //              description "Trace graceful restart events";
  //            }
  //            enum "ldp-synchronization" {
  //              description "Trace synchronization between IS-IS and LDP";
  //            }
  //            enum "nsr-synchronization" {
  //              description "Trace NSR synchronization events";
  //            }
  //            enum "spring" {
  //              description "Trace source packet routing";
  //            }
  //            enum "prefix-sid" {
  //              description "Trace source packet routing, prefix-sids";
  //            }
  //            enum "flex-algorithm" {
  //              description "Trace flex-algorithm related events";
  //            }
  //            enum "adj-sid" {
  //              description "Trace adj-sid related events";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "srv6" {
  //              description "Trace srv6 related events";
  //            }
  //            enum "rmopd" {
  //              description "Trace rmopd interactions";
  //            }
  //            enum "mapping-server" {
  //              description "Trace mapping server related events";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //    }
  //    container backup-spf-options {
  //      description "Configure backup SPF attributes";
  //      // uses apply-advanced;
  //      container remote-backup-calculation {
  //        presence "enable remote-backup-calculation";
  //        description "Calculate Remote LFA backup nexthops";
  //        // uses apply-advanced;
  //      }
  //      container use-post-convergence-lfa {
  //        presence "enable use-post-convergence-lfa";
  //        description "Calculate Post Convergence Backup Nexthops";
  //        // uses apply-advanced;
  //        leaf maximum-labels {
  //          description "Set maximum number of label supported for post convergence path calculations";
  //          type union {
  //            type string {
  //              pattern "<.*>|$.*";
  //            }
  //            type uint32 {
  //              range "2 .. 8";
  //            }
  //          }
  //        }
  //        leaf maximum-srv6-sids {
  //          description "Set maximum number of SRV6 SIDs for post convergence path calculations";
  //          type union {
  //            type string {
  //              pattern "<.*>|$.*";
  //            }
  //            type uint32 {
  //              range "2 .. 12";
  //            }
  //          }
  //        }
  //        leaf maximum-backup-paths {
  //          description "Set maximum equal cost backup post convergence paths";
  //          type union {
  //            type string {
  //              pattern "<.*>|$.*";
  //            }
  //            type uint32 {
  //              range "1 .. 8";
  //            }
  //          }
  //        }
  //      }
  //      container use-source-packet-routing {
  //        presence "enable use-source-packet-routing";
  //        description "Use SPRING routed paths for protection";
  //        // uses apply-advanced;
  //      }
  //      leaf per-prefix-calculation {
  //        description "Calculate backup nexthops for non-best prefix originators";
  //        type empty;
  //      }
  //      leaf node-link-degradation {
  //        description "Degrade to link protection when nodelink protection not available";
  //        type empty;
  //      }
  //    }
  //    list context-identifier {
  //      key name;
  //      ordered-by user;
  //      description "Configuration for advertisement of a context-identifier ";
  //      leaf name {
  //        description "Context identifier range";
  //        type jt:ipprefix;
  //      }
  //      // uses apply-advanced;
  //      list level {
  //        key name;
  //        ordered-by user;
  //        description "Configure global level attributes";
  //        leaf name {
  //          description "IS-IS level number";
  //          type union {
  //            type string {
  //              pattern "<.*>|$.*";
  //            }
  //            type uint32 {
  //              range "1 .. 2";
  //            }
  //          }
  //        }
  //        // uses apply-advanced;
  //        choice enable-disable {
  //          case case_1 {
  //            leaf disable {
  //              description "Disable advertisements to this level";
  //              type empty;
  //            }
  //          }
  //        }
  //      }
  //    }
  //    container traffic-engineering {
  //      description "Configure traffic engineering attributes";
  //      // uses apply-advanced;
  //      choice enable-disable {
  //        case case_1 {
  //          leaf disable {
  //            description "Disable traffic engineering";
  //            type empty;
  //          }
  //        }
  //      }
  //      leaf l3-unicast-topology {
  //        description "Download IGP topology into TED";
  //        type empty;
  //      }
  //      leaf ipv6 {
  //        description "Enable TEDv6";
  //        type empty;
  //      }
  //      leaf credibility-protocol-preference {
  //        description "Follow IGP protocol preference for TED protocol credibility";
  //        type empty;
  //      }
  //      leaf ipv4-multicast-rpf-routes {
  //        description "Install IPv4 routes for multicast RPF checks into inet.2";
  //        status deprecated;
  //        type empty;
  //      }
  //      leaf ignore-lsp-metrics {
  //        description "Ignore label-switched path metrics when doing shortcuts";
  //        type empty;
  //      }
  //      container tunnel-source-protocol {
  //        description "Protocols from which to pick label-switched paths";
  //        // uses apply-advanced;
  //        container rsvp {
  //          presence "enable rsvp";
  //          description "Pick label-switched paths from rsvp";
  //          // uses apply-advanced;
  //          leaf preference {
  //            description "Preference for label-switched paths from this protocol";
  //            type union {
  //              type string {
  //                pattern "<.*>|$.*";
  //              }
  //              type uint32 {
  //                range "1 .. 255";
  //              }
  //            }
  //          }
  //        }
  //        container spring-te {
  //          presence "enable spring-te";
  //          description "Pick label-switched paths from spring-te";
  //          // uses apply-advanced;
  //          leaf preference {
  //            description "Preference for label-switched paths from this protocol";
  //            type union {
  //              type string {
  //                pattern "<.*>|$.*";
  //              }
  //              type uint32 {
  //                range "1 .. 255";
  //              }
  //            }
  //          }
  //        }
  //      }
  //      list family {
  //        key name;
  //        ordered-by user;
  //        description "Address family specific traffic-engineering attributes";
  //        leaf name {
  //          type enumeration {
  //            enum "inet" {
  //              description "IPv4 family";
  //            }
  //            enum "inet6" {
  //              description "IPv6 family";
  //            }
  //            enum "inet-mpls" {
  //              description "IPv4-MPLS family";
  //            }
  //            enum "inet6-mpls" {
  //              description "IPv6-MPLS family";
  //            }
  //          }
  //        }
  //        // uses apply-advanced;
  //        container shortcuts {
  //          presence "enable shortcuts";
  //          description "Use label-switched paths as next hops, if possible";
  //          // uses apply-advanced;
  //          leaf multicast-rpf-routes {
  //            description "Install routes for multicast RPF checks into multicast RIB";
  //            type empty;
  //          }
  //          leaf-list import {
  //            ordered-by user;
  //            description "Import policy for shortcut";
  //            type jt:policy-algebra;
  //          }
  //        }
  //      }
  //      container shortcuts {
  //        presence "enable shortcuts";
  //        description "Use label-switched paths as next hops, if possible";
  //        status deprecated;
  //        // uses apply-advanced;
  //        leaf ignore-lsp-metrics {
  //          description "Ignore label-switched path metrics when doing shortcuts";
  //          status deprecated;
  //          type empty;
  //        }
  //      }
  //      container multipath {
  //        description "Configure label-switched-path multipath behavior";
  //        // uses apply-advanced;
  //        leaf lsp-equal-cost {
  //          description "Include equal cost label-switched-paths";
  //          type empty;
  //        }
  //      }
  //      container advertisement {
  //        description "Configure traffic engineering attribute advertisements";
  //        // uses apply-advanced;
  //        leaf always {
  //          description "Advertise applicable legacy TE attributes always";
  //          type empty;
  //        }
  //        container application-specific {
  //          description "Advertise application-specific TE attributes";
  //          // uses apply-advanced;
  //          container all-applications {
  //            presence "enable all-applications";
  //            description "Advertise common application-specific link attributes";
  //            // uses apply-advanced;
  //            leaf legacy {
  //              description "Use legacy TE attributes for this application";
  //              type empty;
  //            }
  //          }
  //        }
  //      }
  //    }
  //    list label-switched-path {
  //      key name;
  //      ordered-by user;
  //      description "Configuration for advertisement of a label-switched path";
  //      leaf name {
  //        description "Name of label-switched path to be advertised";
  //        type string {
  //          length "1 .. 64";
  //        }
  //      }
  //      // uses apply-advanced;
  //      list level {
  //        key name;
  //        ordered-by user;
  //        description "Configure global level attributes";
  //        leaf name {
  //          description "IS-IS level number";
  //          type union {
  //            type string {
  //              pattern "<.*>|$.*";
  //            }
  //            type uint32 {
  //              range "1 .. 2";
  //            }
  //          }
  //        }
  //        // uses apply-advanced;
  //        choice enable-disable {
  //          case case_1 {
  //            leaf disable {
  //              description "Disable advertisements to this level";
  //              type empty;
  //            }
  //          }
  //        }
  //        leaf metric {
  //          description "SPF metric for this level";
  //          type union {
  //            type string {
  //              pattern "<.*>|$.*";
  //            }
  //            type uint32 {
  //              range "0 .. 16777215";
  //            }
  //          }
  //        }
  //      }
  //    }
  //    choice enable-disable {
  //      case case_1 {
  //        leaf disable {
  //          description "Disable IS-IS";
  //          type empty;
  //        }
  //      }
  //    }
  //    leaf-list export {
  //      ordered-by user;
  //      description "Export policy";
  //      type jt:policy-algebra;
  //    }
  //    leaf-list import {
  //      ordered-by user;
  //      description "Import policy";
  //      type jt:policy-algebra;
  //    }
  //    leaf reference-bandwidth {
  //      description "Bandwidth for calculating metric defaults";
  //      type string;
  //    }
  //    choice layer2-map-choice {
  //      leaf layer2-map {
  //        description "Kernel ARP/ND creation for nexthops";
  //        type empty;
  //      }
  //      leaf no-layer2-map {
  //        description "Don't kernel ARP/ND creation for nexthops";
  //        type empty;
  //      }
  //    }
  //    leaf job-stats {
  //      description "Collect job statistics";
  //      type empty;
  //    }
  //    leaf lsp-lifetime {
  //      description "Lifetime of LSPs";
  //      units "seconds";
  //      type union {
  //        type string {
  //          pattern "<.*>|$.*";
  //        }
  //        type uint32 {
  //          range "350 .. 65535";
  //        }
  //      }
  //    }
  //    leaf max-lsp-size {
  //      description "Maximum size allowed for LSPs";
  //      default "1492";
  //      type union {
  //        type string {
  //          pattern "<.*>|$.*";
  //        }
  //        type uint32 {
  //          range "512 .. 9192";
  //        }
  //      }
  //    }
  //    leaf max-hello-size {
  //      description "Maximum size allowed for ISIS Hello PDUs";
  //      default "1492";
  //      type union {
  //        type string {
  //          pattern "<.*>|$.*";
  //        }
  //        type uint32 {
  //          range "512 .. 16000";
  //        }
  //      }
  //    }
  //    leaf max-snp-size {
  //      description "Maximum size allowed for Sequence Number (Complete/Partial) PDUs";
  //      default "1400";
  //      type union {
  //        type string {
  //          pattern "<.*>|$.*";
  //        }
  //        type uint32 {
  //          range "512 .. 1400";
  //        }
  //      }
  //    }
  //    leaf spf-delay {
  //      description "Time to wait before running an SPF";
  //      status deprecated;
  //      units "milliseconds";
  //      type union {
  //        type string {
  //          pattern "<.*>|$.*";
  //        }
  //        type uint32 {
  //          range "50 .. 120000";
  //        }
  //      }
  //    }
  //    leaf authentication-key {
  //      description "Authentication key (password)";
  //      status deprecated;
  //      type jt:unreadable;
  //    }
  //    leaf authentication-type {
  //      description "Authentication type";
  //      status deprecated;
  //      type enumeration {
  //        enum "md5" {
  //          description "MD5 authentication";
  //          status deprecated;
  //        }
  //        enum "simple" {
  //          description "Simple password authentication";
  //          status deprecated;
  //        }
  //      }
  //    }
  //    leaf loose-authentication-check {
  //      description "Verify authentication only if PDU has authentication TLV";
  //      type empty;
  //    }
  //    leaf max-areas {
  //      description "Maximum number of advertised Areas";
  //      default "3";
  //      type union {
  //        type string {
  //          pattern "<.*>|$.*";
  //        }
  //        type uint32 {
  //          range "3 .. 64";
  //        }
  //      }
  //    }
  //    leaf no-authentication-check {
  //      description "Disable authentication checking";
  //      type empty;
  //    }
  //    leaf no-ipv4-routing {
  //      description "Disable IPv4 routing";
  //      type empty;
  //    }
  //    leaf no-ipv6-routing {
  //      description "Disable IPv6 routing";
  //      type empty;
  //    }
  //    leaf clns-routing {
  //      description "Enable CLNS routing";
  //      type empty;
  //    }
  //    leaf clns-updown-compatibility {
  //      description "Set the Up/Down Bit in place of the I/E bit in CLNS TLVs";
  //      type empty;
  //    }
  //    leaf no-adjacency-holddown {
  //      description "Disable adjacency hold down";
  //      type empty;
  //    }
  //    leaf multicast-topology {
  //      description "Enable multicast topology";
  //      status deprecated;
  //      type empty;
  //    }
  //    leaf ignore-attached-bit {
  //      description "Ignore the attached bit in Level 1 LSPs";
  //      type empty;
  //    }
  //    container rib-group {
  //      description "Routing table group for importing IS-IS routes";
  //      uses rib_group_type;
  //    }
  //    container no-external-export {
  //      description "No external export";
  //      // uses apply-advanced;
  //      list protocol {
  //        key name;
  //        ordered-by user;
  //        description "Protocol parameters";
  //        leaf name {
  //          type enumeration {
  //            enum "bgp" {
  //              description "BGP";
  //            }
  //            enum "ospf" {
  //              description "OSPF";
  //            }
  //            enum "isis" {
  //              description "ISIS";
  //            }
  //            enum "l-isis" {
  //              description "Labelled ISIS";
  //            }
  //            enum "l-ospf" {
  //              description "Labelled OSPF";
  //            }
  //            enum "static" {
  //              description "Static";
  //            }
  //          }
  //        }
  //      }
  //    }
  //    container strict-dual-isis {
  //      presence "enable strict-dual-isis";
  //      description "Enable dual isis if spf computation is required for both ipv4 and ipv6 family";
  //      // uses apply-advanced;
  //      leaf holdown {
  //        description "Time to wait for ipv4 and ipv6 connectivity";
  //        status deprecated;
  //        default "12";
  //        type union {
  //          type string {
  //            pattern "<.*>|$.*";
  //          }
  //          type uint32 {
  //            range "1 .. 65535";
  //          }
  //        }
  //      }
  //      leaf holddown {
  //        description "Time to wait for ipv4 and ipv6 connectivity";
  //        default "12";
  //        type union {
  //          type string {
  //            pattern "<.*>|$.*";
  //          }
  //          type uint32 {
  //            range "1 .. 65535";
  //          }
  //        }
  //      }
  //    }
  //    container topologies {
  //      description "Enable topologies";
  //      // uses apply-advanced;
  //      leaf ipv4-multicast {
  //        description "Enable IPv4-multicast topology";
  //        type empty;
  //      }
  //      leaf ipv6-unicast {
  //        description "Enable IPv6-unicast topology";
  //        type empty;
  //      }
  //      leaf ipv6-multicast {
  //        description "Enable IPv6-multicast topology";
  //        type empty;
  //      }
  //    }
  //    container overload {
  //      presence "enable overload";
  //      description "Set the overload bit (no transit traffic)";
  //      // uses apply-advanced;
  //      leaf timeout {
  //        description "Time after which overload bit is reset";
  //        units "seconds";
  //        type union {
  //          type string {
  //            pattern "<.*>|$.*";
  //          }
  //          type uint32 {
  //            range "60 .. 3600";
  //          }
  //        }
  //      }
  //      leaf advertise-high-metrics {
  //        description "Advertise high metrics instead of setting the overload bit";
  //        type empty;
  //      }
  //      leaf allow-route-leaking {
  //        description "Allow routes to be leaked when overload is configured";
  //        type empty;
  //      }
  //      leaf internal-prefixes {
  //        description "Allow internal prefixes to be advertised with high metric";
  //        type empty;
  //      }
  //      leaf external-prefixes {
  //        description "Allow external prefixes to be advertised with high metric";
  //        type empty;
  //      }
  //    }
  //    container dynamic-overload {
  //      description "Set the dynamic overload options";
  //      // uses apply-advanced;
  //      leaf no-overload-on-prefix-export-limit {
  //        description "Do not set overload bit when prefix export limit is reached";
  //        type empty;
  //      }
  //      leaf auto-recovery {
  //        description "Enable Auto recovery to recover from dynamic overload state";
  //        type empty;
  //      }
  //    }
  //    container graceful-restart {
  //      description "IS-IS graceful restart options";
  //      choice enable-disable {
  //        case case_1 {
  //          leaf disable {
  //            description "Disable graceful restart";
  //            type empty;
  //          }
  //        }
  //      }
  //      leaf helper-disable {
  //        description "Disable graceful restart helper capability";
  //        type empty;
  //      }
  //      leaf restart-duration {
  //        description "Maximum time for graceful restart to finish";
  //        units "seconds";
  //        type union {
  //          type string {
  //            pattern "<.*>|$.*";
  //          }
  //          type uint32 {
  //            range "30 .. 300";
  //          }
  //        }
  //      }
  //    }
  //    list net {
  //      key name;
  //      description "Assign Network Entity Title (NET) configuration";
  //      leaf name {
  //        description "Assign Network Entity Title (NET) address to an IS-IS router";
  //        type jt:isoaddr;
  //      }
  //    }
  //  }
  //  grouping juniper-protocols-l2vpn {
  //    description "Layer 2 VPN, VPLS or EVPN configuration";
  //    // uses apply-advanced;
  //    leaf bum-hashing {
  //      description "Enable BUM hashing feature in the instance";
  //      type empty;
  //    }
  //    leaf enable-mac-move-action {
  //      description "Enable VPLS loop prevention feature in the instance";
  //      type empty;
  //    }
  //    leaf mac-pinning {
  //      description "Enable MAC pinning";
  //      type empty;
  //    }
  //    container mac-table-size {
  //      description "Size of MAC address forwarding table";
  //      // uses apply-advanced;
  //      leaf limit {
  //        description "Maximum number of MAC addresses";
  //        type union {
  //          type string {
  //            pattern "<.*>|$.*";
  //          }
  //          type uint32;
  //        }
  //      }
  //      leaf packet-action {
  //        description "Action when MAC limit is reached";
  //        type enumeration {
  //          enum "none" {
  //            description "Forward the packet";
  //          }
  //          enum "drop" {
  //            description "Drop packets and do not learn. Default is forward";
  //          }
  //        }
  //      }
  //    }
  //    container mac-ip-table-size {
  //      description "Size of MAC+IP bindings table";
  //      // uses apply-advanced;
  //      leaf limit {
  //        description "Maximum number of MAC+IP bindings";
  //        type union {
  //          type string {
  //            pattern "<.*>|$.*";
  //          }
  //          type uint32;
  //        }
  //      }
  //    }
  //    container interface-mac-limit {
  //      description "Maximum MAC address learned per interface";
  //      // uses apply-advanced;
  //      leaf limit {
  //        description "Maximum number of MAC addresses per interface";
  //        type union {
  //          type string {
  //            pattern "<.*>|$.*";
  //          }
  //          type uint32;
  //        }
  //      }
  //      leaf packet-action {
  //        description "Action when MAC limit is reached";
  //        type enumeration {
  //          enum "none" {
  //            description "Forward the packet";
  //          }
  //          enum "drop" {
  //            description "Drop packets and do not learn. Default is forward";
  //          }
  //          enum "log" {
  //            description "Do not drop the packet but generate an alarm, an SNMP trap or a system log entry";
  //          }
  //          enum "shutdown" {
  //            description "Disable the interface and generate an alarm, an SNMP trap or a system log entry";
  //          }
  //          enum "drop-and-log" {
  //            description "Drop the packet and generate an alarm, an SNMP trap or a system log entry";
  //          }
  //        }
  //      }
  //    }
  //    container interface-mac-ip-limit {
  //      description "Maximum MAC+IP bindings learned per interface";
  //      // uses apply-advanced;
  //      leaf limit {
  //        description "Maximum number of MAC+IP bindings per interface";
  //        type union {
  //          type string {
  //            pattern "<.*>|$.*";
  //          }
  //          type uint32;
  //        }
  //      }
  //    }
  //    container mac-move-limit {
  //      presence "enable mac-move-limit";
  //      description "Number of MAC movements allowed on this VLAN";
  //      // uses apply-advanced;
  //      choice limit-choice {
  //        case case_1 {
  //          leaf none {
  //            description "Disable mac-move-limit for this VLAN";
  //            type empty;
  //          }
  //        }
  //        case case_2 {
  //          leaf limit {
  //            description "Number of MAC movements allowed on this VLAN";
  //            type union {
  //              type string {
  //                pattern "<.*>|$.*";
  //              }
  //              type uint32 {
  //                range "1 .. 4294967295";
  //              }
  //            }
  //          }
  //        }
  //      }
  //      leaf packet-action {
  //        description "Action to be taken in case the MAC movement limit is exceeded";
  //        default "drop";
  //        type enumeration {
  //          enum "none" {
  //            description "Take no action";
  //          }
  //          enum "drop" {
  //            description "Drop the packet and do not generate an alarm";
  //          }
  //          enum "log" {
  //            description "Do not drop the packet but generate an alarm, an SNMP trap, or a system log entry.";
  //          }
  //          enum "shutdown" {
  //            description "Disable the interface and generate an alarm, an SNMP trap, or a system log entry.";
  //          }
  //          enum "drop-and-log" {
  //            description "Drop the packet and generate an alarm, an SNMP trap, or a system log entry.";
  //          }
  //          enum "vlan-member-shutdown" {
  //            description "Disable the interface of this VLAN";
  //          }
  //        }
  //      }
  //      list interface {
  //        key name;
  //        description "Interface that connect this site to the VPN";
  //        leaf name {
  //          description "Interface name";
  //          type union {
  //            type jt:interface-name;
  //            type string {
  //              pattern "<.*>|$.*";
  //            }
  //          }
  //        }
  //        // uses apply-advanced;
  //        leaf action-priority {
  //          description "Blocking priority of this interface on mac move detection";
  //          type union {
  //            type string {
  //              pattern "<.*>|$.*";
  //            }
  //            type uint32 {
  //              range "0 .. 7";
  //            }
  //          }
  //        }
  //      }
  //    }
  //    container mac-notification {
  //      presence "enable mac-notification";
  //      description "MAC notification options";
  //      // uses apply-advanced;
  //      leaf notification-interval {
  //        description "Interval for sending MAC notifications";
  //        default "30";
  //        units "seconds";
  //        type union {
  //          type string {
  //            pattern "<.*>|$.*";
  //          }
  //          type uint32 {
  //            range "1 .. 60";
  //          }
  //        }
  //      }
  //    }
  //    leaf mac-table-aging-time {
  //      description "Delay for discarding MAC address if no updates are received";
  //      units "seconds";
  //      type union {
  //        type string {
  //          pattern "<.*>|$.*";
  //        }
  //        type uint32;
  //      }
  //    }
  //    leaf no-mac-learning {
  //      description "Disable dynamic MAC address learning";
  //      type empty;
  //    }
  //    leaf no-normalization {
  //      description "Disable vlan id normalization for interfaces";
  //      type empty;
  //    }
  //    leaf drop-unknown-mac-ip {
  //      description "Drop unknown MAC-IP traffic";
  //      type empty;
  //    }
  //    leaf mac-statistics {
  //      description "Enable MAC address statistics";
  //      type empty;
  //    }
  //    container mib {
  //      presence "enable mib";
  //      description "Snmp mib options";
  //      // uses apply-advanced;
  //      container dot1q-mib {
  //        presence "enable dot1q-mib";
  //        description "Dot1q MIB configuration options";
  //        // uses apply-advanced;
  //        leaf port-list {
  //          description "Port list for staticegressports and staticuntaggedports MIB";
  //          type enumeration {
  //            enum "bit-map" {
  //              description "Port list is represented in bit-map format";
  //            }
  //            enum "string" {
  //              description "Port list is represented in string format";
  //            }
  //          }
  //        }
  //      }
  //    }
  //    container static-rvtep-mac {
  //      description "Configure Static MAC and remote VxLAN tunnel endpoint entries";
  //      // uses apply-advanced;
  //      list mac {
  //        key "mac_addr remote-vtep";
  //        description "Unicast MAC address";
  //        leaf mac_addr {
  //          type jt:mac-unicast;
  //        }
  //        leaf remote-vtep {
  //          description "Configure static remote VXLAN tunnel endpoints";
  //          type jt:ipaddr;
  //        }
  //      }
  //    }
  //    list interface {
  //      key name;
  //      description "Interface that connect this site to the VPN";
  //      leaf name {
  //        description "Interface name";
  //        type union {
  //          type jt:interface-name;
  //          type string {
  //            pattern "<.*>|$.*";
  //          }
  //        }
  //      }
  //      // uses apply-advanced;
  //      container mac-learning-priority {
  //        description "MAC learning priority for the interface";
  //        // uses apply-advanced;
  //        leaf priority {
  //          description "Mac learning priority for the interface";
  //          type union {
  //            type string {
  //              pattern "<.*>|$.*";
  //            }
  //            type uint32 {
  //              range "1 .. 65535";
  //            }
  //          }
  //        }
  //        leaf packet-action {
  //          default "discard";
  //          type enumeration {
  //            enum "discard" {
  //              description "Discard the packets and do not learn. Default is forward";
  //            }
  //            enum "forward" {
  //              description "Forward the packet";
  //            }
  //          }
  //        }
  //      }
  //      container interface-mac-limit {
  //        description "Maximum number of MAC addresses learned on the interface";
  //        // uses apply-advanced;
  //        leaf limit {
  //          description "Maximum number of MAC addresses per interface";
  //          type union {
  //            type string {
  //              pattern "<.*>|$.*";
  //            }
  //            type uint32;
  //          }
  //        }
  //        leaf disable {
  //          description "Disable interface for interface-mac-limit";
  //          type empty;
  //        }
  //        leaf packet-action {
  //          description "Action when MAC limit is reached";
  //          type enumeration {
  //            enum "none" {
  //              description "Forward the packet";
  //            }
  //            enum "drop" {
  //              description "Drop packets and do not learn. Default is forward";
  //            }
  //            enum "log" {
  //              description "Do not drop the packet but generate an alarm, an SNMP trap or a system log entry";
  //            }
  //            enum "shutdown" {
  //              description "Disable the interface and generate an alarm, an SNMP trap or a system log entry";
  //            }
  //            enum "drop-and-log" {
  //              description "Drop the packet and generate an alarm, an SNMP trap or a system log entry";
  //            }
  //          }
  //        }
  //      }
  //      leaf action-priority {
  //        description "Blocking priority of this interface on mac move detection";
  //        type union {
  //          type string {
  //            pattern "<.*>|$.*";
  //          }
  //          type uint32 {
  //            range "0 .. 8";
  //          }
  //        }
  //      }
  //      list static-mac {
  //        key name;
  //        ordered-by user;
  //        description "Static MAC addresses assigned to this interface";
  //        leaf name {
  //          description "MAC address";
  //          type jt:mac-addr;
  //        }
  //        // uses apply-advanced;
  //        list vlan-id {
  //          key name;
  //          ordered-by user;
  //          description "VLAN ID of learning VLAN";
  //          leaf name {
  //            description "Learning VLAN";
  //            type union {
  //              type string {
  //                pattern "<.*>|$.*";
  //              }
  //              type uint32 {
  //                range "0 .. 4094";
  //              }
  //            }
  //          }
  //          // uses apply-advanced;
  //        }
  //      }
  //      list static-mac-ip {
  //        key name;
  //        ordered-by user;
  //        description "Static MAC-IP address bindings";
  //        leaf name {
  //          description "IP address";
  //          type jt:ipaddr;
  //        }
  //        // uses apply-advanced;
  //        leaf-list mac-address {
  //          ordered-by user;
  //          description "MAC address";
  //          type jt:mac-unicast;
  //          max-elements 8;
  //        }
  //        leaf router {
  //          description "Router flag for ipv6 addresses";
  //          type empty;
  //        }
  //      }
  //      container interface-mac-ip-limit {
  //        description "Maximum number of MAC+IP bindings learned on the interface";
  //        // uses apply-advanced;
  //        leaf limit {
  //          description "Maximum number of MAC+IP bindings per interface";
  //          type union {
  //            type string {
  //              pattern "<.*>|$.*";
  //            }
  //            type uint32;
  //          }
  //        }
  //      }
  //      leaf no-mac-learning {
  //        description "Disable dynamic MAC address learning";
  //        type empty;
  //      }
  //      leaf mac-pinning {
  //        description "Enable MAC pinning";
  //        type empty;
  //      }
  //      leaf persistent-learning {
  //        description "Enable persistent MAC learning on this interface";
  //        type empty;
  //      }
  //      container vpws-service-id {
  //        presence "enable vpws-service-id";
  //        description "Service-id for EVPN VPWS routing instance";
  //        // uses apply-advanced;
  //        leaf local {
  //          description "Local EVPN VPWS service id";
  //          type union {
  //            type string {
  //              pattern "<.*>|$.*";
  //            }
  //            type uint32 {
  //              range "1 .. 16777215";
  //            }
  //          }
  //        }
  //        leaf remote {
  //          description "Remote EVPN VPWS service id";
  //          type union {
  //            type string {
  //              pattern "<.*>|$.*";
  //            }
  //            type uint32 {
  //              range "1 .. 16777215";
  //            }
  //          }
  //        }
  //        container source-packet-routing {
  //          presence "enable source-packet-routing";
  //          // uses apply-advanced;
  //          container srv6 {
  //            description "Enable IPv6 segment routing (SRv6)";
  //            container locator {
  //              description "SRv6 locator";
  //              leaf loc-name {
  //                description "Locator name";
  //                type string;
  //              }
  //              leaf end-dx2-sid {
  //                description "End dx2 sid with 128 bit address";
  //                type jt:ipv6addr;
  //              }
  //            }
  //          }
  //        }
  //      }
  //      leaf flow-label-transmit-static {
  //        description "Push Flow Label on PW packets sent to remote PE";
  //        type empty;
  //      }
  //      leaf flow-label-receive-static {
  //        description "Pop Flow Label from PW packets received from remote PE";
  //        type empty;
  //      }
  //      leaf protect-interface {
  //        description "Name of protect interface";
  //        type union {
  //          type jt:interface-name;
  //          type string {
  //            pattern "<.*>|$.*";
  //          }
  //        }
  //      }
  //      leaf remote-site-id {
  //        description "Site identifier associated with this interface";
  //        type union {
  //          type string {
  //            pattern "<.*>|$.*";
  //          }
  //          type uint32 {
  //            range "1 .. 65534";
  //          }
  //        }
  //      }
  //      leaf target-attachment-identifier {
  //        description "FEC 129 VPWS target attachment identifier";
  //        type string {
  //        }
  //      }
  //      leaf flow-label-transmit {
  //        description "Advertise capability to push Flow Label in transmit direction to remote PE";
  //        type empty;
  //      }
  //      leaf flow-label-receive {
  //        description "Advertise capability to pop Flow Label in receive direction to remote PE";
  //        type empty;
  //      }
  //      choice cword {
  //        case case_1 {
  //          leaf control-word {
  //            description "Add control word to the Layer 2 encapsulation";
  //            type empty;
  //          }
  //        }
  //        case case_2 {
  //          leaf no-control-word {
  //            description "Disables control word on the Layer 2 encapsulation";
  //            type empty;
  //          }
  //        }
  //      }
  //      leaf encapsulation-type {
  //        description "Encapsulation type for VPN";
  //        type enumeration {
  //          enum "atm-aal5" {
  //            description "ATM AAL/5 encapsulation";
  //          }
  //          enum "atm-cell" {
  //            description "ATM port promiscuous mode cell encapsulation";
  //          }
  //          enum "atm-cell-port-mode" {
  //            description "ATM port promiscuous mode cell encapsulation";
  //          }
  //          enum "atm-cell-vp-mode" {
  //            description "ATM VP promiscuous mode cell encapsulation";
  //          }
  //          enum "atm-cell-vc-mode" {
  //            description "ATM non-promiscuous cell encapsulation";
  //          }
  //          enum "frame-relay" {
  //            description "Frame Relay encapsulation";
  //          }
  //          enum "ppp" {
  //            description "PPP encapsulation";
  //          }
  //          enum "cisco-hdlc" {
  //            description "Cisco-compatible HDLC encapsulation";
  //          }
  //          enum "ethernet-vlan" {
  //            description "Ethernet VLAN encapsulation";
  //          }
  //          enum "ethernet" {
  //            description "Ethernet encapsulation";
  //          }
  //          enum "interworking" {
  //            description "Layer 2.5 interworking VPN";
  //          }
  //          enum "frame-relay-port-mode" {
  //            description "Frame Relay port mode encapsulation";
  //          }
  //          enum "satop-t1" {
  //            description "SATOP-T1 based Layer 2 VPN";
  //          }
  //          enum "satop-e1" {
  //            description "SATOP-E1 based Layer 2 VPN";
  //          }
  //          enum "satop-t3" {
  //            description "SATOP-T3 based Layer 2 VPN";
  //          }
  //          enum "satop-e3" {
  //            description "SATOP-E3 based Layer 2 VPN";
  //          }
  //          enum "cesop" {
  //            description "CESOP based Layer 2 VPN";
  //          }
  //        }
  //      }
  //      leaf ignore-encapsulation-mismatch {
  //        description "Allow different encapsulation types on local and remote end";
  //        type empty;
  //      }
  //      leaf mtu {
  //        description "MTU to be advertised to the remote end";
  //        type union {
  //          type string {
  //            pattern "<.*>|$.*";
  //          }
  //          type uint16 {
  //            range "512 .. 65535";
  //          }
  //        }
  //      }
  //      leaf ignore-mtu-mismatch {
  //        description "Allow different MTU values on local and remote end";
  //        type empty;
  //      }
  //      leaf pseudowire-status-tlv {
  //        description "Send pseudowire status TLV";
  //        type empty;
  //      }
  //      container oam {
  //        description "OAM Configuration for VPN";
  //        // uses apply-advanced;
  //        leaf ping-interval {
  //          description "Time interval between ping messages";
  //          default "60";
  //          units "seconds";
  //          type union {
  //            type string {
  //              pattern "<.*>|$.*";
  //            }
  //            type uint16 {
  //              range "30 .. 3600";
  //            }
  //          }
  //        }
  //        leaf ping-multiplier {
  //          description "Number of ping reply missed before declaring BFD down";
  //          type union {
  //            type string {
  //              pattern "<.*>|$.*";
  //            }
  //            type uint8 {
  //              range "1 .. 5";
  //            }
  //          }
  //        }
  //        container bfd-liveness-detection {
  //          description "Bidirectional Forwarding Detection (BFD) options";
  //          // uses apply-advanced;
  //          leaf version {
  //            description "BFD protocol version number";
  //            default "automatic";
  //            type enumeration {
  //              enum "0" {
  //                description "BFD version 0 (deprecated)";
  //              }
  //              enum "1" {
  //                description "BFD version 1";
  //              }
  //              enum "automatic" {
  //                description "Choose BFD version automatically";
  //              }
  //            }
  //          }
  //          leaf minimum-interval {
  //            description "Minimum transmit and receive interval";
  //            units "milliseconds";
  //            type union {
  //              type string {
  //                pattern "<.*>|$.*";
  //              }
  //              type uint32 {
  //                range "1 .. 255000";
  //              }
  //            }
  //          }
  //          leaf minimum-transmit-interval {
  //            description "Minimum transmit interval";
  //            status deprecated;
  //            units "milliseconds";
  //            type union {
  //              type string {
  //                pattern "<.*>|$.*";
  //              }
  //              type uint32 {
  //                range "1 .. 255000";
  //              }
  //            }
  //          }
  //          leaf minimum-receive-interval {
  //            description "Minimum receive interval";
  //            units "milliseconds";
  //            type union {
  //              type string {
  //                pattern "<.*>|$.*";
  //              }
  //              type uint32 {
  //                range "1 .. 255000";
  //              }
  //            }
  //          }
  //          leaf multiplier {
  //            description "Detection time multiplier";
  //            default "3";
  //            type union {
  //              type string {
  //                pattern "<.*>|$.*";
  //              }
  //              type uint32 {
  //                range "1 .. 255";
  //              }
  //            }
  //          }
  //          leaf inline-disable {
  //            description "Disable inline mode for this BFD session";
  //            type empty;
  //          }
  //          leaf pdu-size {
  //            description "BFD transport protocol payload size";
  //            default "24";
  //            type union {
  //              type string {
  //                pattern "<.*>|$.*";
  //              }
  //              type uint32 {
  //                range "24 .. 9000";
  //              }
  //            }
  //          }
  //          choice adaptation-choice {
  //            case case_1 {
  //              leaf no-adaptation {
  //                description "Disable adaptation";
  //                type empty;
  //              }
  //            }
  //          }
  //          container transmit-interval {
  //            description "Transmit-interval options";
  //            // uses apply-advanced;
  //            leaf minimum-interval {
  //              description "Minimum transmit interval";
  //              units "milliseconds";
  //              type union {
  //                type string {
  //                  pattern "<.*>|$.*";
  //                }
  //                type uint32 {
  //                  range "1 .. 255000";
  //                }
  //              }
  //            }
  //            leaf threshold {
  //              description "High transmit interval triggering a trap";
  //              units "milliseconds";
  //              type union {
  //                type uint32;
  //                type string {
  //                  pattern "<.*>|$.*";
  //                }
  //              }
  //            }
  //          }
  //          container detection-time {
  //            description "Detection-time options";
  //            // uses apply-advanced;
  //            leaf threshold {
  //              description "High detection-time triggering a trap";
  //              units "milliseconds";
  //              type union {
  //                type uint32;
  //                type string {
  //                  pattern "<.*>|$.*";
  //                }
  //              }
  //            }
  //          }
  //        }
  //      }
  //      leaf community {
  //        description "Community associated with this interface";
  //        type string;
  //      }
  //      leaf description {
  //        description "Text description";
  //        type string;
  //      }
  //    }
  //    list site {
  //      key name;
  //      description "Sites connected to this provider equipment";
  //      leaf name {
  //        description "Name of Layer 2 VPN or VPLS site";
  //        type string;
  //      }
  //      // uses apply-advanced;
  //      leaf mac-pinning {
  //        description "Enable MAC pinning";
  //        type empty;
  //      }
  //      list mesh-group {
  //        key name;
  //        ordered-by user;
  //        description "Mesh-groups that are part of this site";
  //        leaf name {
  //          description "Mesh-group name";
  //          type string;
  //        }
  //        // uses apply-advanced;
  //      }
  //      list interface {
  //        key name;
  //        description "Interface that connect this site to the VPN";
  //        leaf name {
  //          description "Interface name";
  //          type union {
  //            type jt:interface-name;
  //            type string {
  //              pattern "<.*>|$.*";
  //            }
  //          }
  //        }
  //        // uses apply-advanced;
  //        container mac-learning-priority {
  //          description "MAC learning priority for the interface";
  //          // uses apply-advanced;
  //          leaf priority {
  //            description "Mac learning priority for the interface";
  //            type union {
  //              type string {
  //                pattern "<.*>|$.*";
  //              }
  //              type uint32 {
  //                range "1 .. 65535";
  //              }
  //            }
  //          }
  //          leaf packet-action {
  //            default "discard";
  //            type enumeration {
  //              enum "discard" {
  //                description "Discard the packets and do not learn. Default is forward";
  //              }
  //              enum "forward" {
  //                description "Forward the packet";
  //              }
  //            }
  //          }
  //        }
  //        container interface-mac-limit {
  //          description "Maximum number of MAC addresses learned on the interface";
  //          // uses apply-advanced;
  //          leaf limit {
  //            description "Maximum number of MAC addresses per interface";
  //            type union {
  //              type string {
  //                pattern "<.*>|$.*";
  //              }
  //              type uint32;
  //            }
  //          }
  //          leaf disable {
  //            description "Disable interface for interface-mac-limit";
  //            type empty;
  //          }
  //          leaf packet-action {
  //            description "Action when MAC limit is reached";
  //            type enumeration {
  //              enum "none" {
  //                description "Forward the packet";
  //              }
  //              enum "drop" {
  //                description "Drop packets and do not learn. Default is forward";
  //              }
  //              enum "log" {
  //                description "Do not drop the packet but generate an alarm, an SNMP trap or a system log entry";
  //              }
  //              enum "shutdown" {
  //                description "Disable the interface and generate an alarm, an SNMP trap or a system log entry";
  //              }
  //              enum "drop-and-log" {
  //                description "Drop the packet and generate an alarm, an SNMP trap or a system log entry";
  //              }
  //            }
  //          }
  //        }
  //        leaf action-priority {
  //          description "Blocking priority of this interface on mac move detection";
  //          type union {
  //            type string {
  //              pattern "<.*>|$.*";
  //            }
  //            type uint32 {
  //              range "0 .. 8";
  //            }
  //          }
  //        }
  //        list static-mac {
  //          key name;
  //          ordered-by user;
  //          description "Static MAC addresses assigned to this interface";
  //          leaf name {
  //            description "MAC address";
  //            type jt:mac-addr;
  //          }
  //          // uses apply-advanced;
  //          list vlan-id {
  //            key name;
  //            ordered-by user;
  //            description "VLAN ID of learning VLAN";
  //            leaf name {
  //              description "Learning VLAN";
  //              type union {
  //                type string {
  //                  pattern "<.*>|$.*";
  //                }
  //                type uint32 {
  //                  range "0 .. 4094";
  //                }
  //              }
  //            }
  //            // uses apply-advanced;
  //          }
  //        }
  //        list static-mac-ip {
  //          key name;
  //          ordered-by user;
  //          description "Static MAC-IP address bindings";
  //          leaf name {
  //            description "IP address";
  //            type jt:ipaddr;
  //          }
  //          // uses apply-advanced;
  //          leaf-list mac-address {
  //            ordered-by user;
  //            description "MAC address";
  //            type jt:mac-unicast;
  //            max-elements 8;
  //          }
  //          leaf router {
  //            description "Router flag for ipv6 addresses";
  //            type empty;
  //          }
  //        }
  //        container interface-mac-ip-limit {
  //          description "Maximum number of MAC+IP bindings learned on the interface";
  //          // uses apply-advanced;
  //          leaf limit {
  //            description "Maximum number of MAC+IP bindings per interface";
  //            type union {
  //              type string {
  //                pattern "<.*>|$.*";
  //              }
  //              type uint32;
  //            }
  //          }
  //        }
  //        leaf no-mac-learning {
  //          description "Disable dynamic MAC address learning";
  //          type empty;
  //        }
  //        leaf mac-pinning {
  //          description "Enable MAC pinning";
  //          type empty;
  //        }
  //        leaf persistent-learning {
  //          description "Enable persistent MAC learning on this interface";
  //          type empty;
  //        }
  //        leaf remote-site-id {
  //          description "Site identifier associated with this interface";
  //          type union {
  //            type string {
  //              pattern "<.*>|$.*";
  //            }
  //            type uint32 {
  //              range "1 .. 65534";
  //            }
  //          }
  //        }
  //        leaf target-attachment-identifier {
  //          description "FEC 129 VPWS target attachment identifier";
  //          type string {
  //          }
  //        }
  //        leaf flow-label-transmit {
  //          description "Advertise capability to push Flow Label in transmit direction to remote PE";
  //          type empty;
  //        }
  //        leaf flow-label-receive {
  //          description "Advertise capability to pop Flow Label in receive direction to remote PE";
  //          type empty;
  //        }
  //        choice cword {
  //          case case_1 {
  //            leaf control-word {
  //              description "Add control word to the Layer 2 encapsulation";
  //              type empty;
  //            }
  //          }
  //          case case_2 {
  //            leaf no-control-word {
  //              description "Disables control word on the Layer 2 encapsulation";
  //              type empty;
  //            }
  //          }
  //        }
  //        leaf encapsulation-type {
  //          description "Encapsulation type for VPN";
  //          type enumeration {
  //            enum "atm-aal5" {
  //              description "ATM AAL/5 encapsulation";
  //            }
  //            enum "atm-cell" {
  //              description "ATM port promiscuous mode cell encapsulation";
  //            }
  //            enum "atm-cell-port-mode" {
  //              description "ATM port promiscuous mode cell encapsulation";
  //            }
  //            enum "atm-cell-vp-mode" {
  //              description "ATM VP promiscuous mode cell encapsulation";
  //            }
  //            enum "atm-cell-vc-mode" {
  //              description "ATM non-promiscuous cell encapsulation";
  //            }
  //            enum "frame-relay" {
  //              description "Frame Relay encapsulation";
  //            }
  //            enum "ppp" {
  //              description "PPP encapsulation";
  //            }
  //            enum "cisco-hdlc" {
  //              description "Cisco-compatible HDLC encapsulation";
  //            }
  //            enum "ethernet-vlan" {
  //              description "Ethernet VLAN encapsulation";
  //            }
  //            enum "ethernet" {
  //              description "Ethernet encapsulation";
  //            }
  //            enum "interworking" {
  //              description "Layer 2.5 interworking VPN";
  //            }
  //            enum "frame-relay-port-mode" {
  //              description "Frame Relay port mode encapsulation";
  //            }
  //            enum "satop-t1" {
  //              description "SATOP-T1 based Layer 2 VPN";
  //            }
  //            enum "satop-e1" {
  //              description "SATOP-E1 based Layer 2 VPN";
  //            }
  //            enum "satop-t3" {
  //              description "SATOP-T3 based Layer 2 VPN";
  //            }
  //            enum "satop-e3" {
  //              description "SATOP-E3 based Layer 2 VPN";
  //            }
  //            enum "cesop" {
  //              description "CESOP based Layer 2 VPN";
  //            }
  //          }
  //        }
  //        leaf ignore-encapsulation-mismatch {
  //          description "Allow different encapsulation types on local and remote end";
  //          type empty;
  //        }
  //        leaf mtu {
  //          description "MTU to be advertised to the remote end";
  //          type union {
  //            type string {
  //              pattern "<.*>|$.*";
  //            }
  //            type uint16 {
  //              range "512 .. 65535";
  //            }
  //          }
  //        }
  //        leaf ignore-mtu-mismatch {
  //          description "Allow different MTU values on local and remote end";
  //          type empty;
  //        }
  //        leaf pseudowire-status-tlv {
  //          description "Send pseudowire status TLV";
  //          type empty;
  //        }
  //        container oam {
  //          description "OAM Configuration for VPN";
  //          // uses apply-advanced;
  //          leaf ping-interval {
  //            description "Time interval between ping messages";
  //            default "60";
  //            units "seconds";
  //            type union {
  //              type string {
  //                pattern "<.*>|$.*";
  //              }
  //              type uint16 {
  //                range "30 .. 3600";
  //              }
  //            }
  //          }
  //          leaf ping-multiplier {
  //            description "Number of ping reply missed before declaring BFD down";
  //            type union {
  //              type string {
  //                pattern "<.*>|$.*";
  //              }
  //              type uint8 {
  //                range "1 .. 5";
  //              }
  //            }
  //          }
  //          container bfd-liveness-detection {
  //            description "Bidirectional Forwarding Detection (BFD) options";
  //            // uses apply-advanced;
  //            leaf version {
  //              description "BFD protocol version number";
  //              default "automatic";
  //              type enumeration {
  //                enum "0" {
  //                  description "BFD version 0 (deprecated)";
  //                }
  //                enum "1" {
  //                  description "BFD version 1";
  //                }
  //                enum "automatic" {
  //                  description "Choose BFD version automatically";
  //                }
  //              }
  //            }
  //            leaf minimum-interval {
  //              description "Minimum transmit and receive interval";
  //              units "milliseconds";
  //              type union {
  //                type string {
  //                  pattern "<.*>|$.*";
  //                }
  //                type uint32 {
  //                  range "1 .. 255000";
  //                }
  //              }
  //            }
  //            leaf minimum-transmit-interval {
  //              description "Minimum transmit interval";
  //              status deprecated;
  //              units "milliseconds";
  //              type union {
  //                type string {
  //                  pattern "<.*>|$.*";
  //                }
  //                type uint32 {
  //                  range "1 .. 255000";
  //                }
  //              }
  //            }
  //            leaf minimum-receive-interval {
  //              description "Minimum receive interval";
  //              units "milliseconds";
  //              type union {
  //                type string {
  //                  pattern "<.*>|$.*";
  //                }
  //                type uint32 {
  //                  range "1 .. 255000";
  //                }
  //              }
  //            }
  //            leaf multiplier {
  //              description "Detection time multiplier";
  //              default "3";
  //              type union {
  //                type string {
  //                  pattern "<.*>|$.*";
  //                }
  //                type uint32 {
  //                  range "1 .. 255";
  //                }
  //              }
  //            }
  //            leaf inline-disable {
  //              description "Disable inline mode for this BFD session";
  //              type empty;
  //            }
  //            leaf pdu-size {
  //              description "BFD transport protocol payload size";
  //              default "24";
  //              type union {
  //                type string {
  //                  pattern "<.*>|$.*";
  //                }
  //                type uint32 {
  //                  range "24 .. 9000";
  //                }
  //              }
  //            }
  //            choice adaptation-choice {
  //              case case_1 {
  //                leaf no-adaptation {
  //                  description "Disable adaptation";
  //                  type empty;
  //                }
  //              }
  //            }
  //            container transmit-interval {
  //              description "Transmit-interval options";
  //              // uses apply-advanced;
  //              leaf minimum-interval {
  //                description "Minimum transmit interval";
  //                units "milliseconds";
  //                type union {
  //                  type string {
  //                    pattern "<.*>|$.*";
  //                  }
  //                  type uint32 {
  //                    range "1 .. 255000";
  //                  }
  //                }
  //              }
  //              leaf threshold {
  //                description "High transmit interval triggering a trap";
  //                units "milliseconds";
  //                type union {
  //                  type uint32;
  //                  type string {
  //                    pattern "<.*>|$.*";
  //                  }
  //                }
  //              }
  //            }
  //            container detection-time {
  //              description "Detection-time options";
  //              // uses apply-advanced;
  //              leaf threshold {
  //                description "High detection-time triggering a trap";
  //                units "milliseconds";
  //                type union {
  //                  type uint32;
  //                  type string {
  //                    pattern "<.*>|$.*";
  //                  }
  //                }
  //              }
  //            }
  //          }
  //        }
  //        leaf community {
  //          description "Community associated with this interface";
  //          type string;
  //        }
  //        leaf description {
  //          description "Text description";
  //          type string;
  //        }
  //      }
  //      choice site-identifier-mode {
  //        case case_1 {
  //          leaf site-identifier {
  //            description "Layer 2 VPN or VPLS site identifier (unique in the VPN)";
  //            type union {
  //              type string {
  //                pattern "<.*>|$.*";
  //              }
  //              type uint32 {
  //                range "1 .. 65534";
  //              }
  //            }
  //          }
  //        }
  //        case case_2 {
  //          container automatic-site-id {
  //            presence "enable automatic-site-id";
  //            description "Enable automatic assignment of site identifier";
  //            // uses apply-advanced;
  //            leaf startup-wait-time {
  //              description "Time to wait at startup before claming a site identifier (seconds)";
  //              units "seconds";
  //              type union {
  //                type string {
  //                  pattern "<.*>|$.*";
  //                }
  //                type uint32 {
  //                  range "1 .. 3600";
  //                }
  //              }
  //            }
  //            leaf new-site-wait-time {
  //              description "Time to wait before claiming a site identifier";
  //              units "seconds";
  //              type union {
  //                type string {
  //                  pattern "<.*>|$.*";
  //                }
  //                type uint32 {
  //                  range "1 .. 3600";
  //                }
  //              }
  //            }
  //            leaf collision-detect-time {
  //              description "Time to wait for detecting a collision";
  //              units "seconds";
  //              type union {
  //                type string {
  //                  pattern "<.*>|$.*";
  //                }
  //                type uint32 {
  //                  range "1 .. 3600";
  //                }
  //              }
  //            }
  //            container reclaim-wait-time {
  //              presence "enable reclaim-wait-time";
  //              description "Time to wait for reclaiming a site identifier";
  //              leaf minimum {
  //                description "Minimum wait time";
  //                units "milliseconds";
  //                type union {
  //                  type uint32;
  //                  type string {
  //                    pattern "<.*>|$.*";
  //                  }
  //                }
  //              }
  //              leaf maximum {
  //                description "Maximum wait time";
  //                units "milliseconds";
  //                type union {
  //                  type uint32;
  //                  type string {
  //                    pattern "<.*>|$.*";
  //                  }
  //                }
  //              }
  //            }
  //          }
  //        }
  //      }
  //      leaf source-attachment-identifier {
  //        description "FEC 129 VPWS source attachment identifier";
  //        type string {
  //        }
  //      }
  //      leaf flow-label-transmit {
  //        description "Advertise capability to push Flow Label in transmit direction to remote PE";
  //        type empty;
  //      }
  //      leaf flow-label-receive {
  //        description "Advertise capability to push Flow Label in receive direction to remote PE";
  //        type empty;
  //      }
  //      leaf encapsulation-type {
  //        description "Encapsulation type for VPN";
  //        type enumeration {
  //          enum "atm-aal5" {
  //            description "ATM AAL/5 encapsulation";
  //          }
  //          enum "atm-cell" {
  //            description "ATM port promiscuous mode cell encapsulation";
  //          }
  //          enum "atm-cell-port-mode" {
  //            description "ATM port promiscuous mode cell encapsulation";
  //          }
  //          enum "atm-cell-vp-mode" {
  //            description "ATM VP promiscuous mode cell encapsulation";
  //          }
  //          enum "atm-cell-vc-mode" {
  //            description "ATM non-promiscuous cell encapsulation";
  //          }
  //          enum "frame-relay" {
  //            description "Frame Relay encapsulation";
  //          }
  //          enum "ppp" {
  //            description "PPP encapsulation";
  //          }
  //          enum "cisco-hdlc" {
  //            description "Cisco-compatible HDLC encapsulation";
  //          }
  //          enum "ethernet-vlan" {
  //            description "Ethernet VLAN encapsulation";
  //          }
  //          enum "ethernet" {
  //            description "Ethernet encapsulation";
  //          }
  //          enum "interworking" {
  //            description "Layer 2.5 interworking VPN";
  //          }
  //          enum "frame-relay-port-mode" {
  //            description "Frame Relay port mode encapsulation";
  //          }
  //          enum "satop-t1" {
  //            description "SATOP-T1 based Layer 2 VPN";
  //          }
  //          enum "satop-e1" {
  //            description "SATOP-E1 based Layer 2 VPN";
  //          }
  //          enum "satop-t3" {
  //            description "SATOP-T3 based Layer 2 VPN";
  //          }
  //          enum "satop-e3" {
  //            description "SATOP-E3 based Layer 2 VPN";
  //          }
  //          enum "cesop" {
  //            description "CESOP based Layer 2 VPN";
  //          }
  //        }
  //      }
  //      leaf ignore-encapsulation-mismatch {
  //        description "Allow different encapsulation types on local and remote end";
  //        type empty;
  //      }
  //      choice cword {
  //        case case_1 {
  //          leaf control-word {
  //            description "Adds control-word to the Layer 2 encapsulation";
  //            type empty;
  //          }
  //        }
  //        case case_2 {
  //          leaf no-control-word {
  //            description "Disables control-word to the Layer 2 encapsulation";
  //            type empty;
  //          }
  //        }
  //      }
  //      leaf pseudowire-status-tlv {
  //        description "Send pseudowire status TLV";
  //        type empty;
  //      }
  //      container oam {
  //        description "OAM Configuration for VPN";
  //        // uses apply-advanced;
  //        leaf ping-interval {
  //          description "Time interval between ping messages";
  //          default "60";
  //          units "seconds";
  //          type union {
  //            type string {
  //              pattern "<.*>|$.*";
  //            }
  //            type uint16 {
  //              range "30 .. 3600";
  //            }
  //          }
  //        }
  //        leaf ping-multiplier {
  //          description "Number of ping reply missed before declaring BFD down";
  //          type union {
  //            type string {
  //              pattern "<.*>|$.*";
  //            }
  //            type uint8 {
  //              range "1 .. 5";
  //            }
  //          }
  //        }
  //        container bfd-liveness-detection {
  //          description "Bidirectional Forwarding Detection (BFD) options";
  //          // uses apply-advanced;
  //          leaf version {
  //            description "BFD protocol version number";
  //            default "automatic";
  //            type enumeration {
  //              enum "0" {
  //                description "BFD version 0 (deprecated)";
  //              }
  //              enum "1" {
  //                description "BFD version 1";
  //              }
  //              enum "automatic" {
  //                description "Choose BFD version automatically";
  //              }
  //            }
  //          }
  //          leaf minimum-interval {
  //            description "Minimum transmit and receive interval";
  //            units "milliseconds";
  //            type union {
  //              type string {
  //                pattern "<.*>|$.*";
  //              }
  //              type uint32 {
  //                range "1 .. 255000";
  //              }
  //            }
  //          }
  //          leaf minimum-transmit-interval {
  //            description "Minimum transmit interval";
  //            status deprecated;
  //            units "milliseconds";
  //            type union {
  //              type string {
  //                pattern "<.*>|$.*";
  //              }
  //              type uint32 {
  //                range "1 .. 255000";
  //              }
  //            }
  //          }
  //          leaf minimum-receive-interval {
  //            description "Minimum receive interval";
  //            units "milliseconds";
  //            type union {
  //              type string {
  //                pattern "<.*>|$.*";
  //              }
  //              type uint32 {
  //                range "1 .. 255000";
  //              }
  //            }
  //          }
  //          leaf multiplier {
  //            description "Detection time multiplier";
  //            default "3";
  //            type union {
  //              type string {
  //                pattern "<.*>|$.*";
  //              }
  //              type uint32 {
  //                range "1 .. 255";
  //              }
  //            }
  //          }
  //          leaf inline-disable {
  //            description "Disable inline mode for this BFD session";
  //            type empty;
  //          }
  //          leaf pdu-size {
  //            description "BFD transport protocol payload size";
  //            default "24";
  //            type union {
  //              type string {
  //                pattern "<.*>|$.*";
  //              }
  //              type uint32 {
  //                range "24 .. 9000";
  //              }
  //            }
  //          }
  //          choice adaptation-choice {
  //            case case_1 {
  //              leaf no-adaptation {
  //                description "Disable adaptation";
  //                type empty;
  //              }
  //            }
  //          }
  //          container transmit-interval {
  //            description "Transmit-interval options";
  //            // uses apply-advanced;
  //            leaf minimum-interval {
  //              description "Minimum transmit interval";
  //              units "milliseconds";
  //              type union {
  //                type string {
  //                  pattern "<.*>|$.*";
  //                }
  //                type uint32 {
  //                  range "1 .. 255000";
  //                }
  //              }
  //            }
  //            leaf threshold {
  //              description "High transmit interval triggering a trap";
  //              units "milliseconds";
  //              type union {
  //                type uint32;
  //                type string {
  //                  pattern "<.*>|$.*";
  //                }
  //              }
  //            }
  //          }
  //          container detection-time {
  //            description "Detection-time options";
  //            // uses apply-advanced;
  //            leaf threshold {
  //              description "High detection-time triggering a trap";
  //              units "milliseconds";
  //              type union {
  //                type uint32;
  //                type string {
  //                  pattern "<.*>|$.*";
  //                }
  //              }
  //            }
  //          }
  //        }
  //      }
  //      leaf community {
  //        description "Community associated with this site";
  //        type string;
  //      }
  //      container multi-homing {
  //        presence "enable multi-homing";
  //        description "Enable multi-homing functionality for this site";
  //        // uses apply-advanced;
  //        leaf hold-time {
  //          description "Enable multi-homing non-designated forwarder hold time (seconds)";
  //          units "seconds";
  //          type union {
  //            type string {
  //              pattern "<.*>|$.*";
  //            }
  //            type uint32 {
  //              range "1 .. 18000";
  //            }
  //          }
  //        }
  //      }
  //      leaf site-preference {
  //        description "Layer 2 VPN or VPLS site preference";
  //        type string;
  //      }
  //      leaf hot-standby {
  //        description "Keep backup pseudowire in continuous standby mode and ready for traffic forwarding";
  //        type empty;
  //      }
  //      leaf mtu {
  //        description "MTU to be advertised to the remote end";
  //        type union {
  //          type string {
  //            pattern "<.*>|$.*";
  //          }
  //          type uint16 {
  //            range "512 .. 65535";
  //          }
  //        }
  //      }
  //      leaf ignore-mtu-mismatch {
  //        description "Allow different MTU values on local and remote end";
  //        type empty;
  //      }
  //      container active-interface {
  //        description "Configure interface to designate as active";
  //        choice interface_name {
  //          case case_1 {
  //            leaf any {
  //              description "One configured interface is designated active at random";
  //              type empty;
  //            }
  //          }
  //          case case_2 {
  //            leaf primary {
  //              description "Interface to designate as active if it is operational";
  //              type union {
  //                type jt:interface-name;
  //                type string {
  //                  pattern "<.*>|$.*";
  //                }
  //              }
  //            }
  //          }
  //        }
  //      }
  //      leaf best-site {
  //        description "Activates best-site functionality for this instance";
  //        type empty;
  //      }
  //    }
  //    list neighbor {
  //      key name;
  //      ordered-by user;
  //      description "Neighbor for this VPLS instance";
  //      leaf name {
  //        description "Neighbor ID";
  //        type jt:ipv4addr;
  //      }
  //      // uses apply-advanced;
  //      leaf mac-pinning {
  //        description "Enable MAC pinning";
  //        type empty;
  //      }
  //      container static {
  //        presence "enable static";
  //        description "Configuration of static vpls";
  //        // uses apply-advanced;
  //        leaf incoming-label {
  //          description "VPLS incoming static label [1000000 - 1048575] or [29696 - 41983]";
  //          type union {
  //            type uint32;
  //            type string {
  //              pattern "<.*>|$.*";
  //            }
  //          }
  //        }
  //        leaf outgoing-label {
  //          description "VPLS outgoing static label";
  //          type union {
  //            type string {
  //              pattern "<.*>|$.*";
  //            }
  //            type uint32 {
  //              range "16 .. 1048575";
  //            }
  //          }
  //        }
  //        choice cword {
  //          case case_1 {
  //            leaf control-word {
  //              description "Adds control-word to the Layer 2 encapsulation";
  //              type empty;
  //            }
  //          }
  //          case case_2 {
  //            leaf no-control-word {
  //              description "Disables control-word to the Layer 2 encapsulation";
  //              type empty;
  //            }
  //          }
  //        }
  //      }
  //      container associate-profile {
  //        description "Associate profile options for dynamic IFL";
  //        // uses apply-advanced;
  //        leaf profile-name {
  //          description "Associated profile name";
  //          type string {
  //            length "1 .. 81";
  //          }
  //        }
  //        leaf profile-variable-set {
  //          description "Associate dynamic variable set with the profile";
  //          type string {
  //            length "1 .. 81";
  //          }
  //        }
  //      }
  //      leaf psn-tunnel-endpoint {
  //        description "Endpoint of the transport tunnel on the remote PE";
  //        type jt:ipv4addr;
  //      }
  //      leaf community {
  //        description "Community associated with this neighbor";
  //        type string;
  //      }
  //      leaf encapsulation-type {
  //        description "Encapsulation type for VPN";
  //        type enumeration {
  //          enum "ethernet-vlan" {
  //            description "Ethernet VLAN encapsulation";
  //          }
  //          enum "ethernet" {
  //            description "Ethernet encapsulation";
  //          }
  //        }
  //      }
  //      leaf ignore-encapsulation-mismatch {
  //        description "Allow different encapsulation types on local and remote end";
  //        type empty;
  //      }
  //      container pseudowire-status-tlv {
  //        presence "enable pseudowire-status-tlv";
  //        description "Send pseudowire status TLV";
  //        // uses apply-advanced;
  //        leaf hot-standby-vc-on {
  //          description "Activate pseudowire upon arrival of 'hot-standby' status TLV message";
  //          type empty;
  //        }
  //      }
  //      leaf switchover-delay {
  //        description "Pseudowire switchover delay ";
  //        default "10000";
  //        units "milliseconds";
  //        type union {
  //          type string {
  //            pattern "<.*>|$.*";
  //          }
  //          type uint32 {
  //            range "0 .. 180000";
  //          }
  //        }
  //      }
  //      container revert-time {
  //        presence "enable revert-time";
  //        description "Enable pseudowire redundancy reversion (seconds)";
  //        leaf delay {
  //          description "Reversion timer (seconds)";
  //          units "seconds";
  //          type union {
  //            type string {
  //              pattern "<.*>|$.*";
  //            }
  //            type uint32 {
  //              range "0 .. 3600";
  //            }
  //          }
  //        }
  //        leaf maximum {
  //          description "Maximum reversion interval to add over revert-time delay";
  //          units "seconds";
  //          type union {
  //            type string {
  //              pattern "<.*>|$.*";
  //            }
  //            type uint32 {
  //              range "0 .. 7200";
  //            }
  //          }
  //        }
  //      }
  //      leaf connection-protection {
  //        description "End-2-end protection via OAM failure detection";
  //        type empty;
  //      }
  //      list backup-neighbor {
  //        key name;
  //        ordered-by user;
  //        description "Configuration of redundant l2circuit";
  //        leaf name {
  //          description "Neighbor ID";
  //          type jt:ipv4addr;
  //        }
  //        // uses apply-advanced;
  //        container static {
  //          presence "enable static";
  //          description "Configuration of static vpls";
  //          // uses apply-advanced;
  //          leaf incoming-label {
  //            description "VPLS incoming static label [1000000 - 1048575] or [29696 - 41983]";
  //            type union {
  //              type uint32;
  //              type string {
  //                pattern "<.*>|$.*";
  //              }
  //            }
  //          }
  //          leaf outgoing-label {
  //            description "VPLS outgoing static label";
  //            type union {
  //              type string {
  //                pattern "<.*>|$.*";
  //              }
  //              type uint32 {
  //                range "16 .. 1048575";
  //              }
  //            }
  //          }
  //        }
  //        leaf community {
  //          description "Community associated with this Layer 2 circuit";
  //          type string;
  //        }
  //        leaf psn-tunnel-endpoint {
  //          description "Endpoint of the transport tunnel on the remote PE";
  //          type jt:ipv4addr;
  //        }
  //        leaf standby {
  //          description "Keep backup pseudowire in continuous standby";
  //          type empty;
  //        }
  //        leaf hot-standby {
  //          description "Keep backup pseudowire in continuous standby mode and ready for traffic forwarding";
  //          type empty;
  //        }
  //      }
  //      container oam {
  //        description "OAM Configuration for VPN";
  //        // uses apply-advanced;
  //        leaf ping-interval {
  //          description "Time interval between ping messages";
  //          default "60";
  //          units "seconds";
  //          type union {
  //            type string {
  //              pattern "<.*>|$.*";
  //            }
  //            type uint16 {
  //              range "30 .. 3600";
  //            }
  //          }
  //        }
  //        leaf ping-multiplier {
  //          description "Number of ping reply missed before declaring BFD down";
  //          type union {
  //            type string {
  //              pattern "<.*>|$.*";
  //            }
  //            type uint8 {
  //              range "1 .. 5";
  //            }
  //          }
  //        }
  //        container bfd-liveness-detection {
  //          description "Bidirectional Forwarding Detection (BFD) options";
  //          // uses apply-advanced;
  //          leaf version {
  //            description "BFD protocol version number";
  //            default "automatic";
  //            type enumeration {
  //              enum "0" {
  //                description "BFD version 0 (deprecated)";
  //              }
  //              enum "1" {
  //                description "BFD version 1";
  //              }
  //              enum "automatic" {
  //                description "Choose BFD version automatically";
  //              }
  //            }
  //          }
  //          leaf minimum-interval {
  //            description "Minimum transmit and receive interval";
  //            units "milliseconds";
  //            type union {
  //              type string {
  //                pattern "<.*>|$.*";
  //              }
  //              type uint32 {
  //                range "1 .. 255000";
  //              }
  //            }
  //          }
  //          leaf minimum-transmit-interval {
  //            description "Minimum transmit interval";
  //            status deprecated;
  //            units "milliseconds";
  //            type union {
  //              type string {
  //                pattern "<.*>|$.*";
  //              }
  //              type uint32 {
  //                range "1 .. 255000";
  //              }
  //            }
  //          }
  //          leaf minimum-receive-interval {
  //            description "Minimum receive interval";
  //            units "milliseconds";
  //            type union {
  //              type string {
  //                pattern "<.*>|$.*";
  //              }
  //              type uint32 {
  //                range "1 .. 255000";
  //              }
  //            }
  //          }
  //          leaf multiplier {
  //            description "Detection time multiplier";
  //            default "3";
  //            type union {
  //              type string {
  //                pattern "<.*>|$.*";
  //              }
  //              type uint32 {
  //                range "1 .. 255";
  //              }
  //            }
  //          }
  //          leaf inline-disable {
  //            description "Disable inline mode for this BFD session";
  //            type empty;
  //          }
  //          leaf pdu-size {
  //            description "BFD transport protocol payload size";
  //            default "24";
  //            type union {
  //              type string {
  //                pattern "<.*>|$.*";
  //              }
  //              type uint32 {
  //                range "24 .. 9000";
  //              }
  //            }
  //          }
  //          choice adaptation-choice {
  //            case case_1 {
  //              leaf no-adaptation {
  //                description "Disable adaptation";
  //                type empty;
  //              }
  //            }
  //          }
  //          container transmit-interval {
  //            description "Transmit-interval options";
  //            // uses apply-advanced;
  //            leaf minimum-interval {
  //              description "Minimum transmit interval";
  //              units "milliseconds";
  //              type union {
  //                type string {
  //                  pattern "<.*>|$.*";
  //                }
  //                type uint32 {
  //                  range "1 .. 255000";
  //                }
  //              }
  //            }
  //            leaf threshold {
  //              description "High transmit interval triggering a trap";
  //              units "milliseconds";
  //              type union {
  //                type uint32;
  //                type string {
  //                  pattern "<.*>|$.*";
  //                }
  //              }
  //            }
  //          }
  //          container detection-time {
  //            description "Detection-time options";
  //            // uses apply-advanced;
  //            leaf threshold {
  //              description "High detection-time triggering a trap";
  //              units "milliseconds";
  //              type union {
  //                type uint32;
  //                type string {
  //                  pattern "<.*>|$.*";
  //                }
  //              }
  //            }
  //          }
  //        }
  //      }
  //    }
  //    list mesh-group {
  //      key name;
  //      description "Mesh-group under this VPLS instance";
  //      leaf name {
  //        description "Mesh-group name";
  //        type string {
  //        }
  //      }
  //      // uses apply-advanced;
  //      leaf local-switching {
  //        description "Allow local-switching within interfaces in this mesh-group";
  //        type empty;
  //      }
  //      list neighbor {
  //        key name;
  //        ordered-by user;
  //        description "Neighbor belonging to this mesh-group";
  //        leaf name {
  //          description "Neighbor ID";
  //          type jt:ipv4addr;
  //        }
  //        // uses apply-advanced;
  //        leaf mac-pinning {
  //          description "Enable MAC pinning";
  //          type empty;
  //        }
  //        container static {
  //          presence "enable static";
  //          description "Configuration of static vpls";
  //          // uses apply-advanced;
  //          leaf incoming-label {
  //            description "VPLS incoming static label [1000000 - 1048575] or [29696 - 41983]";
  //            type union {
  //              type uint32;
  //              type string {
  //                pattern "<.*>|$.*";
  //              }
  //            }
  //          }
  //          leaf outgoing-label {
  //            description "VPLS outgoing static label";
  //            type union {
  //              type string {
  //                pattern "<.*>|$.*";
  //              }
  //              type uint32 {
  //                range "16 .. 1048575";
  //              }
  //            }
  //          }
  //          choice cword {
  //            case case_1 {
  //              leaf control-word {
  //                description "Adds control-word to the Layer 2 encapsulation";
  //                type empty;
  //              }
  //            }
  //            case case_2 {
  //              leaf no-control-word {
  //                description "Disables control-word to the Layer 2 encapsulation";
  //                type empty;
  //              }
  //            }
  //          }
  //        }
  //        container associate-profile {
  //          description "Associate profile options for dynamic IFL";
  //          // uses apply-advanced;
  //          leaf profile-name {
  //            description "Associated profile name";
  //            type string {
  //              length "1 .. 81";
  //            }
  //          }
  //          leaf profile-variable-set {
  //            description "Associate dynamic variable set with the profile";
  //            type string {
  //              length "1 .. 81";
  //            }
  //          }
  //        }
  //        leaf psn-tunnel-endpoint {
  //          description "Endpoint of the transport tunnel on the remote PE";
  //          type jt:ipv4addr;
  //        }
  //        leaf community {
  //          description "Community associated with this neighbor";
  //          type string;
  //        }
  //        leaf encapsulation-type {
  //          description "Encapsulation type for VPN";
  //          type enumeration {
  //            enum "ethernet-vlan" {
  //              description "Ethernet VLAN encapsulation";
  //            }
  //            enum "ethernet" {
  //              description "Ethernet encapsulation";
  //            }
  //          }
  //        }
  //        leaf ignore-encapsulation-mismatch {
  //          description "Allow different encapsulation types on local and remote end";
  //          type empty;
  //        }
  //        container pseudowire-status-tlv {
  //          presence "enable pseudowire-status-tlv";
  //          description "Send pseudowire status TLV";
  //          // uses apply-advanced;
  //          leaf hot-standby-vc-on {
  //            description "Activate pseudowire upon arrival of 'hot-standby' status TLV message";
  //            type empty;
  //          }
  //        }
  //        leaf switchover-delay {
  //          description "Pseudowire switchover delay ";
  //          default "10000";
  //          units "milliseconds";
  //          type union {
  //            type string {
  //              pattern "<.*>|$.*";
  //            }
  //            type uint32 {
  //              range "0 .. 180000";
  //            }
  //          }
  //        }
  //        container revert-time {
  //          presence "enable revert-time";
  //          description "Enable pseudowire redundancy reversion (seconds)";
  //          leaf delay {
  //            description "Reversion timer (seconds)";
  //            units "seconds";
  //            type union {
  //              type string {
  //                pattern "<.*>|$.*";
  //              }
  //              type uint32 {
  //                range "0 .. 3600";
  //              }
  //            }
  //          }
  //          leaf maximum {
  //            description "Maximum reversion interval to add over revert-time delay";
  //            units "seconds";
  //            type union {
  //              type string {
  //                pattern "<.*>|$.*";
  //              }
  //              type uint32 {
  //                range "0 .. 7200";
  //              }
  //            }
  //          }
  //        }
  //        leaf connection-protection {
  //          description "End-2-end protection via OAM failure detection";
  //          type empty;
  //        }
  //        list backup-neighbor {
  //          key name;
  //          ordered-by user;
  //          description "Configuration of redundant l2circuit";
  //          leaf name {
  //            description "Neighbor ID";
  //            type jt:ipv4addr;
  //          }
  //          // uses apply-advanced;
  //          container static {
  //            presence "enable static";
  //            description "Configuration of static vpls";
  //            // uses apply-advanced;
  //            leaf incoming-label {
  //              description "VPLS incoming static label [1000000 - 1048575] or [29696 - 41983]";
  //              type union {
  //                type uint32;
  //                type string {
  //                  pattern "<.*>|$.*";
  //                }
  //              }
  //            }
  //            leaf outgoing-label {
  //              description "VPLS outgoing static label";
  //              type union {
  //                type string {
  //                  pattern "<.*>|$.*";
  //                }
  //                type uint32 {
  //                  range "16 .. 1048575";
  //                }
  //              }
  //            }
  //          }
  //          leaf community {
  //            description "Community associated with this Layer 2 circuit";
  //            type string;
  //          }
  //          leaf psn-tunnel-endpoint {
  //            description "Endpoint of the transport tunnel on the remote PE";
  //            type jt:ipv4addr;
  //          }
  //          leaf standby {
  //            description "Keep backup pseudowire in continuous standby";
  //            type empty;
  //          }
  //          leaf hot-standby {
  //            description "Keep backup pseudowire in continuous standby mode and ready for traffic forwarding";
  //            type empty;
  //          }
  //        }
  //        container oam {
  //          description "OAM Configuration for VPN";
  //          // uses apply-advanced;
  //          leaf ping-interval {
  //            description "Time interval between ping messages";
  //            default "60";
  //            units "seconds";
  //            type union {
  //              type string {
  //                pattern "<.*>|$.*";
  //              }
  //              type uint16 {
  //                range "30 .. 3600";
  //              }
  //            }
  //          }
  //          leaf ping-multiplier {
  //            description "Number of ping reply missed before declaring BFD down";
  //            type union {
  //              type string {
  //                pattern "<.*>|$.*";
  //              }
  //              type uint8 {
  //                range "1 .. 5";
  //              }
  //            }
  //          }
  //          container bfd-liveness-detection {
  //            description "Bidirectional Forwarding Detection (BFD) options";
  //            // uses apply-advanced;
  //            leaf version {
  //              description "BFD protocol version number";
  //              default "automatic";
  //              type enumeration {
  //                enum "0" {
  //                  description "BFD version 0 (deprecated)";
  //                }
  //                enum "1" {
  //                  description "BFD version 1";
  //                }
  //                enum "automatic" {
  //                  description "Choose BFD version automatically";
  //                }
  //              }
  //            }
  //            leaf minimum-interval {
  //              description "Minimum transmit and receive interval";
  //              units "milliseconds";
  //              type union {
  //                type string {
  //                  pattern "<.*>|$.*";
  //                }
  //                type uint32 {
  //                  range "1 .. 255000";
  //                }
  //              }
  //            }
  //            leaf minimum-transmit-interval {
  //              description "Minimum transmit interval";
  //              status deprecated;
  //              units "milliseconds";
  //              type union {
  //                type string {
  //                  pattern "<.*>|$.*";
  //                }
  //                type uint32 {
  //                  range "1 .. 255000";
  //                }
  //              }
  //            }
  //            leaf minimum-receive-interval {
  //              description "Minimum receive interval";
  //              units "milliseconds";
  //              type union {
  //                type string {
  //                  pattern "<.*>|$.*";
  //                }
  //                type uint32 {
  //                  range "1 .. 255000";
  //                }
  //              }
  //            }
  //            leaf multiplier {
  //              description "Detection time multiplier";
  //              default "3";
  //              type union {
  //                type string {
  //                  pattern "<.*>|$.*";
  //                }
  //                type uint32 {
  //                  range "1 .. 255";
  //                }
  //              }
  //            }
  //            leaf inline-disable {
  //              description "Disable inline mode for this BFD session";
  //              type empty;
  //            }
  //            leaf pdu-size {
  //              description "BFD transport protocol payload size";
  //              default "24";
  //              type union {
  //                type string {
  //                  pattern "<.*>|$.*";
  //                }
  //                type uint32 {
  //                  range "24 .. 9000";
  //                }
  //              }
  //            }
  //            choice adaptation-choice {
  //              case case_1 {
  //                leaf no-adaptation {
  //                  description "Disable adaptation";
  //                  type empty;
  //                }
  //              }
  //            }
  //            container transmit-interval {
  //              description "Transmit-interval options";
  //              // uses apply-advanced;
  //              leaf minimum-interval {
  //                description "Minimum transmit interval";
  //                units "milliseconds";
  //                type union {
  //                  type string {
  //                    pattern "<.*>|$.*";
  //                  }
  //                  type uint32 {
  //                    range "1 .. 255000";
  //                  }
  //                }
  //              }
  //              leaf threshold {
  //                description "High transmit interval triggering a trap";
  //                units "milliseconds";
  //                type union {
  //                  type uint32;
  //                  type string {
  //                    pattern "<.*>|$.*";
  //                  }
  //                }
  //              }
  //            }
  //            container detection-time {
  //              description "Detection-time options";
  //              // uses apply-advanced;
  //              leaf threshold {
  //                description "High detection-time triggering a trap";
  //                units "milliseconds";
  //                type union {
  //                  type uint32;
  //                  type string {
  //                    pattern "<.*>|$.*";
  //                  }
  //                }
  //              }
  //            }
  //          }
  //        }
  //        leaf-list vpls-id-list {
  //          ordered-by user;
  //          description "LDP VPLS Identifier list for this neighbor";
  //          type union {
  //            type string {
  //              pattern "<.*>|$.*";
  //            }
  //            type uint32 {
  //              range "1 .. 4294967295";
  //            }
  //          }
  //        }
  //      }
  //      list interface {
  //        key name;
  //        description "Interfaces belonging to this flood group";
  //        leaf name {
  //          description "Interface name";
  //          type union {
  //            type jt:interface-name;
  //            type string {
  //              pattern "<.*>|$.*";
  //            }
  //          }
  //        }
  //        // uses apply-advanced;
  //      }
  //      container associate-profile {
  //        description "Associate profile options for dynamic IFL";
  //        // uses apply-advanced;
  //        leaf profile-name {
  //          description "Associated profile name";
  //          type string {
  //            length "1 .. 81";
  //          }
  //        }
  //        leaf profile-variable-set {
  //          description "Associate dynamic variable set with the profile";
  //          type string {
  //            length "1 .. 81";
  //          }
  //        }
  //      }
  //      choice peer-as-choice {
  //        case case_1 {
  //          container peer-as {
  //            description "Autonomous system of the peer";
  //            // uses apply-advanced;
  //            leaf all {
  //              description "Include peers from all autonomous systems";
  //              type empty;
  //            }
  //          }
  //        }
  //      }
  //      leaf vpls-id {
  //        description "LDP VPLS Identifier for this mesh-group";
  //        type string;
  //      }
  //      leaf-list vrf-import {
  //        ordered-by user;
  //        description "Import policy for VPLS instance mesh-group";
  //        type jt:policy-algebra;
  //      }
  //      leaf-list vrf-export {
  //        ordered-by user;
  //        description "Export policy for VPLS instance mesh-group";
  //        type jt:policy-algebra;
  //      }
  //      container vrf-target {
  //        description "VPLS mesh-group target community configuration";
  //        // uses apply-advanced;
  //        leaf community {
  //          description "Target community to use in import and export";
  //          type string {
  //          }
  //        }
  //        leaf import {
  //          description "Target community to use when filtering on import";
  //          type string {
  //          }
  //        }
  //        leaf export {
  //          description "Target community to use when marking routes on export";
  //          type string {
  //          }
  //        }
  //      }
  //      container mac-flush {
  //        presence "enable mac-flush";
  //        description "Enables mac-flush processing";
  //        // uses apply-advanced;
  //        leaf any-interface {
  //          description "Send mac-flush when any AC interface goes down";
  //          type empty;
  //        }
  //        leaf any-spoke {
  //          description "Send mac-flush when any spoke pseudo wire goes down";
  //          type empty;
  //        }
  //        leaf propagate {
  //          description "Propagate mac-flush to the core";
  //          type empty;
  //        }
  //      }
  //      container route-distinguisher {
  //        description "Route distinguisher for this mesh-group";
  //        leaf rd-type {
  //          description "Number in (16 bit:32 bit) or (32 bit 'L':16 bit) or (IP address:16 bit) format";
  //          type string {
  //          }
  //        }
  //      }
  //    }
  //    container proxy-mac {
  //      description "Proxy MAC settings";
  //      // uses apply-advanced;
  //      leaf irb {
  //        description "Reply with virtual-gateway MAC or IRB MAC";
  //        type empty;
  //      }
  //      leaf proxy-mac-address {
  //        description "Reply with configured MAC for all requests";
  //        type jt:mac-unicast;
  //      }
  //    }
  //    container mclag {
  //      description "EVPN with MC-LAG support";
  //      // uses apply-advanced;
  //      leaf bgp-peer {
  //        description "Configure IP address of BGP neighbor, which is also MC-LAG peer";
  //        type jt:ipaddr;
  //      }
  //      leaf source-vtep-peer {
  //        description "Confiugure IP address of MC-LAG peer's source vtep IP address";
  //        type jt:ipaddr;
  //      }
  //    }
  //    leaf service-type {
  //      description "Specify service type for vpls";
  //      type enumeration {
  //        enum "single" {
  //          description "Only one service for the virtual-switch";
  //        }
  //      }
  //    }
  //    leaf designated-forwarder-election-hold-time {
  //      description "Time to wait before electing a DF(seconds)";
  //      units "seconds";
  //      type union {
  //        type string {
  //          pattern "<.*>|$.*";
  //        }
  //        type uint32 {
  //          range "1 .. 1800";
  //        }
  //      }
  //    }
  //    leaf designated-forwarder-preference-least {
  //      description "Use least preference in DF election";
  //      type empty;
  //    }
  //    leaf encapsulation {
  //      description "Encapsulation type for EVPN";
  //      default "mpls";
  //      type enumeration {
  //        enum "mpls" {
  //          description "MPLS encapsulation";
  //        }
  //        enum "vxlan" {
  //          description "VXLAN encapsulation";
  //        }
  //        enum "mpls-inet6" {
  //          description "MPLS over IPv6 encapsulation";
  //        }
  //        enum "srv6" {
  //          description "SRv6 encapsulation";
  //        }
  //      }
  //    }
  //    leaf default-gateway {
  //      description "Default gateway mode";
  //      type enumeration {
  //        enum "advertise" {
  //          description "Advertise IRB MACs with default gateway community";
  //        }
  //        enum "no-gateway-community" {
  //          description "Advertise IRB MACs without default gateway community";
  //        }
  //        enum "do-not-advertise" {
  //          description "Do not advertise IRB MACs";
  //        }
  //      }
  //    }
  //    container duplicate-mac-detection {
  //      description "Duplicate MAC detection settings";
  //      // uses apply-advanced;
  //      leaf detection-threshold {
  //        description "Number of moves to trigger duplicate MAC detection";
  //        type union {
  //          type string {
  //            pattern "<.*>|$.*";
  //          }
  //          type uint32 {
  //            range "2 .. 20";
  //          }
  //        }
  //      }
  //      leaf detection-window {
  //        description "Time window for detection of duplicate MACs";
  //        units "seconds";
  //        type union {
  //          type string {
  //            pattern "<.*>|$.*";
  //          }
  //          type uint32 {
  //            range "5 .. 600";
  //          }
  //        }
  //      }
  //      leaf auto-recovery-time {
  //        description "Automatically unblock duplicate MACs after a time delay";
  //        units "minutes";
  //        type union {
  //          type string {
  //            pattern "<.*>|$.*";
  //          }
  //          type uint32 {
  //            range "1 .. 360";
  //          }
  //        }
  //      }
  //      leaf include-local-moves {
  //        description "Include local moves in duplicate MAC detection";
  //        type empty;
  //      }
  //      leaf action {
  //        description "Loop protection action";
  //        type enumeration {
  //          enum "block" {
  //            description "Drop packet with duplicate MAC as source or destination";
  //          }
  //          enum "shutdown" {
  //            description "Shutdown the port to prevent loop";
  //          }
  //          enum "no-mac-suppression" {
  //            description "Disable MAC suppression for duplicate MACs";
  //          }
  //        }
  //      }
  //    }
  //    container irb-symmetric-routing {
  //      description "Enable EVPN T-2 symmetric routing";
  //      // uses apply-advanced;
  //      leaf vni {
  //        description "VXLAN network identifier used for T-2 symmetric routing IP prefixes";
  //        type union {
  //          type string {
  //            pattern "<.*>|$.*";
  //          }
  //          type uint32 {
  //            range "1 .. 16777214";
  //          }
  //        }
  //      }
  //    }
  //    container source-packet-routing {
  //      presence "enable source-packet-routing";
  //      // uses apply-advanced;
  //      container srv6 {
  //        description "Enable IPv6 segment routing (SRv6)";
  //        container locator {
  //          description "SRv6 locator";
  //          leaf loc-name {
  //            description "Locator name";
  //            type string;
  //          }
  //          choice mode {
  //            case case_1 {
  //              leaf end-dt2-sid {
  //                description "Segment Routing Header-based End.DT2 SIDs";
  //                type empty;
  //              }
  //            }
  //            case case_2 {
  //              leaf micro-dt2-sid {
  //                description "Micro-SID based End.DT2 SIDs";
  //                type empty;
  //              }
  //            }
  //          }
  //        }
  //      }
  //    }
  //    choice extended-attributes {
  //      case case_1 {
  //        leaf-list extended-vlan-list {
  //          description "List of VLAN identifiers that are to be EVPN extended";
  //          type jt:vlan-range;
  //        }
  //      }
  //      case case_2 {
  //        leaf-list extended-vni-list {
  //          description "List of VNI identifiers (1..16777214) or all, that are to be EVPN extended";
  //          type string;
  //        }
  //      }
  //      case case_3 {
  //        leaf-list extended-isid-list {
  //          description "Configure list of isids or all for extending to PBB EVPN";
  //          type string;
  //        }
  //      }
  //    }
  //    container evi-options {
  //      description "EVI options";
  //      uses juniper-protocols-evi-options;
  //    }
  //    leaf p2mp-bud-support {
  //      description "Enable EVPN to act as P2MP transit and egress PE (bud)";
  //      type empty;
  //    }
  //    container remote-ip-host-routes {
  //      presence "enable remote-ip-host-routes";
  //      description "Virtual machine traffic optimization(VMTO) for EVPN";
  //      // uses apply-advanced;
  //      leaf-list import {
  //        ordered-by user;
  //        description "Policy to control the creation of remote IP host routes";
  //        type jt:policy-algebra;
  //      }
  //      leaf no-advertise-community {
  //        description "Don't advertise Type 2 route's community";
  //        type empty;
  //      }
  //    }
  //    leaf pbb-evpn-core {
  //      description "Configure PBB EVPN core";
  //      type empty;
  //    }
  //    leaf label-allocation {
  //      description "Label allocation policy";
  //      type enumeration {
  //        enum "per-instance" {
  //          description "Allocate one label for the entire instance";
  //        }
  //      }
  //    }
  //    leaf evpn-etree {
  //      description "Evpn etree mode";
  //      type empty;
  //    }
  //    container assisted-replication {
  //      description "Option to enable Assisted Replication";
  //      // uses apply-advanced;
  //      choice AR {
  //        case case_1 {
  //          container leaf {
  //            presence "enable leaf";
  //            description "Assisted Replicator Leaf";
  //            // uses apply-advanced;
  //            leaf replicator-activation-delay {
  //              description "Dealy interval in starting replication";
  //              default "10";
  //              units "seconds";
  //              type union {
  //                type string {
  //                  pattern "<.*>|$.*";
  //                }
  //                type uint32 {
  //                  range "0 .. 180";
  //                }
  //              }
  //            }
  //            leaf-list deterministic-ar-policy {
  //              ordered-by user;
  //              description "Deterministic mapping of multicast flow to replicator";
  //              type jt:policy-algebra;
  //            }
  //          }
  //        }
  //        case case_2 {
  //          container replicator {
  //            presence "enable replicator";
  //            description "Assisted Replicator";
  //            // uses apply-advanced;
  //            choice family {
  //              case case_1 {
  //                container inet {
  //                  presence "enable inet";
  //                  description "IPv4 source";
  //                  // uses apply-advanced;
  //                  leaf ip {
  //                    description "Assisted Replicator IP address";
  //                    type jt:ipv4addr;
  //                  }
  //                }
  //              }
  //            }
  //            leaf vxlan-encapsulation-source-ip {
  //              description "VXLAN encapsulation source IP for replicated traffic";
  //              type enumeration {
  //                enum "ingress-replication-ip" {
  //                  description "Use regular ingress replication IP address";
  //                }
  //              }
  //            }
  //          }
  //        }
  //      }
  //    }
  //    container vrf-target {
  //      description "VRF target community configuration";
  //      // uses apply-advanced;
  //      leaf community {
  //        description "Target community to use in import and export";
  //        type string {
  //        }
  //      }
  //    }
  //    container interconnect {
  //      description "Interconnect";
  //      uses juniper-protocols-evpn-interconnect;
  //    }
  //    leaf pmsi-tunnel-endpoint {
  //      description "IM IR PMSI tunnel Endpoint for remote PE";
  //      type jt:ipv4addr;
  //    }
  //    leaf pmsi-tunnel-endpoint-inet6 {
  //      description "IM IR PMSI IPv6 tunnel Endpoint for remote PE";
  //      type jt:ipv6addr;
  //    }
  //    leaf normalization {
  //      description "Enable vlan id normalization for interfaces";
  //      type empty;
  //    }
  //    leaf smet-etag-carry-vid {
  //      description "SMET Type 6,7 and 8 Routes to carry vlan id in Ethernet Tag field";
  //      type empty;
  //    }
  //    container mark-local-ip-host-routes {
  //      description "Mark local ip host routes";
  //      // uses apply-advanced;
  //      leaf-list export {
  //        ordered-by user;
  //        description "Policy to mark local IP host routes";
  //        type jt:policy-algebra;
  //      }
  //    }
  //    container ip-prefix-routes {
  //      presence "enable ip-prefix-routes";
  //      description "Advertise IP prefixes through EVPN";
  //      // uses apply-advanced;
  //      leaf advertise {
  //        description "Advertisement attributes for IP prefixes";
  //        type enumeration {
  //          enum "gateway-address" {
  //            description "Advertise a gateway address in exported IP prefix routes";
  //          }
  //          enum "direct-nexthop" {
  //            description "Advertise a direct nexthop in exported IP prefix routes";
  //          }
  //        }
  //      }
  //      leaf gateway-interface {
  //        description "Gateway interface used when gateway address is advertised";
  //        type union {
  //          type jt:interface-unit;
  //          type string {
  //            pattern "<.*>|$.*";
  //          }
  //        }
  //      }
  //      leaf encapsulation {
  //        description "Encapsulation used for IP prefixes";
  //        type enumeration {
  //          enum "mpls" {
  //            description "MPLS encapsulation";
  //          }
  //          enum "vxlan" {
  //            description "VXLAN encapsulation";
  //          }
  //          enum "srv6" {
  //            description "SRV6 encapsulation";
  //          }
  //        }
  //      }
  //      leaf reject-asymmetric-vni {
  //        description "Disable Type-5 asymmetric-vni";
  //        type empty;
  //      }
  //      leaf vni {
  //        description "VXLAN network identifier used for IP prefixes";
  //        type union {
  //          type string {
  //            pattern "<.*>|$.*";
  //          }
  //          type uint32 {
  //            range "1 .. 16777214";
  //          }
  //        }
  //      }
  //      leaf-list import {
  //        ordered-by user;
  //        description "Policy to control import of IP prefixes from EVPN";
  //        type jt:policy-algebra;
  //      }
  //      leaf-list export {
  //        ordered-by user;
  //        description "Policy to control export of IP prefixes through EVPN";
  //        type jt:policy-algebra;
  //      }
  //      container route-attributes {
  //        description "Route Attribute Import Export Option";
  //        // uses apply-advanced;
  //        container as-path {
  //          description "AS-PATH Attribute";
  //          // uses apply-advanced;
  //          leaf import-action {
  //            description "AS-PATH Attribute Inherit Option on Import";
  //            type enumeration {
  //              enum "allow" {
  //                description "Inherit as-path from EVPN routes to IP routes";
  //              }
  //              enum "skip" {
  //                description "Donot inehrit as-path from EVPN routes to IP routes";
  //              }
  //            }
  //          }
  //          leaf export-action {
  //            description "AS-PATH Attribute Inherit Option on Export";
  //            type enumeration {
  //              enum "allow" {
  //                description "Inherit as-path from IP routes to EVPN routes";
  //              }
  //              enum "skip" {
  //                description "Donot inherit as-path from IP routes to EVPN routes";
  //              }
  //            }
  //          }
  //        }
  //        container preference {
  //          description "Preference Attribute";
  //          // uses apply-advanced;
  //          leaf import-action {
  //            description "Preference Attribute Inerit Option on Import";
  //            type enumeration {
  //              enum "allow" {
  //                description "Inherit preference from EVPN routes to IP routes";
  //              }
  //              enum "skip" {
  //                description "Donot inherit preference from EVPN routes to EVPN routes";
  //              }
  //            }
  //          }
  //          leaf export-action {
  //            description "Preference Attribute Inherit Option on Export";
  //            type enumeration {
  //              enum "allow" {
  //                description "Inherit preference from IP routes to EVPN routes";
  //              }
  //              enum "skip" {
  //                description "Donot inherit preference from IP routes to EVPN routes";
  //              }
  //            }
  //          }
  //        }
  //        container community {
  //          description "Community Attribute";
  //          // uses apply-advanced;
  //          leaf import-action {
  //            description "Community Attribute Inherit Option on Import";
  //            type enumeration {
  //              enum "allow" {
  //                description "Inherit community from EVPN routes to IP routes";
  //              }
  //              enum "skip" {
  //                description "Donot inherit community from EVPN routes to IP routes";
  //              }
  //            }
  //          }
  //          leaf export-action {
  //            description "Community Attribute Inherit Option on Export";
  //            type enumeration {
  //              enum "allow" {
  //                description "Inherit community from IP routes to EVPN routes";
  //              }
  //              enum "skip" {
  //                description "Donot inherit community from IP route to EVPN routes";
  //              }
  //            }
  //          }
  //        }
  //      }
  //      container source-packet-routing {
  //        description "Enable source packet routing";
  //        // uses apply-advanced;
  //        container srv6 {
  //          description "Enable IPv6 segment souting (SRv6)";
  //          // uses apply-advanced;
  //          list locator {
  //            key name;
  //            ordered-by user;
  //            description "SRv6 locator";
  //            leaf name {
  //              description "Locator name";
  //              type string;
  //            }
  //            // uses apply-advanced;
  //            container end-dt4-sid {
  //              presence "enable end-dt4-sid";
  //              description "End dt4 sid";
  //            }
  //            container end-dt6-sid {
  //              presence "enable end-dt6-sid";
  //              description "End dt6 sid";
  //            }
  //            container end-dt46-sid {
  //              presence "enable end-dt46-sid";
  //              description "End dt46 sid";
  //            }
  //            container micro-dt4-sid {
  //              presence "enable micro-dt4-sid";
  //              description "Micro dt4 sid";
  //            }
  //            container micro-dt6-sid {
  //              presence "enable micro-dt6-sid";
  //              description "Micro dt6 sid";
  //            }
  //            container micro-dt46-sid {
  //              presence "enable micro-dt46-sid";
  //              description "Micro dt46 sid";
  //            }
  //          }
  //        }
  //      }
  //    }
  //    leaf igmp-id {
  //      description "EVPN IGMP Identifier value";
  //      type union {
  //        type string {
  //          pattern "<.*>|$.*";
  //        }
  //        type uint32 {
  //          range "1 .. 65535";
  //        }
  //      }
  //    }
  //    leaf multicast-mode {
  //      description "Multicast mode for EVPN";
  //      default "ingress-replication";
  //      type enumeration {
  //        enum "ingress-replication" {
  //          description "Ingress Replication";
  //        }
  //      }
  //    }
  //    container oism {
  //      description "EVPN Multicast OISM features";
  //      // uses apply-advanced;
  //      leaf supplemental-bridge-domain-irb {
  //        description "OISM SBD irb interface address";
  //        type union {
  //          type jt:interface-unit;
  //          type string {
  //            pattern "<.*>|$.*";
  //          }
  //        }
  //      }
  //      leaf originate-smet-on-revenue-vlan-too {
  //        description "Originate smet route on revenue vlan too";
  //        type empty;
  //      }
  //      container pim-evpn-gateway {
  //        presence "enable pim-evpn-gateway";
  //        description "Configure PIM EVPN Gateway PEG parameters";
  //        // uses apply-advanced;
  //        list external-irb {
  //          key name;
  //          ordered-by user;
  //          description "List of IRBs for external connectivity";
  //          leaf name {
  //            description "External vlan interface name";
  //            type union {
  //              type jt:interface-name;
  //              type string {
  //                pattern "<.*>|$.*";
  //              }
  //            }
  //          }
  //          // uses apply-advanced;
  //        }
  //        container peg-df-election {
  //          presence "enable peg-df-election";
  //          description "PEG DF Election Options";
  //          // uses apply-advanced;
  //          choice pref_choice {
  //            case case_1 {
  //              container preference {
  //                presence "enable preference";
  //                description "Preference based DF election";
  //                // uses apply-advanced;
  //                leaf value {
  //                  description "Preference value for EVPN OISM PEG DF election";
  //                  default "32767";
  //                  type union {
  //                    type string {
  //                      pattern "<.*>|$.*";
  //                    }
  //                    type uint32 {
  //                      range "0 .. 65535";
  //                    }
  //                  }
  //                }
  //                leaf use-least {
  //                  description "Use least preference in OISM PEG DF election";
  //                  type empty;
  //                }
  //              }
  //            }
  //          }
  //          choice mod_choice {
  //            case case_1 {
  //              container mod {
  //                presence "enable mod";
  //                description "MOD based DF election";
  //              }
  //            }
  //          }
  //          leaf delay-time {
  //            description "Time to wait before electing a DF(seconds)";
  //            units "seconds";
  //            type union {
  //              type string {
  //                pattern "<.*>|$.*";
  //              }
  //              type uint32 {
  //                range "1 .. 1800";
  //              }
  //            }
  //          }
  //        }
  //      }
  //    }
  //    choice flexible-cross-connect-type {
  //      case case_1 {
  //        leaf flexible-cross-connect-vlan-aware {
  //          description "Enable EVPN flexible cross-connect VLAN aware Service";
  //          type empty;
  //        }
  //      }
  //      case case_2 {
  //        leaf flexible-cross-connect-vlan-unaware {
  //          description "Enable EVPN flexible cross-connect VLAN unaware Service";
  //          type empty;
  //        }
  //      }
  //    }
  //    leaf auto-service-id {
  //      description "Enable auto-derivation of VPWS service instance identifier";
  //      type empty;
  //    }
  //    leaf hot-standby-on {
  //      description "Activate evpn vpws upon becoming DF";
  //      type empty;
  //    }
  //    list group {
  //      key name;
  //      ordered-by user;
  //      description "Enable EVPN flexible cross-connect VLAN unaware Service";
  //      leaf name {
  //        description "Group name to group vlan unaware cross connects";
  //        type string;
  //      }
  //      // uses apply-advanced;
  //      container esi {
  //        presence "enable esi";
  //        description "ESI configuration to group vlan unaware cross connects";
  //        // uses apply-advanced;
  //        leaf identifier {
  //          description "ESI value for grouping of vlan unaware cross connects";
  //          type jt:esi;
  //        }
  //      }
  //      list interface {
  //        key name;
  //        ordered-by user;
  //        description "Name of the  interface part of vlan unaware fxc";
  //        leaf name {
  //          description "Interface name";
  //          type union {
  //            type jt:interface-name;
  //            type string {
  //              pattern "<.*>|$.*";
  //            }
  //          }
  //        }
  //        // uses apply-advanced;
  //      }
  //      container service-id {
  //        presence "enable service-id";
  //        description "Service-id for vlan unaware cross connects for  EVPN VPWS";
  //        // uses apply-advanced;
  //        leaf local {
  //          description "Local service id for vlan unaware service";
  //          type union {
  //            type string {
  //              pattern "<.*>|$.*";
  //            }
  //            type uint32 {
  //              range "1 .. 16777215";
  //            }
  //          }
  //        }
  //        leaf remote {
  //          description "Remote service id for vlan unaware service";
  //          type union {
  //            type string {
  //              pattern "<.*>|$.*";
  //            }
  //            type uint32 {
  //              range "1 .. 16777215";
  //            }
  //          }
  //        }
  //      }
  //    }
  //    container vni-options {
  //      description "VNI options";
  //      // uses apply-advanced;
  //      list vni {
  //        key name;
  //        description "Per-vni options";
  //        leaf name {
  //          type union {
  //            type string {
  //              pattern "<.*>|$.*";
  //            }
  //            type int32 {
  //              range "1 .. 16777214";
  //            }
  //          }
  //        }
  //        // uses apply-advanced;
  //        container vrf-target {
  //          description "VRF target community configuration";
  //          // uses apply-advanced;
  //          leaf export {
  //            description "Target community to use when marking routes on export";
  //            status deprecated;
  //            type string {
  //            }
  //          }
  //          leaf community {
  //            description "Target community";
  //            type string {
  //            }
  //          }
  //        }
  //      }
  //    }
  //    container traceoptions {
  //      description "Trace options for Layer 2 VPNs";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "error" {
  //              description "Trace errors";
  //            }
  //            enum "topology" {
  //              description "Trace Layer 2 VPN, VPLS and EVPN topology changes";
  //            }
  //            enum "nlri" {
  //              description "Trace Layer 2 VPN, VPLS and EVPN remote site advertisements";
  //            }
  //            enum "connections" {
  //              description "Trace Layer 2 VPN and VPLS connections";
  //            }
  //            enum "automatic-site" {
  //              description "Trace VPLS automatic site state";
  //            }
  //            enum "oam" {
  //              description "Trace OAM messages";
  //            }
  //            enum "mac-database" {
  //              description "Trace MAC route database in a EVPN instance";
  //            }
  //            enum "nsr" {
  //              description "Trace NSR in a EVPN instance";
  //            }
  //            enum "egress-protection" {
  //              description "Trace Edge Protection messages";
  //            }
  //            enum "instance" {
  //              description "Evpn instance related messages";
  //            }
  //            enum "interface" {
  //              description "Interface related messages";
  //            }
  //            enum "l2aldsync" {
  //              description "Messages related to EVPN-L2ALD communication";
  //            }
  //            enum "p2mp" {
  //              description "P2MP messages";
  //            }
  //            enum "esi" {
  //              description "Evpn ethernet segment related messages";
  //            }
  //            enum "mcsn" {
  //              description "Evpn multicast snooping related messages";
  //            }
  //            enum "vpws" {
  //              description "VPWS messages";
  //            }
  //            enum "irb" {
  //              description "Integrated routing bridging messages";
  //            }
  //            enum "ar" {
  //              description "Assisted-replication messages";
  //            }
  //            enum "etree" {
  //              description "Evpn etree messages";
  //            }
  //            enum "kernel" {
  //              description "Messages related to rpd-kernel communication";
  //            }
  //            enum "bd" {
  //              description "Evpn bridge domain messages";
  //            }
  //            enum "pbb" {
  //              description "Evpn provider backbone bridging messages";
  //            }
  //            enum "infra" {
  //              description "Messages related to infrastructure in evpn";
  //            }
  //            enum "pfxdb" {
  //              description "Type-5 related messages";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    leaf encapsulation-type {
  //      description "Encapsulation type for VPN";
  //      type enumeration {
  //        enum "atm-aal5" {
  //          description "ATM AAL/5 encapsulation";
  //        }
  //        enum "atm-cell" {
  //          description "ATM port promiscuous mode cell encapsulation";
  //        }
  //        enum "atm-cell-port-mode" {
  //          description "ATM port promiscuous mode cell encapsulation";
  //        }
  //        enum "atm-cell-vp-mode" {
  //          description "ATM VP promiscuous mode cell encapsulation";
  //        }
  //        enum "atm-cell-vc-mode" {
  //          description "ATM non-promiscuous cell encapsulation";
  //        }
  //        enum "frame-relay" {
  //          description "Frame Relay encapsulation";
  //        }
  //        enum "ppp" {
  //          description "PPP encapsulation";
  //        }
  //        enum "cisco-hdlc" {
  //          description "Cisco-compatible HDLC encapsulation";
  //        }
  //        enum "ethernet-vlan" {
  //          description "Ethernet VLAN encapsulation";
  //        }
  //        enum "ethernet" {
  //          description "Ethernet encapsulation";
  //        }
  //        enum "interworking" {
  //          description "Layer 2.5 interworking VPN";
  //        }
  //        enum "frame-relay-port-mode" {
  //          description "Frame Relay port mode encapsulation";
  //        }
  //        enum "satop-t1" {
  //          description "SATOP-T1 based Layer 2 VPN";
  //        }
  //        enum "satop-e1" {
  //          description "SATOP-E1 based Layer 2 VPN";
  //        }
  //        enum "satop-t3" {
  //          description "SATOP-T3 based Layer 2 VPN";
  //        }
  //        enum "satop-e3" {
  //          description "SATOP-E3 based Layer 2 VPN";
  //        }
  //        enum "cesop" {
  //          description "CESOP based Layer 2 VPN";
  //        }
  //      }
  //    }
  //    leaf control-word {
  //      description "Add control word to the Layer 2 encapsulation";
  //      type empty;
  //    }
  //    leaf no-control-word {
  //      description "Disables control word on the Layer 2 encapsulation";
  //      type empty;
  //    }
  //    leaf site-range {
  //      description "Maximum site identifier in this VPLS domain";
  //      type union {
  //        type string {
  //          pattern "<.*>|$.*";
  //        }
  //        type uint32 {
  //          range "1 .. 65534";
  //        }
  //      }
  //    }
  //    leaf label-block-size {
  //      description "Label block size for this VPLS instance";
  //      type enumeration {
  //        enum "2" {
  //          description "Label block size of 2";
  //        }
  //        enum "4" {
  //          description "Label block size of 4";
  //        }
  //        enum "8" {
  //          description "Label block size of 8";
  //        }
  //        enum "16" {
  //          description "Label block size of 16";
  //        }
  //      }
  //    }
  //    choice tunnel-services-choice {
  //      case case_1 {
  //        container tunnel-services {
  //          description "Use tunnel services for this VPLS instance";
  //          // uses apply-advanced;
  //          leaf-list devices {
  //            ordered-by user;
  //            description "Tunnel services devices to use for this VPLS instance";
  //            type union {
  //              type jt:interface-device;
  //              type string {
  //                pattern "<.*>|$.*";
  //              }
  //            }
  //          }
  //          leaf primary {
  //            description "Primary tunnel services device to use for VPLS instance";
  //            type union {
  //              type jt:interface-device;
  //              type string {
  //                pattern "<.*>|$.*";
  //              }
  //            }
  //          }
  //        }
  //      }
  //      case case_2 {
  //        leaf no-tunnel-services {
  //          description "Do not use tunnel services for this VPLS instance";
  //          type empty;
  //        }
  //      }
  //    }
  //    leaf community {
  //      description "Community associated with this VPLS instance";
  //      type string;
  //    }
  //    leaf vpls-id {
  //      description "Identifier for this VPLS instance";
  //      type string;
  //    }
  //    leaf mtu {
  //      description "MTU to be advertised to the remote end";
  //      type union {
  //        type string {
  //          pattern "<.*>|$.*";
  //        }
  //        type uint16 {
  //          range "512 .. 65535";
  //        }
  //      }
  //    }
  //    leaf ignore-mtu-mismatch {
  //      description "Allow different MTU values on local and remote end";
  //      type empty;
  //    }
  //    container mac-flush {
  //      presence "enable mac-flush";
  //      description "Enables mac-flush processing";
  //      // uses apply-advanced;
  //      leaf any-interface {
  //        description "Send mac-flush when any AC interface goes down";
  //        type empty;
  //      }
  //      leaf any-spoke {
  //        description "Send mac-flush when any spoke pseudo wire goes down";
  //        type empty;
  //      }
  //      leaf propagate {
  //        description "Propagate mac-flush to the core";
  //        type empty;
  //      }
  //    }
  //    leaf ignore-encapsulation-mismatch {
  //      description "Allow different encapsulation types on local and remote end";
  //      type empty;
  //    }
  //    leaf pseudowire-status-tlv {
  //      description "Send pseudowire status TLV";
  //      type empty;
  //    }
  //    leaf flow-label-transmit {
  //      description "Advertise capability to push Flow Label in transmit direction to remote PE";
  //      type empty;
  //    }
  //    leaf flow-label-receive {
  //      description "Advertise capability to pop Flow Label in receive direction to remote PE";
  //      type empty;
  //    }
  //    leaf flow-label-transmit-static {
  //      description "Push Flow Label on PW packets sent to remote PE";
  //      type empty;
  //    }
  //    leaf flow-label-receive-static {
  //      description "Pop Flow Label from PW packets received from remote PE";
  //      type empty;
  //    }
  //    leaf flow-label {
  //      description "Advertise flow-label capability";
  //      type empty;
  //    }
  //    leaf flow-label-static {
  //      description "Static flow-label";
  //      type empty;
  //    }
  //    container associate-profile {
  //      description "Associate profile options for dynamic IFL";
  //      // uses apply-advanced;
  //      leaf profile-name {
  //        description "Associated profile name";
  //        type string {
  //          length "1 .. 81";
  //        }
  //      }
  //      leaf profile-variable-set {
  //        description "Associate dynamic variable set with the profile";
  //        type string {
  //          length "1 .. 81";
  //        }
  //      }
  //    }
  //    leaf connectivity-type {
  //      description "Specify type of interface sufficient to bring vpls connection up";
  //      type enumeration {
  //        enum "ce" {
  //          description "CE interface is required";
  //        }
  //        enum "irb" {
  //          description "IRB interface is sufficient";
  //        }
  //        enum "permanent" {
  //          description "Pseudowire permanently up";
  //        }
  //      }
  //    }
  //    list import-labeled-routes {
  //      key name;
  //      ordered-by user;
  //      description "Import ingress label route to instance.mpls.0 from mpls.0";
  //      leaf name {
  //        description "Routing instance name where label route has to be imported";
  //        type string;
  //      }
  //    }
  //    container oam {
  //      description "OAM Configuration for VPN";
  //      // uses apply-advanced;
  //      leaf ping-interval {
  //        description "Time interval between ping messages";
  //        default "60";
  //        units "seconds";
  //        type union {
  //          type string {
  //            pattern "<.*>|$.*";
  //          }
  //          type uint16 {
  //            range "30 .. 3600";
  //          }
  //        }
  //      }
  //      leaf ping-multiplier {
  //        description "Number of ping reply missed before declaring BFD down";
  //        type union {
  //          type string {
  //            pattern "<.*>|$.*";
  //          }
  //          type uint8 {
  //            range "1 .. 5";
  //          }
  //        }
  //      }
  //      container bfd-liveness-detection {
  //        description "Bidirectional Forwarding Detection (BFD) options";
  //        // uses apply-advanced;
  //        leaf version {
  //          description "BFD protocol version number";
  //          default "automatic";
  //          type enumeration {
  //            enum "0" {
  //              description "BFD version 0 (deprecated)";
  //            }
  //            enum "1" {
  //              description "BFD version 1";
  //            }
  //            enum "automatic" {
  //              description "Choose BFD version automatically";
  //            }
  //          }
  //        }
  //        leaf minimum-interval {
  //          description "Minimum transmit and receive interval";
  //          units "milliseconds";
  //          type union {
  //            type string {
  //              pattern "<.*>|$.*";
  //            }
  //            type uint32 {
  //              range "1 .. 255000";
  //            }
  //          }
  //        }
  //        leaf minimum-transmit-interval {
  //          description "Minimum transmit interval";
  //          status deprecated;
  //          units "milliseconds";
  //          type union {
  //            type string {
  //              pattern "<.*>|$.*";
  //            }
  //            type uint32 {
  //              range "1 .. 255000";
  //            }
  //          }
  //        }
  //        leaf minimum-receive-interval {
  //          description "Minimum receive interval";
  //          units "milliseconds";
  //          type union {
  //            type string {
  //              pattern "<.*>|$.*";
  //            }
  //            type uint32 {
  //              range "1 .. 255000";
  //            }
  //          }
  //        }
  //        leaf multiplier {
  //          description "Detection time multiplier";
  //          default "3";
  //          type union {
  //            type string {
  //              pattern "<.*>|$.*";
  //            }
  //            type uint32 {
  //              range "1 .. 255";
  //            }
  //          }
  //        }
  //        leaf inline-disable {
  //          description "Disable inline mode for this BFD session";
  //          type empty;
  //        }
  //        leaf pdu-size {
  //          description "BFD transport protocol payload size";
  //          default "24";
  //          type union {
  //            type string {
  //              pattern "<.*>|$.*";
  //            }
  //            type uint32 {
  //              range "24 .. 9000";
  //            }
  //          }
  //        }
  //        choice adaptation-choice {
  //          case case_1 {
  //            leaf no-adaptation {
  //              description "Disable adaptation";
  //              type empty;
  //            }
  //          }
  //        }
  //        container transmit-interval {
  //          description "Transmit-interval options";
  //          // uses apply-advanced;
  //          leaf minimum-interval {
  //            description "Minimum transmit interval";
  //            units "milliseconds";
  //            type union {
  //              type string {
  //                pattern "<.*>|$.*";
  //              }
  //              type uint32 {
  //                range "1 .. 255000";
  //              }
  //            }
  //          }
  //          leaf threshold {
  //            description "High transmit interval triggering a trap";
  //            units "milliseconds";
  //            type union {
  //              type uint32;
  //              type string {
  //                pattern "<.*>|$.*";
  //              }
  //            }
  //          }
  //        }
  //        container detection-time {
  //          description "Detection-time options";
  //          // uses apply-advanced;
  //          leaf threshold {
  //            description "High detection-time triggering a trap";
  //            units "milliseconds";
  //            type union {
  //              type uint32;
  //              type string {
  //                pattern "<.*>|$.*";
  //              }
  //            }
  //          }
  //        }
  //      }
  //      container control-channel {
  //        description "Supported control channel type ";
  //        // uses apply-advanced;
  //        choice action-choice {
  //          case case_1 {
  //            leaf pwe3-control-word {
  //              description "For BGP based PW send oam packets with control word, with 0001b as first nibble";
  //              type empty;
  //            }
  //          }
  //          case case_2 {
  //            leaf router-alert-label {
  //              description "For BGP based PW send oam packets with router alert label";
  //              type empty;
  //            }
  //          }
  //          case case_3 {
  //            leaf pw-label-ttl-1 {
  //              description "For BGP based PW send oam packets with MPLS pw label TTL = 1";
  //              type empty;
  //            }
  //          }
  //        }
  //      }
  //    }
  //    container multi-homing {
  //      description "Multi-homing configuration for FEC129 VPLS";
  //      // uses apply-advanced;
  //      leaf peer-active {
  //        description "Keep CE interfaces in up state when all BGP peers go down";
  //        type empty;
  //      }
  //      list site {
  //        key name;
  //        description "Sites connected to this provider equipment";
  //        leaf name {
  //          description "Name of Layer 2 VPN or VPLS site";
  //          type string;
  //        }
  //        // uses apply-advanced;
  //        leaf identifier {
  //          description "Layer 2 VPN or VPLS multi-homing identifier";
  //          type union {
  //            type string {
  //              pattern "<.*>|$.*";
  //            }
  //            type uint16 {
  //              range "1 .. 65534";
  //            }
  //          }
  //        }
  //        leaf preference {
  //          description "Layer 2 VPN or VPLS multi-homing preference";
  //          type string;
  //        }
  //        container active-interface {
  //          description "Configure interface to designate as active";
  //          // uses apply-advanced;
  //          choice interface_name {
  //            case case_1 {
  //              leaf any {
  //                description "One configured interface is designated active at random";
  //                type empty;
  //              }
  //            }
  //            case case_2 {
  //              leaf primary {
  //                description "Interface to designate as active if it is operational";
  //                type union {
  //                  type jt:interface-name;
  //                  type string {
  //                    pattern "<.*>|$.*";
  //                  }
  //                }
  //              }
  //            }
  //          }
  //        }
  //        list interface {
  //          key name;
  //          ordered-by user;
  //          description "Interface that connects this site to the VPN";
  //          leaf name {
  //            description "Interface name";
  //            type union {
  //              type jt:interface-name;
  //              type string {
  //                pattern "<.*>|$.*";
  //              }
  //            }
  //          }
  //          // uses apply-advanced;
  //          leaf preference {
  //            description "Layer 2 VPN or VPLS multi-homing preference for the interface";
  //            type union {
  //              type string {
  //                pattern "<.*>|$.*";
  //              }
  //              type uint16 {
  //                range "1 .. 65535";
  //              }
  //            }
  //          }
  //        }
  //        leaf peer-active {
  //          description "Keep CE interfaces in up state when all BGP peers go down";
  //          type empty;
  //        }
  //      }
  //    }
  //  }
  //  grouping juniper-protocols-evi-options {
  //    // uses apply-advanced;
  //    list isid {
  //      key name;
  //      description "Per-evi options";
  //      leaf name {
  //        type union {
  //          type string {
  //            pattern "<.*>|$.*";
  //          }
  //          type int32 {
  //            range "256 .. 16777214";
  //          }
  //        }
  //      }
  //      // uses apply-advanced;
  //      container vrf-target {
  //        description "VRF target community configuration";
  //        // uses apply-advanced;
  //        leaf community {
  //          description "Target community";
  //          type string {
  //          }
  //        }
  //      }
  //    }
  //  }
  //  grouping juniper-protocols-evpn-interconnect {
  //    description "Interconnect configuration for the routing instance";
  //    // uses apply-advanced;
  //    leaf-list vrf-import {
  //      ordered-by user;
  //      description "Import policy for Interconnect";
  //      type jt:policy-algebra;
  //    }
  //    leaf-list vrf-export {
  //      ordered-by user;
  //      description "Export policy for Interconnect";
  //      type jt:policy-algebra;
  //    }
  //    container vrf-target {
  //      description "Interconnect target community configuration";
  //      // uses apply-advanced;
  //      leaf community {
  //        description "Target community to use in import and export";
  //        type string {
  //        }
  //      }
  //      leaf import {
  //        description "Target community to use when filtering on import";
  //        type string {
  //        }
  //      }
  //      leaf export {
  //        description "Target community to use when marking routes on export";
  //        type string {
  //        }
  //      }
  //    }
  //    container route-distinguisher {
  //      description "Route distinguisher for this interconnect";
  //      leaf rd-type {
  //        description "Number in (16 bit:32 bit) or (32 bit 'L':16 bit) or (IP address:16 bit) format";
  //        type string {
  //        }
  //      }
  //    }
  //    list domain-path-id {
  //      key name;
  //      ordered-by user;
  //      description "DCI VRF domain path id configuration";
  //      max-elements 1;
  //      uses domain-id-type;
  //    }
  //    container esi {
  //      description "ESI configuration of interconnect";
  //      // uses apply-advanced;
  //      leaf identifier {
  //        description "ESI value for interconnect";
  //        type jt:esi;
  //      }
  //      choice mode {
  //        case case_1 {
  //          leaf all-active {
  //            description "All-active mode";
  //            type empty;
  //          }
  //        }
  //      }
  //      container df-election-type {
  //        presence "enable df-election-type";
  //        description "DF Election Type";
  //        // uses apply-advanced;
  //        choice pref_choice {
  //          case case_1 {
  //            container preference {
  //              presence "enable preference";
  //              description "Preference based DF election";
  //              // uses apply-advanced;
  //              leaf value {
  //                description "Preference value for EVPN Multihoming DF election";
  //                default "32767";
  //                type union {
  //                  type string {
  //                    pattern "<.*>|$.*";
  //                  }
  //                  type uint32 {
  //                    range "0 .. 65535";
  //                  }
  //                }
  //              }
  //            }
  //          }
  //        }
  //        choice mod_choice {
  //          case case_1 {
  //            container mod {
  //              presence "enable mod";
  //              description "MOD based DF election";
  //            }
  //          }
  //        }
  //      }
  //    }
  //    leaf-list interconnected-vni-list {
  //      description "List of translated VNIs (1..16777214) or all, that are to be EVPN interconnected";
  //      type string;
  //    }
  //    leaf-list interconnected-vlan-list {
  //      ordered-by user;
  //      description "List of VLAN identifiers that are to be EVPN interconnected";
  //      type string;
  //    }
  //    container irb-symmetric-routing {
  //      description "Enable EVPN T-2 symmetric DCI routing";
  //      // uses apply-advanced;
  //      leaf vni {
  //        description "VXLAN network identifier used for T-2 symmetric routing IP prefixes";
  //        type union {
  //          type string {
  //            pattern "<.*>|$.*";
  //          }
  //          type uint32 {
  //            range "1 .. 16777214";
  //          }
  //        }
  //      }
  //    }
  //    leaf encapsulation {
  //      type enumeration {
  //        enum "mpls" {
  //          description "MPLS encapsulation";
  //        }
  //        enum "vxlan" {
  //          description "VXLAN encapsulation";
  //        }
  //      }
  //    }
  //  }
  //  grouping domain-id-type {
  //    leaf name {
  //      description "Domain id for type 5 evpn DCI";
  //      type string {
  //      }
  //    }
  //    // uses apply-advanced;
  //  }
   grouping juniper-protocols-ldp {
     // uses apply-advanced;
    //  container traceoptions {
    //    description "Trace options for LDP";
    //    // uses apply-advanced;
    //    container file {
    //      description "Trace file options";
    //      leaf filename {
    //        description "Name of file in which to write trace information";
    //        type string {
    //          length "1 .. 1024";
    //        }
    //      }
    //      leaf replace {
    //        description "Replace trace file rather than appending to it";
    //        status deprecated;
    //        type empty;
    //      }
    //      leaf size {
    //        description "Maximum trace file size";
    //        type string;
    //      }
    //      leaf files {
    //        description "Maximum number of trace files";
    //        default "10";
    //        type union {
    //          type string {
    //            pattern "<.*>|$.*";
    //          }
    //          type uint32 {
    //            range "2 .. 1000";
    //          }
    //        }
    //      }
    //      leaf no-stamp {
    //        description "Do not timestamp trace file";
    //        status deprecated;
    //        type empty;
    //      }
    //      choice world-readable-choice {
    //        leaf world-readable {
    //          description "Allow any user to read the log file";
    //          type empty;
    //        }
    //        leaf no-world-readable {
    //          description "Don't allow any user to read the log file";
    //          type empty;
    //        }
    //      }
    //    }
    //    list flag {
    //      key name;
    //      ordered-by user;
    //      description "Tracing parameters";
    //      leaf name {
    //        type enumeration {
    //          enum "error" {
    //            description "Trace errored packets";
    //          }
    //          enum "event" {
    //            description "Trace LDP state machine events";
    //          }
    //          enum "packet-dump" {
    //            description "Dump the contents of selected packet types";
    //          }
    //          enum "packets" {
    //            description "Trace all LDP packets";
    //          }
    //          enum "periodic" {
    //            description "Trace periodic (hello and keepalive) packets";
    //          }
    //          enum "initialization" {
    //            description "Trace initialization packets";
    //          }
    //          enum "notification" {
    //            description "Trace notification packets";
    //          }
    //          enum "address" {
    //            description "Trace address packets";
    //          }
    //          enum "label" {
    //            description "Trace label packets";
    //          }
    //          enum "binding" {
    //            description "Trace label binding state";
    //          }
    //          enum "path" {
    //            description "Trace label path state";
    //          }
    //          enum "ppmd" {
    //            description "Trace state and events for ppmd process";
    //          }
    //          enum "nsr-synchronization" {
    //            description "Trace NSR synchronization events";
    //          }
    //          enum "link-protection" {
    //            description "Trace link protection events";
    //          }
    //          enum "p2mp-nsr-synchronization" {
    //            description "Trace p2mp NSR synchronization events";
    //          }
    //          enum "route" {
    //            description "Trace routing information";
    //          }
    //          enum "normal" {
    //            description "Trace normal events";
    //          }
    //          enum "general" {
    //            description "Trace general events";
    //          }
    //          enum "state" {
    //            description "Trace state transitions";
    //          }
    //          enum "policy" {
    //            description "Trace policy processing";
    //          }
    //          enum "task" {
    //            description "Trace routing protocol task processing";
    //          }
    //          enum "timer" {
    //            description "Trace routing protocol timer processing";
    //          }
    //          enum "all" {
    //            description "Trace everything";
    //          }
    //        }
    //      }
    //      leaf send {
    //        description "Trace transmitted packets";
    //        type empty;
    //      }
    //      leaf receive {
    //        description "Trace received packets";
    //        type empty;
    //      }
    //      leaf detail {
    //        description "Trace detailed information";
    //        type empty;
    //      }
    //      leaf disable {
    //        description "Disable this trace flag";
    //        type empty;
    //      }
    //      container filter {
    //        description "Filter to apply to this flag";
    //        presence "enable filter";
    //        uses ldp_filter_obj;
    //      }
    //    }
    //  }
    //  container traffic-statistics {
    //    description "Collect statistics for LDP label-switched paths";
    //    // uses apply-advanced;
    //    container file {
    //      description "Statistics file options";
    //      leaf filename {
    //        description "Name of file in which to write trace information";
    //        type string {
    //          length "1 .. 1024";
    //        }
    //      }
    //      leaf replace {
    //        description "Replace trace file rather than appending to it";
    //        status deprecated;
    //        type empty;
    //      }
    //      leaf size {
    //        description "Maximum trace file size";
    //        type string;
    //      }
    //      leaf files {
    //        description "Maximum number of trace files";
    //        default "10";
    //        type union {
    //          type string {
    //            pattern "<.*>|$.*";
    //          }
    //          type uint32 {
    //            range "2 .. 1000";
    //          }
    //        }
    //      }
    //      leaf no-stamp {
    //        description "Do not timestamp trace file";
    //        status deprecated;
    //        type empty;
    //      }
    //      choice world-readable-choice {
    //        leaf world-readable {
    //          description "Allow any user to read the log file";
    //          type empty;
    //        }
    //        leaf no-world-readable {
    //          description "Don't allow any user to read the log file";
    //          type empty;
    //        }
    //      }
    //    }
    //    leaf interval {
    //      description "Time to collect statistics (seconds)";
    //      type union {
    //        type string {
    //          pattern "<.*>|$.*";
    //        }
    //        type int32 {
    //          range "60 .. 65535";
    //        }
    //      }
    //    }
    //    leaf sensor-based-stats {
    //      description "Enable sensor based statistics collection";
    //      type empty;
    //    }
    //    leaf no-penultimate-hop {
    //      description "No penultimate hop statistics collection";
    //      type empty;
    //    }
    //  }
     container graceful-restart {
       description "Configure graceful restart attributes";
       // uses apply-advanced;
       choice enable-disable {
         case case_1 {
           leaf disable {
             description "Disable graceful restart";
             type empty;
           }
         }
       }
       leaf helper-disable {
         description "Disable the graceful restart helper capability";
         type empty;
       }
       leaf recovery-time {
         description "Time required for recovery";
         units "seconds";
         type union {
           type string {
             pattern "<.*>|$.*";
           }
           type uint32 {
             range "120 .. 1800";
           }
         }
       }
       leaf maximum-neighbor-recovery-time {
         description "Maximum time stale mappings are maintained";
         units "seconds";
         type union {
           type string {
             pattern "<.*>|$.*";
           }
           type uint32 {
             range "140 .. 1900";
           }
         }
       }
       leaf reconnect-time {
         description "Time required to reestablish session after graceful restart";
         units "seconds";
         type union {
           type string {
             pattern "<.*>|$.*";
           }
           type uint32 {
             range "30 .. 300";
           }
         }
       }
       leaf maximum-neighbor-reconnect-time {
         description "Maximum reconnect time allowed from a restarting neighbor";
         units "seconds";
         type union {
           type string {
             pattern "<.*>|$.*";
           }
           type uint32 {
             range "30 .. 300";
           }
         }
       }
     }
     container auto-targeted-session {
       presence "enable auto-targeted-session";
       description "Configure auto targeted session parameters";
       // uses apply-advanced;
       leaf teardown-delay {
         description "Auto targeted session tear down delay";
         default "90";
         units "seconds";
         type union {
           type string {
             pattern "<.*>|$.*";
           }
           type uint32 {
             range "1 .. 300";
           }
         }
       }
       leaf maximum-sessions {
         description "Auto targeted maximum sessions";
         default "100";
         type union {
           type string {
             pattern "<.*>|$.*";
           }
           type uint32 {
             range "1 .. 1000";
           }
         }
       }
       leaf no-rlfa {
         description "Do not allow RLFA in auto targeted sessions";
         type empty;
       }
       leaf no-dynamic-tunnels {
         description "Do not allow dynamic tunnels in auto targeted sessions";
         type empty;
       }
     }
     leaf preference {
       description "Route preference";
       type union {
         type uint32;
         type string {
           pattern "<.*>|$.*";
         }
       }
     }
     leaf no-forwarding {
       description "Do not use LDP ingress routes for forwarding";
       type empty;
     }
     leaf rib-group {
       description "Routing table group for importing ingress routes";
       type string;
     }
    //  leaf rib-group6 {
    //    description "Routing table group for importing ingress v6 routes";
    //    type string;
    //  }
    //  leaf l2-smart-policy {
    //    description "Do not export or import Layer 3 FECs for Layer 2 sessions";
    //    type empty;
    //  }
    //  leaf track-igp-metric {
    //    description "Track the IGP metric";
    //    type empty;
    //  }
    //  leaf strict-targeted-hellos {
    //    description "Do not send targeted hellos to unconfigured neighbors";
    //    type empty;
    //  }
    //  container longest-match {
    //    presence "enable longest-match";
    //    description "Configure longest match";
    //    // uses apply-advanced;
    //    leaf-list policy {
    //      ordered-by user;
    //      description "Longest match import policy";
    //      type jt:policy-algebra;
    //    }
    //  }
    //  leaf-list color-import-policy {
    //    ordered-by user;
    //    description "Import color policy";
    //    type jt:policy-algebra;
    //  }
     leaf-list import {
       ordered-by user;
       description "Import policy";
       type jt:policy-algebra;
     }
     leaf-list export {
       ordered-by user;
       description "Export policy";
       type jt:policy-algebra;
     }
     leaf-list egress-policy {
       ordered-by user;
       description "Configure LSP egress policy";
       type jt:policy-algebra;
     }
    //  leaf-list dod-request-policy {
    //    ordered-by user;
    //    description "Configure DoD label request policy";
    //    type jt:policy-algebra;
    //  }
     container next-hop {
       description "LDP next-hop control";
       // uses apply-advanced;
       container merged {
         description "Merged next hop";
         // uses apply-advanced;
         leaf-list policy {
           ordered-by user;
           description "Merged next-hop policy";
           type jt:policy-algebra;
         }
       }
       container no-rsvp-tunneling {
         description "No rsvp tunneling";
         // uses apply-advanced;
         leaf-list policy {
           ordered-by user;
           description "No rsvp tunneling next-hop policy";
           type jt:policy-algebra;
         }
       }
     }
     choice mtu-discovery-choice {
       leaf mtu-discovery {
         description "Enable TCP path MTU discovery";
         type empty;
       }
       leaf no-mtu-discovery {
         description "Don't enable TCP path MTU discovery";
         type empty;
       }
     }
     choice deaggregate-choice {
       leaf deaggregate {
         description "Deaggregate FECs into separate labels";
         type empty;
       }
       leaf no-deaggregate {
         description "Don't deaggregate FECs into separate labels";
         type empty;
       }
     }
     leaf explicit-null {
       description "Advertise the EXPLICIT_NULL label for egress FECs";
       type empty;
     }
    //  leaf label-withdrawal-delay {
    //    description "Delay label withdrawal for FECs to avoid label churn";
    //    default "60";
    //    units "seconds";
    //    type union {
    //      type string {
    //        pattern "<.*>|$.*";
    //      }
    //      type uint32 {
    //        range "0 .. 120";
    //      }
    //    }
    //  }
    //  container make-before-break {
    //    presence "enable make-before-break";
    //    description "Configure make before break";
    //    // uses apply-advanced;
    //    leaf timeout {
    //      description "Make before break timeout";
    //      default "30";
    //      units "seconds";
    //      type union {
    //        type string {
    //          pattern "<.*>|$.*";
    //        }
    //        type uint32 {
    //          range "1 .. 300";
    //        }
    //      }
    //    }
    //    leaf switchover-delay {
    //      description "Make before break switchover delay";
    //      default "3";
    //      units "seconds";
    //      type union {
    //        type string {
    //          pattern "<.*>|$.*";
    //        }
    //        type uint32 {
    //          range "1 .. 300";
    //        }
    //      }
    //    }
    //  }
    //  container transport-address {
    //    description "Address used for TCP sessions";
    //    choice address-choice {
    //      case case_1 {
    //        leaf router-id {
    //          description "Use router ID for TCP connections";
    //          type empty;
    //        }
    //      }
    //      case case_2 {
    //        leaf interface {
    //          description "Use interface address for TCP connections";
    //          type empty;
    //        }
    //      }
    //      case case_3 {
    //        leaf address {
    //          description "Use specified address for TCP connections";
    //          type jt:ipaddr;
    //        }
    //      }
    //    }
    //  }
     leaf keepalive-interval {
       description "Keepalive interval (seconds)";
       type union {
         type string {
           pattern "<.*>|$.*";
         }
         type uint32 {
           range "1 .. 65535";
         }
       }
     }
     leaf keepalive-timeout {
       description "Keepalive timeout (seconds)";
       type union {
         type string {
           pattern "<.*>|$.*";
         }
         type uint32 {
           range "1 .. 65535";
         }
       }
     }
     list interface {
       key name;
       description "Enable LDP on this interface";
       leaf name {
         description "Interface name";
         type union {
           type jt:interface-name;
           type string {
             pattern "<.*>|$.*";
           }
         }
       }
       // uses apply-advanced;
       choice enable-disable {
         case case_1 {
           leaf disable {
             description "Disable LDP on this interface";
             type empty;
           }
         }
       }
       leaf hello-interval {
         description "Hello interval (seconds)";
         type union {
           type string {
             pattern "<.*>|$.*";
           }
           type uint32 {
             range "1 .. 65535";
           }
         }
       }
       leaf hold-time {
         description "Hello hold time (seconds)";
         type union {
           type string {
             pattern "<.*>|$.*";
           }
           type uint32 {
             range "1 .. 65535";
           }
         }
       }
       container link-protection {
         presence "enable link-protection";
         description "Enable link protection to protect interface for link faults only";
         // uses apply-advanced;
         choice enable-disable {
           case case_1 {
             leaf disable {
               description "Disable link-protection";
               type empty;
             }
           }
         }
         leaf dynamic-rsvp-lsp {
           description "Enable setup of dynamic rsvp lsp for link protection";
           type empty;
         }
       }
       container transport-address {
         description "Address used for TCP sessions";
         choice address-choice {
           case case_1 {
             leaf router-id {
               description "Use router ID for TCP connections";
               type empty;
             }
           }
           case case_2 {
             leaf interface {
               description "Use interface address for TCP connections";
               type empty;
             }
           }
           case case_3 {
             leaf address {
               description "Use specified address for TCP connections";
               type jt:ipaddr;
             }
           }
         }
       }
       choice allow-subnet-mismatch-choice {
         leaf allow-subnet-mismatch {
           description "Allow subnet mismatch for source address in hello packet";
           type empty;
         }
         leaf no-allow-subnet-mismatch {
           description "Don't allow subnet mismatch for source address in hello packet";
           type empty;
         }
       }
     }
     list neighbor {
       key name;
       description "Configure a remote LDP neighbor";
       leaf name {
         description "Neighbor address";
         type jt:ipaddr;
       }
       // uses apply-advanced;
     }
     list session {
       key name;
       description "Configure session parameters";
       leaf name {
         description "Session destination address";
         type jt:ipaddr;
       }
       // uses apply-advanced;
       leaf authentication-key {
         description "MD5 authentication key";
         type string {
           length "1 .. 126";
         }
       }
       leaf authentication-algorithm {
         description "Authentication algorithm name";
         default "hmac-sha-1-96";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-auth-mismatch {
         description "Continue without TCP-AO if any one TCP endpoint does not have TCP-AO configured";
         type enumeration {
           enum "allow-without-tcpao" {
             description "Allow the connection establishment without TCP-AO";
           }
         }
       }
       leaf authentication-key-chain {
         description "Key chain name";
         type string {
           length "1 .. 128";
         }
       }
       leaf downstream-on-demand {
         description "Configure downstream on demand label distribution mode";
         type empty;
       }
       leaf transport-address {
         description "Address used for TCP sessions to the neighbor";
         type jt:ipaddr;
       }
       choice mtu-discovery-choice {
         leaf mtu-discovery {
           description "Enable TCP path MTU discovery";
           type empty;
         }
         leaf no-mtu-discovery {
           description "Don't enable TCP path MTU discovery";
           type empty;
         }
       }
     }
     list session-group {
       key name;
       description "Configure session group parameters";
       leaf name {
         description "Session destination address/prefix length";
         type jt:ipprefix;
       }
       // uses apply-advanced;
       leaf authentication-key {
         description "MD5 authentication key";
         type string {
           length "1 .. 126";
         }
       }
       leaf authentication-algorithm {
         description "Authentication algorithm name";
         default "hmac-sha-1-96";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-auth-mismatch {
         description "Continue without TCP-AO if any one TCP endpoint does not have TCP-AO configured";
         type enumeration {
           enum "allow-without-tcpao" {
             description "Allow the connection establishment without TCP-AO";
           }
         }
       }
       leaf authentication-key-chain {
         description "Key chain name";
         type string {
           length "1 .. 128";
         }
       }
       leaf downstream-on-demand {
         description "Configure downstream on demand label distribution mode";
         type empty;
       }
       leaf transport-address {
         description "Address used for TCP sessions to the neighbor";
         type jt:ipaddr;
       }
       choice mtu-discovery-choice {
         leaf mtu-discovery {
           description "Enable TCP path MTU discovery";
           type empty;
         }
         leaf no-mtu-discovery {
           description "Don't enable TCP path MTU discovery";
           type empty;
         }
       }
     }
     container session-protection {
       presence "enable session-protection";
       description "Configure session protection";
       leaf timeout {
         description "Session protection timeout";
         units "seconds";
         type union {
           type string {
             pattern "<.*>|$.*";
           }
           type uint16 {
             range "1 .. 65535";
           }
         }
       }
     }
     container igp-synchronization {
       description "Configure IGP synchronization parameters";
       // uses apply-advanced;
       leaf holddown-interval {
         description "Time to hold the up notification to the IGPs";
         units "seconds";
         type union {
           type string {
             pattern "<.*>|$.*";
           }
           type uint32 {
             range "10 .. 300";
           }
         }
       }
     }
    //  container log-updown {
    //    description "Logging actions for LSP up/down events";
    //    // uses apply-advanced;
    //    container trap {
    //      description "SNMP traps options";
    //      choice enable-disable {
    //        case case_1 {
    //          leaf disable {
    //            description "Disable LDP LSP up/down trap";
    //            type empty;
    //          }
    //        }
    //      }
    //    }
    //  }
    //  container policing {
    //    description "Configure policing for an LDP FEC";
    //    // uses apply-advanced;
    //    list fec {
    //      key name;
    //      ordered-by user;
    //      description "Forwarding equivalence class";
    //      leaf name {
    //        description "Forwarding equivalence class address";
    //        type jt:ipv4prefix;
    //      }
    //      // uses apply-advanced;
    //      leaf ingress-traffic {
    //        description "Name of filter to use for policing ingress LDP traffic";
    //        type string {
    //        }
    //      }
    //      leaf transit-traffic {
    //        description "Name of filter to use for policing transit LDP traffic";
    //        type string {
    //        }
    //      }
    //    }
    //  }
    //  container entropy-label {
    //    description "Insert entropy label for  a LDP FEC";
    //    // uses apply-advanced;
    //    leaf-list ingress-policy {
    //      ordered-by user;
    //      description "Entropy label ingress policy";
    //      type jt:policy-algebra;
    //    }
    //  }
    //  container oam {
    //    description "Configure periodic OAM for a LDP FEC";
    //    // uses apply-advanced;
    //    leaf-list ingress-policy {
    //      ordered-by user;
    //      description "OAM ingress policy";
    //      type jt:policy-algebra;
    //    }
    //    leaf-list bfd-port-egress-policy {
    //      ordered-by user;
    //      description "OAM egress policy";
    //      type jt:policy-algebra;
    //    }
    //    list fec {
    //      key name;
    //      ordered-by user;
    //      description "Forwarding equivalence class";
    //      leaf name {
    //        description "Forwarding equivalence class address";
    //        type jt:ipv4prefix;
    //      }
    //      // uses apply-advanced;
    //      choice bfd_liveness_detection_type {
    //        case case_1 {
    //          container bfd-liveness-detection {
    //            description "Bidirectional Forwarding Detection (BFD) options";
    //            // uses apply-advanced;
    //            leaf version {
    //              description "BFD protocol version number";
    //              default "automatic";
    //              type enumeration {
    //                enum "0" {
    //                  description "BFD version 0 (deprecated)";
    //                }
    //                enum "1" {
    //                  description "BFD version 1";
    //                }
    //                enum "automatic" {
    //                  description "Choose BFD version automatically";
    //                }
    //              }
    //            }
    //            leaf minimum-interval {
    //              description "Minimum transmit and receive interval";
    //              units "milliseconds";
    //              type union {
    //                type string {
    //                  pattern "<.*>|$.*";
    //                }
    //                type uint32 {
    //                  range "1 .. 255000";
    //                }
    //              }
    //            }
    //            leaf minimum-transmit-interval {
    //              description "Minimum transmit interval";
    //              status deprecated;
    //              units "milliseconds";
    //              type union {
    //                type string {
    //                  pattern "<.*>|$.*";
    //                }
    //                type uint32 {
    //                  range "1 .. 255000";
    //                }
    //              }
    //            }
    //            leaf minimum-receive-interval {
    //              description "Minimum receive interval";
    //              units "milliseconds";
    //              type union {
    //                type string {
    //                  pattern "<.*>|$.*";
    //                }
    //                type uint32 {
    //                  range "1 .. 255000";
    //                }
    //              }
    //            }
    //            leaf multiplier {
    //              description "Detection time multiplier";
    //              default "3";
    //              type union {
    //                type string {
    //                  pattern "<.*>|$.*";
    //                }
    //                type uint32 {
    //                  range "1 .. 255";
    //                }
    //              }
    //            }
    //            leaf inline-disable {
    //              description "Disable inline mode for this BFD session";
    //              type empty;
    //            }
    //            leaf pdu-size {
    //              description "BFD transport protocol payload size";
    //              default "24";
    //              type union {
    //                type string {
    //                  pattern "<.*>|$.*";
    //                }
    //                type uint32 {
    //                  range "24 .. 9000";
    //                }
    //              }
    //            }
    //            choice adaptation-choice {
    //              case case_1 {
    //                leaf no-adaptation {
    //                  description "Disable adaptation";
    //                  type empty;
    //                }
    //              }
    //            }
    //            container transmit-interval {
    //              description "Transmit-interval options";
    //              // uses apply-advanced;
    //              leaf minimum-interval {
    //                description "Minimum transmit interval";
    //                units "milliseconds";
    //                type union {
    //                  type string {
    //                    pattern "<.*>|$.*";
    //                  }
    //                  type uint32 {
    //                    range "1 .. 255000";
    //                  }
    //                }
    //              }
    //              leaf threshold {
    //                description "High transmit interval triggering a trap";
    //                units "milliseconds";
    //                type union {
    //                  type uint32;
    //                  type string {
    //                    pattern "<.*>|$.*";
    //                  }
    //                }
    //              }
    //            }
    //            container detection-time {
    //              description "Detection-time options";
    //              // uses apply-advanced;
    //              leaf threshold {
    //                description "High detection-time triggering a trap";
    //                units "milliseconds";
    //                type union {
    //                  type uint32;
    //                  type string {
    //                    pattern "<.*>|$.*";
    //                  }
    //                }
    //              }
    //            }
    //            leaf ecmp {
    //              description "Enable equal cost multipath (ECMP) support for BFD";
    //              type empty;
    //            }
    //            container failure-action {
    //              description "Action to take when BFD session goes down";
    //              choice action-choice {
    //                case case_1 {
    //                  leaf remove-route {
    //                    description "Remove LDP route from the ribs";
    //                    type empty;
    //                  }
    //                }
    //                case case_2 {
    //                  leaf remove-nexthop {
    //                    description "Remove LDP nexthop from the route";
    //                    type empty;
    //                  }
    //                }
    //              }
    //            }
    //            leaf holddown-interval {
    //              description "Time to hold the session-UP notification to the client";
    //              default "0";
    //              units "milliseconds";
    //              type union {
    //                type string {
    //                  pattern "<.*>|$.*";
    //                }
    //                type uint32 {
    //                  range "0 .. 255000";
    //                }
    //              }
    //            }
    //            leaf no-router-alert-option {
    //              description "Do not set Router-Alert options in IP header for MPLS-BFD";
    //              type empty;
    //            }
    //            leaf use-ip-ttl-1 {
    //              description "Set TTL value to 1 in IP header for MPLS-BFD";
    //              type empty;
    //            }
    //          }
    //        }
    //        case case_2 {
    //          leaf no-bfd-liveness-detection {
    //            description "Disable BFD liveness detection";
    //            type empty;
    //          }
    //        }
    //      }
    //      container periodic-traceroute {
    //        presence "enable periodic-traceroute";
    //        description "Configure periodic traceroute";
    //        // uses apply-advanced;
    //        leaf frequency {
    //          description "Time between traceroute attempts";
    //          units "minutes";
    //          type union {
    //            type string {
    //              pattern "<.*>|$.*";
    //            }
    //            type uint16 {
    //              range "15 .. 120";
    //            }
    //          }
    //        }
    //        leaf ttl {
    //          description "Maximum time-to-live value";
    //          type union {
    //            type string {
    //              pattern "<.*>|$.*";
    //            }
    //            type uint16 {
    //              range "1 .. 255";
    //            }
    //          }
    //        }
    //        leaf retries {
    //          description "Number of times to resend probe";
    //          type union {
    //            type string {
    //              pattern "<.*>|$.*";
    //            }
    //            type uint16 {
    //              range "1 .. 9";
    //            }
    //          }
    //        }
    //        leaf wait {
    //          description "Time to wait before resending probe";
    //          units "seconds";
    //          type union {
    //            type string {
    //              pattern "<.*>|$.*";
    //            }
    //            type uint16 {
    //              range "5 .. 15";
    //            }
    //          }
    //        }
    //        leaf paths {
    //          description "Maximum number of paths to traverse";
    //          type union {
    //            type string {
    //              pattern "<.*>|$.*";
    //            }
    //            type uint16 {
    //              range "1 .. 255";
    //            }
    //          }
    //        }
    //        leaf source {
    //          description "Source address to use when sending probes";
    //          type jt:ipv4addr;
    //        }
    //        leaf exp {
    //          description "Class-of-service value to use when sending probes";
    //          type union {
    //            type string {
    //              pattern "<.*>|$.*";
    //            }
    //            type uint16 {
    //              range "0 .. 7";
    //            }
    //          }
    //        }
    //        leaf fanout {
    //          description "Maximum number of nexthops to search per node";
    //          type union {
    //            type string {
    //              pattern "<.*>|$.*";
    //            }
    //            type uint16 {
    //              range "1 .. 64";
    //            }
    //          }
    //        }
    //        leaf disable {
    //          description "Disable periodic traceroute for a FEC";
    //          type empty;
    //        }
    //      }
    //    }
    //    container bfd-liveness-detection {
    //      description "Bidirectional Forwarding Detection (BFD) options";
    //      // uses apply-advanced;
    //      leaf version {
    //        description "BFD protocol version number";
    //        default "automatic";
    //        type enumeration {
    //          enum "0" {
    //            description "BFD version 0 (deprecated)";
    //          }
    //          enum "1" {
    //            description "BFD version 1";
    //          }
    //          enum "automatic" {
    //            description "Choose BFD version automatically";
    //          }
    //        }
    //      }
    //      leaf minimum-interval {
    //        description "Minimum transmit and receive interval";
    //        units "milliseconds";
    //        type union {
    //          type string {
    //            pattern "<.*>|$.*";
    //          }
    //          type uint32 {
    //            range "1 .. 255000";
    //          }
    //        }
    //      }
    //      leaf minimum-transmit-interval {
    //        description "Minimum transmit interval";
    //        status deprecated;
    //        units "milliseconds";
    //        type union {
    //          type string {
    //            pattern "<.*>|$.*";
    //          }
    //          type uint32 {
    //            range "1 .. 255000";
    //          }
    //        }
    //      }
    //      leaf minimum-receive-interval {
    //        description "Minimum receive interval";
    //        units "milliseconds";
    //        type union {
    //          type string {
    //            pattern "<.*>|$.*";
    //          }
    //          type uint32 {
    //            range "1 .. 255000";
    //          }
    //        }
    //      }
    //      leaf multiplier {
    //        description "Detection time multiplier";
    //        default "3";
    //        type union {
    //          type string {
    //            pattern "<.*>|$.*";
    //          }
    //          type uint32 {
    //            range "1 .. 255";
    //          }
    //        }
    //      }
    //      leaf inline-disable {
    //        description "Disable inline mode for this BFD session";
    //        type empty;
    //      }
    //      leaf pdu-size {
    //        description "BFD transport protocol payload size";
    //        default "24";
    //        type union {
    //          type string {
    //            pattern "<.*>|$.*";
    //          }
    //          type uint32 {
    //            range "24 .. 9000";
    //          }
    //        }
    //      }
    //      choice adaptation-choice {
    //        case case_1 {
    //          leaf no-adaptation {
    //            description "Disable adaptation";
    //            type empty;
    //          }
    //        }
    //      }
    //      container transmit-interval {
    //        description "Transmit-interval options";
    //        // uses apply-advanced;
    //        leaf minimum-interval {
    //          description "Minimum transmit interval";
    //          units "milliseconds";
    //          type union {
    //            type string {
    //              pattern "<.*>|$.*";
    //            }
    //            type uint32 {
    //              range "1 .. 255000";
    //            }
    //          }
    //        }
    //        leaf threshold {
    //          description "High transmit interval triggering a trap";
    //          units "milliseconds";
    //          type union {
    //            type uint32;
    //            type string {
    //              pattern "<.*>|$.*";
    //            }
    //          }
    //        }
    //      }
    //      container detection-time {
    //        description "Detection-time options";
    //        // uses apply-advanced;
    //        leaf threshold {
    //          description "High detection-time triggering a trap";
    //          units "milliseconds";
    //          type union {
    //            type uint32;
    //            type string {
    //              pattern "<.*>|$.*";
    //            }
    //          }
    //        }
    //      }
    //      leaf ecmp {
    //        description "Enable equal cost multipath (ECMP) support for BFD";
    //        type empty;
    //      }
    //      container failure-action {
    //        description "Action to take when BFD session goes down";
    //        choice action-choice {
    //          case case_1 {
    //            leaf remove-route {
    //              description "Remove LDP route from the ribs";
    //              type empty;
    //            }
    //          }
    //          case case_2 {
    //            leaf remove-nexthop {
    //              description "Remove LDP nexthop from the route";
    //              type empty;
    //            }
    //          }
    //        }
    //      }
    //      leaf holddown-interval {
    //        description "Time to hold the session-UP notification to the client";
    //        default "0";
    //        units "milliseconds";
    //        type union {
    //          type string {
    //            pattern "<.*>|$.*";
    //          }
    //          type uint32 {
    //            range "0 .. 255000";
    //          }
    //        }
    //      }
    //      leaf no-router-alert-option {
    //        description "Do not set Router-Alert options in IP header for MPLS-BFD";
    //        type empty;
    //      }
    //      leaf use-ip-ttl-1 {
    //        description "Set TTL value to 1 in IP header for MPLS-BFD";
    //        type empty;
    //      }
    //    }
    //    container periodic-traceroute {
    //      presence "enable periodic-traceroute";
    //      description "Configure periodic traceroute";
    //      // uses apply-advanced;
    //      leaf frequency {
    //        description "Time between traceroute attempts";
    //        units "minutes";
    //        type union {
    //          type string {
    //            pattern "<.*>|$.*";
    //          }
    //          type uint16 {
    //            range "15 .. 120";
    //          }
    //        }
    //      }
    //      leaf ttl {
    //        description "Maximum time-to-live value";
    //        type union {
    //          type string {
    //            pattern "<.*>|$.*";
    //          }
    //          type uint16 {
    //            range "1 .. 255";
    //          }
    //        }
    //      }
    //      leaf retries {
    //        description "Number of times to resend probe";
    //        type union {
    //          type string {
    //            pattern "<.*>|$.*";
    //          }
    //          type uint16 {
    //            range "1 .. 9";
    //          }
    //        }
    //      }
    //      leaf wait {
    //        description "Time to wait before resending probe";
    //        units "seconds";
    //        type union {
    //          type string {
    //            pattern "<.*>|$.*";
    //          }
    //          type uint16 {
    //            range "5 .. 15";
    //          }
    //        }
    //      }
    //      leaf paths {
    //        description "Maximum number of paths to traverse";
    //        type union {
    //          type string {
    //            pattern "<.*>|$.*";
    //          }
    //          type uint16 {
    //            range "1 .. 255";
    //          }
    //        }
    //      }
    //      leaf source {
    //        description "Source address to use when sending probes";
    //        type jt:ipv4addr;
    //      }
    //      leaf exp {
    //        description "Class-of-service value to use when sending probes";
    //        type union {
    //          type string {
    //            pattern "<.*>|$.*";
    //          }
    //          type uint16 {
    //            range "0 .. 7";
    //          }
    //        }
    //      }
    //      leaf fanout {
    //        description "Maximum number of nexthops to search per node";
    //        type union {
    //          type string {
    //            pattern "<.*>|$.*";
    //          }
    //          type uint16 {
    //            range "1 .. 64";
    //          }
    //        }
    //      }
    //    }
    //    leaf lsp-ping-interval {
    //      description "Time interval between LSP ping messages";
    //      default "60";
    //      units "seconds";
    //      type union {
    //        type string {
    //          pattern "<.*>|$.*";
    //        }
    //        type uint16 {
    //          range "30 .. 3600";
    //        }
    //      }
    //    }
    //    leaf lsp-ping-multiplier {
    //      description "Number of ping reply missed before declaring BFD down";
    //      type union {
    //        type string {
    //          pattern "<.*>|$.*";
    //        }
    //        type uint8 {
    //          range "1 .. 5";
    //        }
    //      }
    //    }
    //  }
    //  container targeted-hello {
    //    description "Configure targeted hello parameters";
    //    // uses apply-advanced;
    //    leaf hello-interval {
    //      description "Hello interval (seconds)";
    //      type union {
    //        type string {
    //          pattern "<.*>|$.*";
    //        }
    //        type uint32 {
    //          range "1 .. 65535";
    //        }
    //      }
    //    }
    //    leaf hold-time {
    //      description "Hold interval (seconds)";
    //      type union {
    //        type string {
    //          pattern "<.*>|$.*";
    //        }
    //        type uint32 {
    //          range "1 .. 65535";
    //        }
    //      }
    //    }
    //  }
    //  container p2mp {
    //    presence "enable p2mp";
    //    description "Advertise P2MP capability to peers";
    //    // uses apply-advanced;
    //    container recursive {
    //      description "Configure P2MP recursive parameters";
    //      // uses apply-advanced;
    //      leaf route {
    //        description "Allow recursive route resolution to signal P2MP FEC";
    //        type empty;
    //      }
    //      leaf fec {
    //        description "Allow recursive fec to signal P2MP FEC";
    //        type empty;
    //      }
    //    }
    //    list root-address {
    //      key name;
    //      description "Configure the root address of P2MP LSP";
    //      leaf name {
    //        description "Root address of the P2MP LSP";
    //        type jt:ipaddr;
    //      }
    //      // uses apply-advanced;
    //      list lsp-id {
    //        key name;
    //        description "Configure the generic LSP identifier";
    //        leaf name {
    //          description "Generic LSP identifier value";
    //          type union {
    //            type string {
    //              pattern "<.*>|$.*";
    //            }
    //            type uint32 {
    //              range "1 .. 65535";
    //            }
    //          }
    //        }
    //        // uses apply-advanced;
    //      }
    //      list group-address {
    //        key name;
    //        description "IPv4/Ipv6 group address for mLDP LSP";
    //        leaf name {
    //          description "IPv4/Ipv6 group address";
    //          type jt:ipaddr;
    //        }
    //        // uses apply-advanced;
    //        list source-address {
    //          key name;
    //          description "IPv4/Ipv6 source address";
    //          leaf name {
    //            description "IPv4/Ipv6 source address for mLDP LSP";
    //            type jt:ipaddr;
    //          }
    //          // uses apply-advanced;
    //        }
    //      }
    //    }
    //    leaf no-rsvp-tunneling {
    //      description "Do not allow LDP P2MP to use RSVP-TE LSPs for tunneling";
    //      type empty;
    //    }
    //  }
    //  container sr-mapping-client {
    //    presence "enable sr-mapping-client";
    //    description "Enable LDP to SR mapping-client functionality";
    //    // uses apply-advanced;
    //    leaf-list policy {
    //      ordered-by user;
    //      description "SR mapping-client policy";
    //      type jt:policy-algebra;
    //    }
    //  }
     leaf upstream-label-assignment {
       description "Allow Upstream Label Assignment capability";
       type empty;
     }
     list family {
       key name;
       ordered-by user;
       description "Address family";
       leaf name {
         type enumeration {
           enum "inet" {
             description "IPv4 family";
           }
           enum "inet6" {
             description "IPv6 family";
           }
         }
       }
       // uses apply-advanced;
     }
     leaf transport-preference {
       description "TCP transport preference";
       type enumeration {
         enum "ipv4" {
           description "Use IPv4 for TCP connections";
         }
         enum "ipv6" {
           description "Use IPv6 for TCP connections";
         }
       }
     }
     container dual-transport {
       presence "enable dual-transport";
       description "Use separate IPv4 and IPv6 TCP transport";
       // uses apply-advanced;
       leaf inet-lsr-id {
         description "LSR identifier for address family inet";
         type jt:ipv4addr;
       }
       leaf inet6-lsr-id {
         description "LSR identifier for address family inet6";
         type jt:ipv4addr;
       }
     }
     leaf no-propagate-ttl {
       description "Disable TTL propagation from IP to MPLS (on push) and MPLS to IP (on pop)";
       type empty;
     }
   }
   grouping juniper-protocols-mpls {
     description "Multiprotocol Label Switching options";
     // uses apply-advanced;
    //  list lsp-external-controller {
    //    key name;
    //    ordered-by user;
    //    description "External path computing entity";
    //    leaf name {
    //      description "Name of the external path computing entity";
    //      type string {
    //      }
    //    }
    //    // uses apply-advanced;
    //    container label-switched-path-template {
    //      description "Template for externally provisioned LSP parameters";
    //      // uses apply-advanced;
    //      choice dynamic-template {
    //        case case_1 {
    //          leaf template-name {
    //            description "Name of point-to-point LSP template";
    //            type string {
    //              length "1 .. 32";
    //            }
    //          }
    //        }
    //        case case_2 {
    //          leaf default-template {
    //            description "Use default parameters";
    //            type empty;
    //          }
    //        }
    //      }
    //    }
    //   //  container label-switched-path-p2mp-template {
    //   //    description "Template for externally provisioned P2MP LSP parameters";
    //   //    // uses apply-advanced;
    //   //    choice dynamic-template {
    //   //      case case_1 {
    //   //        leaf template-name {
    //   //          description "Name of point-to-multipoint LSP template";
    //   //          type string {
    //   //            length "1 .. 32";
    //   //          }
    //   //        }
    //   //      }
    //   //      case case_2 {
    //   //        leaf default-template {
    //   //          description "Use default parameters";
    //   //          type empty;
    //   //        }
    //   //      }
    //   //    }
    //   //  }
    //   //  list pce-controlled-lsp {
    //   //    key name;
    //   //    ordered-by user;
    //   //    description "Template for externally provisioned LSP using regular expression";
    //   //    leaf name {
    //   //      description "Template regular expression";
    //   //      type string {
    //   //      }
    //   //    }
    //   //    // uses apply-advanced;
    //   //    container label-switched-path-template {
    //   //      description "Template for externally provisioned LSP parameters";
    //   //      // uses apply-advanced;
    //   //      leaf template-name {
    //   //        description "Name of point-to-point LSP template";
    //   //        type string {
    //   //          length "1 .. 64";
    //   //        }
    //   //      }
    //   //    }
    //   //    container label-switched-path-p2mp-template {
    //   //      description "Template for externally provisioned P2MP LSP parameters";
    //   //      // uses apply-advanced;
    //   //      leaf template-name {
    //   //        description "Name of point-to-multipoint LSP template";
    //   //        type string {
    //   //          length "1 .. 64";
    //   //        }
    //   //      }
    //   //    }
    //   //  }
    //  }
     container path-mtu {
       presence "enable path-mtu";
       description "Path MTU configuration";
       // uses apply-advanced;
       leaf allow-fragmentation {
         description "If needed, fragment IP before encapsulating in MPLS";
         type empty;
       }
       container rsvp {
         presence "enable rsvp";
         description "RSVP-specific path MTU options";
         // uses apply-advanced;
         leaf mtu-signaling {
           description "Enable RSVP path MTU signaling";
           type empty;
         }
       }
     }
     container diffserv-te {
       description "Global diffserv-traffic-engineering options";
       // uses apply-advanced;
       leaf bandwidth-model {
         description "Bandwidth constraint model supported";
         type enumeration {
           enum "extended-mam" {
             description "Maximum allocation model with support for E-LSPs";
           }
           enum "mam" {
             description "Maximum allocation model";
           }
           enum "rdm" {
             description "Russian dolls model";
           }
         }
       }
      //  container te-class-matrix {
      //    description "Supported combinations of traffic-class and preemption";
      //    // uses apply-advanced;
      //    container te0 {
      //      description "Definition for traffic-engineering class te0";
      //      uses te-class-object;
      //    }
      //    container te1 {
      //      description "Definition for traffic-engineering class te1";
      //      uses te-class-object;
      //    }
      //    container te2 {
      //      description "Definition for traffic-engineering class te2";
      //      uses te-class-object;
      //    }
      //    container te3 {
      //      description "Definition for traffic-engineering class te3";
      //      uses te-class-object;
      //    }
      //    container te4 {
      //      description "Definition for traffic-engineering class te4";
      //      uses te-class-object;
      //    }
      //    container te5 {
      //      description "Definition for traffic-engineering class te5";
      //      uses te-class-object;
      //    }
      //    container te6 {
      //      description "Definition for traffic-engineering class te6";
      //      uses te-class-object;
      //    }
      //    container te7 {
      //      description "Definition for traffic-engineering class te7";
      //      uses te-class-object;
      //    }
      //  }
     }
    //  container auto-policing {
    //    description "Automatic policing of LSPs";
    //    // uses apply-advanced;
    //    list class {
    //      key name;
    //      ordered-by user;
    //      description "Forwarding class";
    //      leaf name {
    //        type enumeration {
    //          enum "all" {
    //            description "All forwarding classes";
    //          }
    //          enum "ct0" {
    //            description "Forwarding class 0";
    //          }
    //          enum "ct1" {
    //            description "Forwarding class 1";
    //          }
    //          enum "ct2" {
    //            description "Forwarding class 2";
    //          }
    //          enum "ct3" {
    //            description "Forwarding class 3";
    //          }
    //        }
    //      }
    //      // uses apply-advanced;
    //      choice policing-action {
    //        case case_1 {
    //          leaf drop {
    //            description "Drop packets if bandwidth is exceeded";
    //            type empty;
    //          }
    //        }
    //        case case_2 {
    //          leaf loss-priority-high {
    //            description "Set loss priority to high if bandwidth is exceeded";
    //            type empty;
    //          }
    //        }
    //        case case_3 {
    //          leaf loss-priority-low {
    //            description "Set loss priority to low if bandwidth is exceeded";
    //            type empty;
    //          }
    //        }
    //      }
    //    }
    //  }
    //  container statistics {
    //    description "Collect statistics for signaled label-switched paths";
    //    // uses apply-advanced;
    //    container file {
    //      presence "enable file";
    //      description "Statistics file options";
    //      leaf filename {
    //        description "Name of file in which to write trace information";
    //        type string {
    //          length "1 .. 1024";
    //        }
    //      }
    //      leaf replace {
    //        description "Replace trace file rather than appending to it";
    //        status deprecated;
    //        type empty;
    //      }
    //      leaf size {
    //        description "Maximum trace file size";
    //        type string;
    //      }
    //      leaf files {
    //        description "Maximum number of trace files";
    //        default "10";
    //        type union {
    //          type string {
    //            pattern "<.*>|$.*";
    //          }
    //          type uint32 {
    //            range "2 .. 1000";
    //          }
    //        }
    //      }
    //      leaf no-stamp {
    //        description "Do not timestamp trace file";
    //        status deprecated;
    //        type empty;
    //      }
    //      choice world-readable-choice {
    //        leaf world-readable {
    //          description "Allow any user to read the log file";
    //          type empty;
    //        }
    //        leaf no-world-readable {
    //          description "Don't allow any user to read the log file";
    //          type empty;
    //        }
    //      }
    //    }
    //    leaf interval {
    //      description "Time to collect statistics (seconds)";
    //      type union {
    //        type string {
    //          pattern "<.*>|$.*";
    //        }
    //        type int32 {
    //          range "1 .. 65535";
    //        }
    //      }
    //    }
    //    leaf auto-bandwidth {
    //      description "Enable auto bandwidth allocation";
    //      type empty;
    //    }
    //    leaf no-transit-statistics {
    //      description "Disable transit LSP statistics collection";
    //      type empty;
    //    }
    //    choice transit-polling-type {
    //      case case_1 {
    //        leaf no-transit-statistics-polling {
    //          description "Disable polling and display of transit lsp statistics";
    //          status deprecated;
    //          type empty;
    //        }
    //      }
    //      case case_2 {
    //        leaf transit-statistics-polling {
    //          description "Enable polling and display of transit lsp statistics";
    //          type empty;
    //        }
    //      }
    //    }
    //    leaf no-bypass-statistics-polling {
    //      description "Disable polling and display of bypass lsp statistics";
    //      type empty;
    //    }
    //    leaf statistics-query-batch-size {
    //      description "Number of LSPs for which statistics will be queried together";
    //      type union {
    //        type string {
    //          pattern "<.*>|$.*";
    //        }
    //        type int32 {
    //          range "1 .. 25";
    //        }
    //      }
    //    }
    //    leaf traffic-class-statistics {
    //      description "Create per traffic class statistics sensors for LSPs";
    //      type empty;
    //    }
    //  }
    //  container p2mp-lsp {
    //    description "P2MP LSP control configuration";
    //    // uses apply-advanced;
    //    leaf single-abr {
    //      description "Try to use same exit node for all inter-domain sub LSPs";
    //      type empty;
    //    }
    //    leaf no-re-merge {
    //      description "Avoid LSP CSPF creating remerge";
    //      type empty;
    //    }
    //  }
     container log-updown {
       description "Logging actions for LSP up/down events";
       // uses apply-advanced;
       choice syslog-choice {
         leaf syslog {
           description "Send syslog messages";
           type empty;
         }
         leaf no-syslog {
           description "Don't send syslog messages";
           type empty;
         }
       }
       choice trap-choice {
         case case_1 {
           leaf trap {
             description "Send SNMP traps";
             type empty;
           }
         }
         case case_2 {
           container no-trap {
             presence "enable no-trap";
             description "Don't send SNMP traps";
             // uses apply-advanced;
             leaf mpls-lsp-traps {
               description "Dont send mpls lsp up/down traps";
               type empty;
             }
             leaf rfc3812-traps {
               description "Dont send rfc3812 traps";
               type empty;
             }
           }
         }
       }
       leaf trap-path-down {
         description "Send SNMP traps when a path goes down";
         type empty;
       }
       leaf trap-path-up {
         description "Send SNMP traps when a path goes up";
         type empty;
       }
     }
     container optimize-adaptive-teardown {
       description "Post make before break adaptive teardown";
       // uses apply-advanced;
       leaf p2p {
         description "Turn on post make before break adaptive teardown for p2p";
         type empty;
       }
       leaf timeout {
         description "Timeout for adaptive teardown to clean up LSP";
         units "seconds";
         type union {
           type string {
             pattern "<.*>|$.*";
           }
           type int32 {
             range "1 .. 65535";
           }
         }
       }
       container delay {
         description "Delay tearing down old optimized path after adaptive-teardown kicks in";
         // uses apply-advanced;
         leaf delay-value {
           description "Delay tearing down old optimized path after adaptive-teardown kicks in";
           units "seconds";
           type union {
             type string {
               pattern "<.*>|$.*";
             }
             type int32 {
               range "3 .. 65535";
             }
           }
         }
       }
     }
     container traffic-engineering {
       presence "enable traffic-engineering";
       description "Traffic-engineering control";
       // uses apply-advanced;
       choice protocols {
         case case_1 {
           leaf bgp {
             description "BGP destinations only";
             type empty;
           }
         }
         case case_2 {
           leaf bgp-igp {
             description "BGP and IGP destinations";
             type empty;
           }
         }
         case case_3 {
           leaf bgp-igp-both-ribs {
             description "BGP and IGP destinations with routes in both routing tables";
             type empty;
           }
         }
         case case_4 {
           leaf mpls-forwarding {
             description "Use MPLS routes for forwarding, not routing";
             type empty;
           }
         }
       }
       container database {
         description "Traffic engineering database";
         // uses apply-advanced;
         container import {
           description "Configure TED import parameters";
           // uses apply-advanced;
           container l3-unicast-topology {
             presence "enable l3-unicast-topology";
             description "Download L3-Unicast topology into RIB";
             // uses apply-advanced;
             leaf bgp-link-state {
               description "Export L3-Unicast topology, instead of TE topology, into BGP-LS";
               type empty;
             }
           }
           leaf-list policy {
             ordered-by user;
             description "Configure import policy";
             type jt:policy-algebra;
           }
           leaf identifier {
             description "BGP-TE identifier";
             type union {
               type string {
                 pattern "<.*>|$.*";
               }
               type uint64 {
                 range "2 .. 18446744073709551615";
               }
             }
           }
           leaf bgp-ls-identifier {
             description "BGP-TE domain identifier";
             type union {
               type uint32;
               type string {
                 pattern "<.*>|$.*";
               }
             }
           }
           leaf ipv6 {
             description "Import ipv6 addresses";
             type empty;
           }
         }
         container export {
           description "Configure TED export related parameters";
           // uses apply-advanced;
           leaf-list policy {
             ordered-by user;
             description "Export policy";
             type jt:policy-algebra;
           }
           container credibility {
             description "TED credibility value for entries from BGP-TE";
             // uses apply-advanced;
             leaf unknown {
               description "Entries sourced from unknown entities";
               type union {
                 type string {
                   pattern "<.*>|$.*";
                 }
                 type uint32 {
                   range "0 .. 512";
                 }
               }
             }
             leaf direct {
               description "Entries sourced from directly connected links";
               type union {
                 type string {
                   pattern "<.*>|$.*";
                 }
                 type uint32 {
                   range "0 .. 512";
                 }
               }
             }
             leaf static {
               description "Entries sourced from static configuration";
               type union {
                 type string {
                   pattern "<.*>|$.*";
                 }
                 type uint32 {
                   range "0 .. 512";
                 }
               }
             }
             leaf ospf {
               description "Entries sourced from ospf";
               type union {
                 type string {
                   pattern "<.*>|$.*";
                 }
                 type uint32 {
                   range "0 .. 512";
                 }
               }
             }
             leaf isis-level-1 {
               description "Entries sourced from ISIS Level 1";
               type union {
                 type string {
                   pattern "<.*>|$.*";
                 }
                 type uint32 {
                   range "0 .. 512";
                 }
               }
             }
             leaf isis-level-2 {
               description "Entries sourced from ISIS Level 2";
               type union {
                 type string {
                   pattern "<.*>|$.*";
                 }
                 type uint32 {
                   range "0 .. 512";
                 }
               }
             }
             leaf bgp {
               description "Entries sourced from BGP";
               type union {
                 type string {
                   pattern "<.*>|$.*";
                 }
                 type uint32 {
                   range "0 .. 512";
                 }
               }
             }
           }
           leaf l3-unicast-topology {
             description "Download RIB entries into L3-Unicast topology";
             type empty;
           }
         }
       }
     }
     list admin-groups {
       key name;
       ordered-by user;
       description "Administrative groups";
       leaf name {
         description "Group name";
         type string;
       }
       // uses apply-advanced;
       leaf group-value {
         description "Group bit position";
         type union {
           type string {
             pattern "<.*>|$.*";
           }
           type uint32 {
             range "0 .. 31";
           }
         }
       }
     }
     leaf advertisement-hold-time {
       description "Time that an 'LSP down' advertisement will be delayed";
       default "5";
       units "seconds";
       type union {
         type string {
           pattern "<.*>|$.*";
         }
         type uint32 {
           range "0 .. 65535";
         }
       }
     }
     leaf rsvp-error-hold-time {
       description "Time that RSVP PathErr events will be remembered";
       default "25";
       units "seconds";
       type union {
         type string {
           pattern "<.*>|$.*";
         }
         type uint32 {
           range "0 .. 240";
         }
       }
     }
    //  leaf optimize-aggressive {
    //    description "Run aggressive optimization algorithm based on IGP metric only";
    //    type empty;
    //  }
    //  leaf smart-optimize-timer {
    //    description "Path optimization interval after a link traversed by the path goes down";
    //    units "seconds";
    //    type union {
    //      type string {
    //        pattern "<.*>|$.*";
    //      }
    //      type int32 {
    //        range "0 .. 65535";
    //      }
    //    }
    //  }
    //  leaf optimize-switchover-delay {
    //    description "Delay before switching LSP to newly optimized path";
    //    units "seconds";
    //    type union {
    //      type string {
    //        pattern "<.*>|$.*";
    //      }
    //      type int32 {
    //        range "1 .. 900";
    //      }
    //    }
    //  }
     leaf no-propagate-ttl {
       description "Disable TTL propagation from IP to MPLS (on push) and MPLS to IP (on pop)";
       type empty;
     }
     leaf sensor-based-stats {
       description "Enable sensor based statistics collection";
       type empty;
     }
     leaf explicit-null {
       description "Advertise the EXPLICIT_NULL label when the router is the egress";
       type empty;
     }
     leaf icmp-tunneling {
       description "Allow MPLS LSPs to be used for tunneling ICMP error packets";
       type empty;
     }
     leaf revert-timer {
       description "Hold-down window before reverting back to primary path, 0 means disable";
       units "seconds";
       type union {
         type string {
           pattern "<.*>|$.*";
         }
         type int32 {
           range "0 .. 65535";
         }
       }
     }
    //  leaf optimize-hold-dead-delay {
    //    description "Delay before tearing down the old optimized path";
    //    units "seconds";
    //    type union {
    //      type string {
    //        pattern "<.*>|$.*";
    //      }
    //      type int32 {
    //        range "0 .. 65535";
    //      }
    //    }
    //  }
    //  leaf cspf-backoff-time {
    //    description "Delay before CSPF, when there is PathErr on backup path";
    //    units "seconds";
    //    type union {
    //      type string {
    //        pattern "<.*>|$.*";
    //      }
    //      type int32 {
    //        range "0 .. 65535";
    //      }
    //    }
    //  }
    //  leaf expand-loose-hop {
    //    description "Perform CSPF path computation to expand loose hops";
    //    type empty;
    //  }
    //  leaf mib-mpls-show-p2mp {
    //    description "Show p2mp tunnels entries in mpls mib walk";
    //    type empty;
    //  }
     container bandwidth {
       description "Bandwidth to reserve (bps)";
       uses bandwidth-type;
     }
    //  container admin-group {
    //    description "Administrative group policy";
    //    uses admin_group_include_exclude;
    //  }
    //  container admin-group-extended {
    //    description "Extended administrative group policy";
    //    uses admin_group_include_exclude;
    //  }
     container priority {
       presence "enable priority";
       description "Preemption priorities";
     }
     leaf setup-priority {
       description "Set-up priority";
       type union {
         type string {
           pattern "<.*>|$.*";
         }
         type uint32 {
           range "0 .. 7";
         }
       }
     }
     leaf reservation-priority {
       description "Reservation priority";
       type union {
         type string {
           pattern "<.*>|$.*";
         }
         type uint32 {
           range "0 .. 7";
         }
       }
     }
    //  container oam {
    //    description "Periodic OAM";
    //    uses periodic_oam;
    //  }
     leaf class-of-service {
       description "Class-of-service value";
       type union {
         type string {
           pattern "<.*>|$.*";
         }
         type int32 {
           range "0 .. 7";
         }
       }
     }
     leaf no-decrement-ttl {
       description "Do not decrement the TTL within an LSP";
       type empty;
     }
     leaf hop-limit {
       description "Maximum allowed router hops";
       type union {
         type string {
           pattern "<.*>|$.*";
         }
         type int32 {
           range "2 .. 255";
         }
       }
     }
     leaf no-cspf {
       description "Disable automatic path computation";
       type empty;
     }
     leaf admin-down {
       description "Set GMPLS LSP to administrative down state";
       type empty;
     }
     leaf optimize-timer {
       description "Periodical path reoptimizations";
       units "seconds";
       type union {
         type string {
           pattern "<.*>|$.*";
         }
         type int32 {
           range "0 .. 65535";
         }
       }
     }
     leaf preference {
       description "Preference value";
       type union {
         type uint32;
         type string {
           pattern "<.*>|$.*";
         }
       }
     }
    //  choice record-choice {
    //    leaf record {
    //      description "Record transit routers";
    //      type empty;
    //    }
    //    leaf no-record {
    //      description "Don't record transit routers";
    //      type empty;
    //    }
    //  }
    //  leaf standby {
    //    description "Keep backup paths in continuous standby";
    //    type empty;
    //  }
    //  leaf exclude-srlg {
    //    description "Exclude SRLG links for secondary path";
    //    type empty;
    //  }
    //  leaf ultimate-hop-popping {
    //    description "Request ultimate hop popping from egress";
    //    type empty;
    //  }
    //  leaf sync-active-path-bandwidth {
    //    description "Signal standby path with bandwidth obtained from active path";
    //    type empty;
    //  }
    //  leaf cross-credibility-cspf {
    //    description "Compute paths across multi-protocol links and nodes";
    //    type empty;
    //  }
    //  leaf top-credibility-only-cspf {
    //    description "Compute paths only using highest credibility links and nodes";
    //    type empty;
    //  }
    //  list label-switched-path {
    //    key name;
    //    ordered-by user;
    //    description "Label-switched path";
    //    leaf name {
    //      description "Name of path";
    //      type string {
    //        length "1 .. 64";
    //      }
    //    }
    //    // uses apply-advanced;
    //    choice enable-disable {
    //      case case_1 {
    //        leaf disable {
    //          description "Disable MPLS label-switched path";
    //          type empty;
    //        }
    //      }
    //    }
    //    container traceoptions {
    //      description "Trace options for MPLS label-switched path";
    //      // uses apply-advanced;
    //      container file {
    //        description "Trace file options";
    //        leaf filename {
    //          description "Name of file in which to write trace information";
    //          type string {
    //            length "1 .. 1024";
    //          }
    //        }
    //        leaf replace {
    //          description "Replace trace file rather than appending to it";
    //          status deprecated;
    //          type empty;
    //        }
    //        leaf size {
    //          description "Maximum trace file size";
    //          type string;
    //        }
    //        leaf files {
    //          description "Maximum number of trace files";
    //          default "10";
    //          type union {
    //            type string {
    //              pattern "<.*>|$.*";
    //            }
    //            type uint32 {
    //              range "2 .. 1000";
    //            }
    //          }
    //        }
    //        leaf no-stamp {
    //          description "Do not timestamp trace file";
    //          status deprecated;
    //          type empty;
    //        }
    //        choice world-readable-choice {
    //          leaf world-readable {
    //            description "Allow any user to read the log file";
    //            type empty;
    //          }
    //          leaf no-world-readable {
    //            description "Don't allow any user to read the log file";
    //            type empty;
    //          }
    //        }
    //      }
    //      list flag {
    //        key name;
    //        ordered-by user;
    //        description "Tracing parameters";
    //        leaf name {
    //          type enumeration {
    //            enum "cspf" {
    //              description "Trace CSPF computation";
    //            }
    //            enum "cspf-node" {
    //              description "Trace nodes visited during CSPF";
    //            }
    //            enum "cspf-link" {
    //              description "Trace links visited during CSPF";
    //            }
    //            enum "cspf-abstract" {
    //              description "Trace abstract hop based CSPF details";
    //            }
    //            enum "state" {
    //              description "Trace state transitions";
    //            }
    //            enum "all" {
    //              description "Trace everything";
    //            }
    //          }
    //        }
    //      }
    //    }
    //    leaf no-install-to-address {
    //      description "Don't install host route 'to' address into routing tables";
    //      type empty;
    //    }
    //    leaf backup {
    //      description "Use LSP for IGP backup";
    //      type empty;
    //    }
    //    leaf from {
    //      description "Address of ingress router";
    //      type jt:ipv4addr;
    //    }
    //    container pop-and-forward {
    //      presence "enable pop-and-forward";
    //      description "Enable LSP as pop-and-forward with auto-delegation";
    //    }
    //    choice label-switched-path-or-template {
    //      case case_1 {
    //        leaf to {
    //          description "Address of egress router";
    //          type jt:ipv4addr;
    //        }
    //      }
    //      case case_2 {
    //        leaf template {
    //          description "Template for dynamic lsp paramaters";
    //          type empty;
    //        }
    //      }
    //    }
    //    leaf corouted-bidirectional {
    //      description "Setup the LSP as a corouted bidirectional LSP";
    //      type empty;
    //    }
    //    leaf corouted-bidirectional-passive {
    //      description "Associate LSP with incoming corouted bidirectional LSP";
    //      type empty;
    //    }
    //    leaf metric {
    //      description "Metric value";
    //      type union {
    //        type string {
    //          pattern "<.*>|$.*";
    //        }
    //        type uint32 {
    //          range "1 .. 16777215";
    //        }
    //      }
    //    }
    //    container conditional-metric {
    //      description "Set a conditional metric value for the LSP";
    //      // uses apply-advanced;
    //      list igp-metric-threshold {
    //        key name;
    //        description "Set conditional LSP metric based on IGP metric, up to 4 conditions";
    //        max-elements 4;
    //        leaf name {
    //          description "Conditional IGP metric threshold";
    //          type union {
    //            type string {
    //              pattern "<.*>|$.*";
    //            }
    //            type uint32 {
    //              range "1 .. 16777215";
    //            }
    //          }
    //        }
    //        leaf conditional-metric-value {
    //          description "Conditional LSP metric value";
    //          type union {
    //            type string {
    //              pattern "<.*>|$.*";
    //            }
    //            type uint32 {
    //              range "1 .. 16777215";
    //            }
    //          }
    //        }
    //      }
    //    }
    //    container metric-type {
    //      description "Metric type used for computaion";
    //      // uses apply-advanced;
    //      choice metric-type-choice {
    //        case case_1 {
    //          leaf te {
    //            description "TE metric";
    //            type empty;
    //          }
    //        }
    //        case case_2 {
    //          leaf igp {
    //            description "IGP metric";
    //            type empty;
    //          }
    //        }
    //        case case_3 {
    //          container delay {
    //            presence "enable delay";
    //            description "Delay metric";
    //            // uses apply-advanced;
    //            choice metric-choice {
    //              case case_1 {
    //                leaf minimum {
    //                  description "Minimum delay metric type";
    //                  type empty;
    //                }
    //              }
    //              case case_2 {
    //                leaf maximum {
    //                  description "Maximum delay metric type";
    //                  type empty;
    //                }
    //              }
    //              case case_3 {
    //                leaf average {
    //                  description "Average delay metric type";
    //                  type empty;
    //                }
    //              }
    //            }
    //            leaf delay-variation-threshold {
    //              description "Link delay variation threshold";
    //              type union {
    //                type string {
    //                  pattern "<.*>|$.*";
    //                }
    //                type uint32 {
    //                  range "1 .. 16777215";
    //                }
    //              }
    //            }
    //          }
    //        }
    //      }
    //    }
    //    leaf ldp-tunneling {
    //      description "Allow LDP to use this LSP for tunneling";
    //      type empty;
    //    }
    //    container soft-preemption {
    //      presence "enable soft-preemption";
    //      description "Attempt make-before-break service while preempting this LSP";
    //      // uses apply-advanced;
    //    }
    //    list install {
    //      key name;
    //      ordered-by user;
    //      description "Install prefix";
    //      leaf name {
    //        description "Destination prefix";
    //        type jt:ipprefix;
    //      }
    //      leaf active {
    //        description "Install prefix into forwarding table";
    //        type empty;
    //      }
    //    }
    //    leaf retry-timer {
    //      description "Time before retrying the primary path";
    //      units "seconds";
    //      type union {
    //        type string {
    //          pattern "<.*>|$.*";
    //        }
    //        type uint32 {
    //          range "1 .. 600";
    //        }
    //      }
    //    }
    //    leaf retry-limit {
    //      description "Maximum number of times to retry primary path";
    //      type union {
    //        type string {
    //          pattern "<.*>|$.*";
    //        }
    //        type uint32 {
    //          range "0 .. 10000";
    //        }
    //      }
    //    }
    //    container lsp-attributes {
    //      description "Attributes for generalized LSP";
    //      // uses apply-advanced;
    //      leaf signal-bandwidth {
    //        description "Signal bandwidth for the LSP";
    //        type enumeration {
    //          enum "ds1" {
    //            description "1.544 Mbps";
    //          }
    //          enum "vt1-5" {
    //            description "1.728 Mbps";
    //          }
    //          enum "e1" {
    //            description "2.048 Mbps";
    //          }
    //          enum "vt2" {
    //            description "2.304 Mbps";
    //          }
    //          enum "ethernet" {
    //            description "10 Mbps";
    //          }
    //          enum "e3" {
    //            description "34.368 Mbps";
    //          }
    //          enum "ds3" {
    //            description "44.736 Mbps";
    //          }
    //          enum "sts-1" {
    //            description "51.84 Mbps";
    //          }
    //          enum "fastether" {
    //            description "100.00 Mbps";
    //          }
    //          enum "stm-1" {
    //            description "155.52 Mbps";
    //          }
    //          enum "stm-4" {
    //            description "622.08 Mbps";
    //          }
    //          enum "gigether" {
    //            description "1000.00 Mbps";
    //          }
    //          enum "stm-16" {
    //            description "2488.32 Mbps";
    //          }
    //          enum "stm-64" {
    //            description "9953.28 Mbps";
    //          }
    //          enum "10gigether" {
    //            description "10000.00 Mbps";
    //          }
    //          enum "stm-256" {
    //            description "39813.12 Mbps";
    //          }
    //          enum "100gige" {
    //            description "100000.00 Mbps";
    //          }
    //        }
    //      }
    //      leaf switching-type {
    //        description "LSP switching type desired";
    //        type enumeration {
    //          enum "psc-1" {
    //            description "Packet switching";
    //          }
    //          enum "lambda" {
    //            description "Lambda switching";
    //          }
    //          enum "fiber" {
    //            description "Fiber switching";
    //          }
    //          enum "tdm" {
    //            description "TDM switching";
    //          }
    //          enum "ethernet-vlan" {
    //            description "Ethernet VLAN switching";
    //          }
    //        }
    //      }
    //      leaf encoding-type {
    //        description "LSP encoding type desired";
    //        type enumeration {
    //          enum "packet" {
    //            description "Packet encoding";
    //          }
    //          enum "ethernet" {
    //            description "Ethernet encoding";
    //          }
    //          enum "pdh" {
    //            description "PDH encoding";
    //          }
    //          enum "sonet-sdh" {
    //            description "SONET-SDH encoding";
    //          }
    //        }
    //      }
    //      leaf gpid {
    //        description "Generalized PID";
    //        type enumeration {
    //          enum "ipv4" {
    //          }
    //          enum "ethernet" {
    //          }
    //          enum "ppp" {
    //          }
    //          enum "hdlc" {
    //          }
    //          enum "pos-no-scrambling-crc-16" {
    //          }
    //          enum "pos-no-scrambling-crc-32" {
    //          }
    //          enum "pos-scrambling-crc-16" {
    //          }
    //          enum "pos-scrambling-crc-32" {
    //          }
    //        }
    //      }
    //      container upstream-label {
    //        description "Upstream Label for the bidirectional label-switched path";
    //        // uses apply-advanced;
    //        leaf vlan-id {
    //          description "VLAN ID label for the label-switched path";
    //          type union {
    //            type string {
    //              pattern "<.*>|$.*";
    //            }
    //            type uint32 {
    //              range "1 .. 4094";
    //            }
    //          }
    //        }
    //      }
    //    }
    //    leaf revert-timer {
    //      description "Hold-down window before reverting back to primary path, 0 means disable";
    //      units "seconds";
    //      type union {
    //        type string {
    //          pattern "<.*>|$.*";
    //        }
    //        type int32 {
    //          range "0 .. 65535";
    //        }
    //      }
    //    }
    //    leaf optimize-hold-dead-delay {
    //      description "Delay before tearing down the old optimized path";
    //      units "seconds";
    //      type union {
    //        type string {
    //          pattern "<.*>|$.*";
    //        }
    //        type int32 {
    //          range "0 .. 65535";
    //        }
    //      }
    //    }
    //    leaf cspf-backoff-time {
    //      description "Delay before CSPF, when there is PathErr on backup path";
    //      units "seconds";
    //      type union {
    //        type string {
    //          pattern "<.*>|$.*";
    //        }
    //        type int32 {
    //          range "0 .. 65535";
    //        }
    //      }
    //    }
    //    container bandwidth {
    //      description "Bandwidth to reserve (bps)";
    //      uses bandwidth-type;
    //    }
    //    container admin-group {
    //      description "Administrative group policy";
    //      uses admin_group_include_exclude;
    //    }
    //    container admin-group-extended {
    //      description "Extended administrative group policy";
    //      uses admin_group_include_exclude;
    //    }
    //    container priority {
    //      presence "enable priority";
    //      description "Preemption priorities";
    //    }
    //    leaf setup-priority {
    //      description "Set-up priority";
    //      type union {
    //        type string {
    //          pattern "<.*>|$.*";
    //        }
    //        type uint32 {
    //          range "0 .. 7";
    //        }
    //      }
    //    }
    //    leaf reservation-priority {
    //      description "Reservation priority";
    //      type union {
    //        type string {
    //          pattern "<.*>|$.*";
    //        }
    //        type uint32 {
    //          range "0 .. 7";
    //        }
    //      }
    //    }
    //   //  container oam {
    //   //    description "Periodic OAM";
    //   //    uses periodic_oam;
    //   //  }
    //    leaf class-of-service {
    //      description "Class-of-service value";
    //      type union {
    //        type string {
    //          pattern "<.*>|$.*";
    //        }
    //        type int32 {
    //          range "0 .. 7";
    //        }
    //      }
    //    }
    //    leaf no-decrement-ttl {
    //      description "Do not decrement the TTL within an LSP";
    //      type empty;
    //    }
    //    leaf hop-limit {
    //      description "Maximum allowed router hops";
    //      type union {
    //        type string {
    //          pattern "<.*>|$.*";
    //        }
    //        type int32 {
    //          range "2 .. 255";
    //        }
    //      }
    //    }
    //    leaf no-cspf {
    //      description "Disable automatic path computation";
    //      type empty;
    //    }
    //    leaf admin-down {
    //      description "Set GMPLS LSP to administrative down state";
    //      type empty;
    //    }
    //    leaf optimize-timer {
    //      description "Periodical path reoptimizations";
    //      units "seconds";
    //      type union {
    //        type string {
    //          pattern "<.*>|$.*";
    //        }
    //        type int32 {
    //          range "0 .. 65535";
    //        }
    //      }
    //    }
    //    leaf preference {
    //      description "Preference value";
    //      type union {
    //        type uint32;
    //        type string {
    //          pattern "<.*>|$.*";
    //        }
    //      }
    //    }
    //    choice record-choice {
    //      leaf record {
    //        description "Record transit routers";
    //        type empty;
    //      }
    //      leaf no-record {
    //        description "Don't record transit routers";
    //        type empty;
    //      }
    //    }
    //    leaf standby {
    //      description "Keep backup paths in continuous standby";
    //      type empty;
    //    }
    //    leaf exclude-srlg {
    //      description "Exclude SRLG links for secondary path";
    //      type empty;
    //    }
    //    leaf ultimate-hop-popping {
    //      description "Request ultimate hop popping from egress";
    //      type empty;
    //    }
    //    leaf sync-active-path-bandwidth {
    //      description "Signal standby path with bandwidth obtained from active path";
    //      type empty;
    //    }
    //    leaf cross-credibility-cspf {
    //      description "Compute paths across multi-protocol links and nodes";
    //      type empty;
    //    }
    //    leaf top-credibility-only-cspf {
    //      description "Compute paths only using highest credibility links and nodes";
    //      type empty;
    //    }
    //    leaf entropy-label {
    //      description "Enable entropy label";
    //      type empty;
    //    }
    //    leaf self-ping-duration {
    //      description "Duration over which to run self-ping (65535 = until success). Default = 1800s";
    //      units "seconds";
    //      type union {
    //        type string {
    //          pattern "<.*>|$.*";
    //        }
    //        type int32 {
    //          range "1 .. 65535";
    //        }
    //      }
    //    }
    //    leaf no-self-ping {
    //      description "Do not run self-ping for this LSP";
    //      type empty;
    //    }
    //    choice cspf-attribute {
    //      case case_1 {
    //        leaf random {
    //          description "Randomly select among equal-cost paths";
    //          type empty;
    //        }
    //      }
    //      case case_2 {
    //        leaf least-fill {
    //          description "Select the least filled among equal-cost paths";
    //          type empty;
    //        }
    //      }
    //      case case_3 {
    //        leaf most-fill {
    //          description "Select the most filled among equal-cost paths";
    //          type empty;
    //        }
    //      }
    //    }
    //    leaf description {
    //      description "Text description of label-switched path";
    //      type string {
    //        length "1 .. 80";
    //      }
    //    }
    //    choice lp-type {
    //      case case_1 {
    //        leaf link-protection {
    //          description "Protect LSP from link faults only";
    //          type empty;
    //        }
    //      }
    //      case case_2 {
    //        leaf node-link-protection {
    //          description "Protect LSP from both link and node faults";
    //          type empty;
    //        }
    //      }
    //    }
    //    leaf intra-domain {
    //      description "Intra-domain LSP";
    //      status deprecated;
    //      type empty;
    //    }
    //    leaf inter-domain {
    //      description "Inter-domain LSP";
    //      type empty;
    //    }
    //    leaf adaptive {
    //      description "Have the LSP smoothly cut over to new routes";
    //      type empty;
    //    }
    //    container in-place-lsp-bandwidth-update {
    //      presence "enable in-place-lsp-bandwidth-update";
    //      description "Update LSP in-place re-using the same LSP identifier";
    //    }
    //    container fast-reroute {
    //      presence "enable fast-reroute";
    //      description "Fast reroute";
    //      // uses apply-advanced;
    //      leaf hop-limit {
    //        description "Maximum allowed router hops";
    //        type union {
    //          type string {
    //            pattern "<.*>|$.*";
    //          }
    //          type int32 {
    //            range "0 .. 255";
    //          }
    //        }
    //      }
    //      choice bw-attribute {
    //        case case_1 {
    //          leaf bandwidth {
    //            description "Bandwidth to reserve (bps)";
    //            type string;
    //          }
    //        }
    //        case case_2 {
    //          leaf bandwidth-percent {
    //            description "Percentage of main path bandwidth to reserve";
    //            type union {
    //              type string {
    //                pattern "<.*>|$.*";
    //              }
    //              type int32 {
    //                range "1 .. 100";
    //              }
    //            }
    //          }
    //        }
    //      }
    //      choice include_any_or_no_include_any {
    //        case case_1 {
    //          leaf no-include-any {
    //            description "Disable include-any checking";
    //            type empty;
    //          }
    //        }
    //        case case_2 {
    //          leaf-list include-any {
    //            ordered-by user;
    //            description "Groups, one or more of which must be present";
    //            type string;
    //          }
    //        }
    //      }
    //      choice include_all_or_no_include_all {
    //        case case_1 {
    //          leaf no-include-all {
    //            description "Disable include-all checking";
    //            type empty;
    //          }
    //        }
    //        case case_2 {
    //          leaf-list include-all {
    //            ordered-by user;
    //            description "Groups, all of which must be present";
    //            type string;
    //          }
    //        }
    //      }
    //      choice exclude_or_no_exclude {
    //        case case_1 {
    //          leaf no-exclude {
    //            description "Disable exclude checking";
    //            type empty;
    //          }
    //        }
    //        case case_2 {
    //          leaf-list exclude {
    //            ordered-by user;
    //            description "Groups, all of which must be absent";
    //            type string;
    //          }
    //        }
    //      }
    //    }
    //    container p2mp {
    //      presence "enable p2mp";
    //      description "Point-to-multipoint label-switched path";
    //      leaf path_name {
    //        description "Name of point-to-multipoint LSP";
    //        type string {
    //        }
    //      }
    //    }
    //    container auto-bandwidth {
    //      presence "enable auto-bandwidth";
    //      description "Do auto bandwidth allocation for this LSP";
    //      // uses apply-advanced;
    //      leaf adjust-interval {
    //        description "Time to adjust LSP bandwidth";
    //        default "86400";
    //        units "seconds";
    //        type union {
    //          type string {
    //            pattern "<.*>|$.*";
    //          }
    //          type uint32 {
    //            range "300 .. 315360000";
    //          }
    //        }
    //      }
    //      leaf adjust-threshold {
    //        description "Percentage change in average LSP utilization to trigger auto-adjustment";
    //        default "0";
    //        units "percent";
    //        type union {
    //          type string {
    //            pattern "<.*>|$.*";
    //          }
    //          type uint32 {
    //            range "0 .. 50";
    //          }
    //        }
    //      }
    //      leaf adjust-threshold-absolute {
    //        description "Change in average LSP utilization to trigger auto-adjustment";
    //        default "0";
    //        units "bps";
    //        type string;
    //      }
    //      leaf adjust-threshold-activate-bandwidth {
    //        description "Adjusts signaled bw if greater than this value";
    //        units "bps";
    //        type string;
    //      }
    //      leaf minimum-bandwidth {
    //        description "Minimum LSP bandwidth";
    //        units "bps";
    //        type string;
    //      }
    //      leaf maximum-bandwidth {
    //        description "Maximum LSP bandwidth";
    //        units "bps";
    //        type string;
    //      }
    //      leaf minimum-bandwidth-adjust-interval {
    //        description "Duration for which minimum bandwidth will be frozen";
    //        units "seconds";
    //        type union {
    //          type string {
    //            pattern "<.*>|$.*";
    //          }
    //          type uint32 {
    //            range "300 .. 31536000";
    //          }
    //        }
    //      }
    //      leaf minimum-bandwidth-adjust-threshold-change {
    //        description "Change in max average bandwidth to freeze min bandwidth";
    //        units "percent";
    //        type union {
    //          type string {
    //            pattern "<.*>|$.*";
    //          }
    //          type uint32 {
    //            range "0 .. 100";
    //          }
    //        }
    //      }
    //      leaf minimum-bandwidth-adjust-threshold-value {
    //        description "Freeze min bandwidth if max average bandwidth falls below this bw";
    //        status deprecated;
    //        units "bps";
    //        type string;
    //      }
    //      leaf monitor-bandwidth {
    //        description "Monitor LSP bandwidth without adjustments";
    //        type empty;
    //      }
    //      leaf adjust-threshold-overflow-limit {
    //        description "Number of consecutive overflow samples to trigger auto-adjustment";
    //        type union {
    //          type string {
    //            pattern "<.*>|$.*";
    //          }
    //          type uint32 {
    //            range "1 .. 65535";
    //          }
    //        }
    //      }
    //      leaf adjust-threshold-underflow-limit {
    //        description "Number of consecutive underflow samples to trigger auto-adjustment";
    //        type union {
    //          type string {
    //            pattern "<.*>|$.*";
    //          }
    //          type uint32 {
    //            range "1 .. 65535";
    //          }
    //        }
    //      }
    //      leaf resignal-minimum-bandwidth {
    //        description "Resignal the LSP using minimum-bandwidth";
    //        type empty;
    //      }
    //      leaf sync-active-path-bandwidth {
    //        description "Signal standby path with bandwidth obtained from active path";
    //        type empty;
    //      }
    //    }
    //    container optimize-on-change {
    //      description "Specify additional re-optimization triggers for this LSP";
    //      // uses apply-advanced;
    //      leaf link-congestion {
    //        description "Optimize when a link becomes congested";
    //        type empty;
    //      }
    //    }
    //    container deselect-on-bandwidth-failure {
    //      presence "enable deselect-on-bandwidth-failure";
    //      description "Deselect active path if it cannot meet the bandwidth constraint";
    //      // uses apply-advanced;
    //      leaf tear-lsp {
    //        description "Bring down active path when all paths fail to reserve required bandwidth";
    //        type empty;
    //      }
    //    }
    //    container track-igp-metric {
    //      description "Track IGP metric for LSP install prefixes";
    //      // uses apply-advanced;
    //      leaf install-v4-prefixes {
    //        description "Track IGP metric for IPV4 prefixes";
    //        type empty;
    //      }
    //      leaf install-v6-prefixes {
    //        description "Track IGP metric for IPV6 prefixes";
    //        type empty;
    //      }
    //    }
    //    container associate-lsp {
    //      description "Associate the LSP for OAM";
    //      // uses apply-advanced;
    //      leaf lsp-name {
    //        description "Name of assocation LSP";
    //        type string {
    //        }
    //      }
    //      leaf from {
    //        description "Address of ingress router of associated LSP";
    //        type jt:ipv4addr;
    //      }
    //    }
    //    list primary {
    //      key name;
    //      ordered-by user;
    //      description "Preferred path";
    //      leaf name {
    //        description "Name of path";
    //        type string {
    //          length "1 .. 64";
    //        }
    //      }
    //      // uses apply-advanced;
    //      container bandwidth {
    //        description "Bandwidth to reserve (bps)";
    //        uses bandwidth-type;
    //      }
    //      container admin-group {
    //        description "Administrative group policy";
    //        uses admin_group_include_exclude;
    //      }
    //      container admin-group-extended {
    //        description "Extended administrative group policy";
    //        uses admin_group_include_exclude;
    //      }
    //      container priority {
    //        presence "enable priority";
    //        description "Preemption priorities";
    //      }
    //      leaf setup-priority {
    //        description "Set-up priority";
    //        type union {
    //          type string {
    //            pattern "<.*>|$.*";
    //          }
    //          type uint32 {
    //            range "0 .. 7";
    //          }
    //        }
    //      }
    //      leaf reservation-priority {
    //        description "Reservation priority";
    //        type union {
    //          type string {
    //            pattern "<.*>|$.*";
    //          }
    //          type uint32 {
    //            range "0 .. 7";
    //          }
    //        }
    //      }
    //     //  container oam {
    //     //    description "Periodic OAM";
    //     //    uses periodic_oam;
    //     //  }
    //      leaf class-of-service {
    //        description "Class-of-service value";
    //        type union {
    //          type string {
    //            pattern "<.*>|$.*";
    //          }
    //          type int32 {
    //            range "0 .. 7";
    //          }
    //        }
    //      }
    //      leaf no-decrement-ttl {
    //        description "Do not decrement the TTL within an LSP";
    //        type empty;
    //      }
    //      leaf hop-limit {
    //        description "Maximum allowed router hops";
    //        type union {
    //          type string {
    //            pattern "<.*>|$.*";
    //          }
    //          type int32 {
    //            range "2 .. 255";
    //          }
    //        }
    //      }
    //      leaf no-cspf {
    //        description "Disable automatic path computation";
    //        type empty;
    //      }
    //      leaf admin-down {
    //        description "Set GMPLS LSP to administrative down state";
    //        type empty;
    //      }
    //      leaf optimize-timer {
    //        description "Periodical path reoptimizations";
    //        units "seconds";
    //        type union {
    //          type string {
    //            pattern "<.*>|$.*";
    //          }
    //          type int32 {
    //            range "0 .. 65535";
    //          }
    //        }
    //      }
    //      leaf preference {
    //        description "Preference value";
    //        type union {
    //          type uint32;
    //          type string {
    //            pattern "<.*>|$.*";
    //          }
    //        }
    //      }
    //      choice record-choice {
    //        leaf record {
    //          description "Record transit routers";
    //          type empty;
    //        }
    //        leaf no-record {
    //          description "Don't record transit routers";
    //          type empty;
    //        }
    //      }
    //      leaf standby {
    //        description "Keep backup paths in continuous standby";
    //        type empty;
    //      }
    //      leaf exclude-srlg {
    //        description "Exclude SRLG links for secondary path";
    //        type empty;
    //      }
    //      leaf ultimate-hop-popping {
    //        description "Request ultimate hop popping from egress";
    //        type empty;
    //      }
    //      leaf sync-active-path-bandwidth {
    //        description "Signal standby path with bandwidth obtained from active path";
    //        type empty;
    //      }
    //      leaf cross-credibility-cspf {
    //        description "Compute paths across multi-protocol links and nodes";
    //        type empty;
    //      }
    //      leaf top-credibility-only-cspf {
    //        description "Compute paths only using highest credibility links and nodes";
    //        type empty;
    //      }
    //      leaf adaptive {
    //        description "Have the LSP smoothly cut over to new routes";
    //        type empty;
    //      }
    //      leaf select {
    //        type enumeration {
    //          enum "manual" {
    //            description "Manual override as preferred active path, if up and stable";
    //          }
    //          enum "unconditional" {
    //            description "Unconditional override as preferred active path, regardless of up/down status";
    //          }
    //        }
    //      }
    //      container upstream-label {
    //        description "Upstream Label for the bidirectional label-switched path";
    //        // uses apply-advanced;
    //        leaf vlan-id {
    //          description "VLAN ID label for the label-switched path";
    //          type union {
    //            type string {
    //              pattern "<.*>|$.*";
    //            }
    //            type uint32 {
    //              range "1 .. 4094";
    //            }
    //          }
    //        }
    //      }
    //      container optimize-on-change {
    //        description "Specify additional re-optimization triggers for this path";
    //        // uses apply-advanced;
    //        leaf link-congestion {
    //          description "Optimize when a link becomes congested";
    //          type empty;
    //        }
    //      }
    //    }
    //    list secondary {
    //      key name;
    //      ordered-by user;
    //      description "Backup path";
    //      leaf name {
    //        description "Name of path";
    //        type string {
    //          length "1 .. 64";
    //        }
    //      }
    //      // uses apply-advanced;
    //      container bandwidth {
    //        description "Bandwidth to reserve (bps)";
    //        uses bandwidth-type;
    //      }
    //      container admin-group {
    //        description "Administrative group policy";
    //        uses admin_group_include_exclude;
    //      }
    //      container admin-group-extended {
    //        description "Extended administrative group policy";
    //        uses admin_group_include_exclude;
    //      }
    //      container priority {
    //        presence "enable priority";
    //        description "Preemption priorities";
    //      }
    //      leaf setup-priority {
    //        description "Set-up priority";
    //        type union {
    //          type string {
    //            pattern "<.*>|$.*";
    //          }
    //          type uint32 {
    //            range "0 .. 7";
    //          }
    //        }
    //      }
    //      leaf reservation-priority {
    //        description "Reservation priority";
    //        type union {
    //          type string {
    //            pattern "<.*>|$.*";
    //          }
    //          type uint32 {
    //            range "0 .. 7";
    //          }
    //        }
    //      }
    //     //  container oam {
    //     //    description "Periodic OAM";
    //     //    uses periodic_oam;
    //     //  }
    //      leaf class-of-service {
    //        description "Class-of-service value";
    //        type union {
    //          type string {
    //            pattern "<.*>|$.*";
    //          }
    //          type int32 {
    //            range "0 .. 7";
    //          }
    //        }
    //      }
    //      leaf no-decrement-ttl {
    //        description "Do not decrement the TTL within an LSP";
    //        type empty;
    //      }
    //      leaf hop-limit {
    //        description "Maximum allowed router hops";
    //        type union {
    //          type string {
    //            pattern "<.*>|$.*";
    //          }
    //          type int32 {
    //            range "2 .. 255";
    //          }
    //        }
    //      }
    //      leaf no-cspf {
    //        description "Disable automatic path computation";
    //        type empty;
    //      }
    //      leaf admin-down {
    //        description "Set GMPLS LSP to administrative down state";
    //        type empty;
    //      }
    //      leaf optimize-timer {
    //        description "Periodical path reoptimizations";
    //        units "seconds";
    //        type union {
    //          type string {
    //            pattern "<.*>|$.*";
    //          }
    //          type int32 {
    //            range "0 .. 65535";
    //          }
    //        }
    //      }
    //      leaf preference {
    //        description "Preference value";
    //        type union {
    //          type uint32;
    //          type string {
    //            pattern "<.*>|$.*";
    //          }
    //        }
    //      }
    //      choice record-choice {
    //        leaf record {
    //          description "Record transit routers";
    //          type empty;
    //        }
    //        leaf no-record {
    //          description "Don't record transit routers";
    //          type empty;
    //        }
    //      }
    //      leaf standby {
    //        description "Keep backup paths in continuous standby";
    //        type empty;
    //      }
    //      leaf exclude-srlg {
    //        description "Exclude SRLG links for secondary path";
    //        type empty;
    //      }
    //      leaf ultimate-hop-popping {
    //        description "Request ultimate hop popping from egress";
    //        type empty;
    //      }
    //      leaf sync-active-path-bandwidth {
    //        description "Signal standby path with bandwidth obtained from active path";
    //        type empty;
    //      }
    //      leaf cross-credibility-cspf {
    //        description "Compute paths across multi-protocol links and nodes";
    //        type empty;
    //      }
    //      leaf top-credibility-only-cspf {
    //        description "Compute paths only using highest credibility links and nodes";
    //        type empty;
    //      }
    //      leaf adaptive {
    //        description "Have the LSP smoothly cut over to new routes";
    //        type empty;
    //      }
    //      leaf select {
    //        type enumeration {
    //          enum "manual" {
    //            description "Manual override as preferred active path, if up and stable";
    //          }
    //          enum "unconditional" {
    //            description "Unconditional override as preferred active path, regardless of up/down status";
    //          }
    //        }
    //      }
    //      container upstream-label {
    //        description "Upstream Label for the bidirectional label-switched path";
    //        // uses apply-advanced;
    //        leaf vlan-id {
    //          description "VLAN ID label for the label-switched path";
    //          type union {
    //            type string {
    //              pattern "<.*>|$.*";
    //            }
    //            type uint32 {
    //              range "1 .. 4094";
    //            }
    //          }
    //        }
    //      }
    //      container optimize-on-change {
    //        description "Specify additional re-optimization triggers for this path";
    //        // uses apply-advanced;
    //        leaf link-congestion {
    //          description "Optimize when a link becomes congested";
    //          type empty;
    //        }
    //      }
    //      container non-active-hold-priority {
    //        description "Non-active hold priority";
    //        leaf non-active-hold-prio-value {
    //          description "Non-active hold priority value";
    //          type union {
    //            type string {
    //              pattern "<.*>|$.*";
    //            }
    //            type uint32 {
    //              range "0 .. 7";
    //            }
    //          }
    //        }
    //      }
    //    }
    //    container policing {
    //      description "Traffic policing for this LSP";
    //      leaf filter {
    //        description "Name of filter to use for policing LSP traffic";
    //        type string {
    //        }
    //      }
    //      leaf no-auto-policing {
    //        description "Turn off automatic policing for this LSP";
    //        type empty;
    //      }
    //    }
    //    container lsp-external-controller {
    //      description "External path computing entity";
    //      // uses apply-advanced;
    //      leaf ctrler_name {
    //        description "Name of the external path computing entity";
    //        type string {
    //        }
    //      }
    //      leaf te-metric-bound {
    //        description "Maximum metric value, a path can have, for the metric-type TE";
    //        type union {
    //          type string {
    //            pattern "<.*>|$.*";
    //          }
    //          type uint32 {
    //            range "1 .. 4294967295";
    //          }
    //        }
    //      }
    //      leaf igp-metric-bound {
    //        description "Maximum metric value, a path can have, for the metric-type IGP";
    //        type union {
    //          type string {
    //            pattern "<.*>|$.*";
    //          }
    //          type uint32 {
    //            range "1 .. 4294967295";
    //          }
    //        }
    //      }
    //      leaf delay-metric-bound {
    //        description "Maximum metric value, a path can have, for the metric-type delay variation";
    //        type union {
    //          type string {
    //            pattern "<.*>|$.*";
    //          }
    //          type uint32 {
    //            range "1 .. 4294967295";
    //          }
    //        }
    //      }
    //      container diversity-association {
    //        description "Configure diversity association for LSP";
    //        // uses apply-advanced;
    //        leaf-list group {
    //          ordered-by user;
    //          description "Configure diversity association group";
    //          type string;
    //          max-elements 8;
    //        }
    //        leaf shortest-path-first {
    //          description "Enable priority computation";
    //          type empty;
    //        }
    //      }
    //      container te-policy-association {
    //        description "Configure te policy association for LSP";
    //        // uses apply-advanced;
    //        leaf-list group {
    //          ordered-by user;
    //          description "Configure te policy association group";
    //          type string;
    //          max-elements 8;
    //        }
    //      }
    //    }
    //    leaf associate-backup-pe-groups {
    //      description "Associate this LSP with backup-pe groups";
    //      type empty;
    //    }
    //    leaf egress-protection {
    //      description "Use this LSP for egress protection data transport";
    //      type empty;
    //    }
    //    leaf transport-class {
    //      description "Transport class this LSP belongs to";
    //      type string {
    //      }
    //    }
    //  }
    //  container deselect-on-bandwidth-failure {
    //    presence "enable deselect-on-bandwidth-failure";
    //    description "Deselect active path if it cannot meet the bandwidth constraint";
    //    // uses apply-advanced;
    //    leaf tear-lsp {
    //      description "Bring down active path when all paths fail to reserve required bandwidth";
    //      type empty;
    //    }
    //  }
     container track-igp-metric {
       description "Track IGP metric for LSP install prefixes";
       // uses apply-advanced;
       leaf install-v4-prefixes {
         description "Track IGP metric for IPV4 prefixes";
         type empty;
       }
       leaf install-v6-prefixes {
         description "Track IGP metric for IPV6 prefixes";
         type empty;
       }
     }
     list container-label-switched-path {
       key name;
       ordered-by user;
       leaf name {
         description "Name of container-lsp";
         type string {
         }
       }
       // uses apply-advanced;
       choice enable-disable {
         case case_1 {
           leaf disable {
             description "Disable MPLS container-label-switched path";
             type empty;
           }
         }
       }
       leaf description {
         description "Text description of label-switched path";
         type string {
           length "1 .. 80";
         }
       }
       container label-switched-path-template {
         description "Template for dynamic point-to-point LSP parameters";
         // uses apply-advanced;
         choice dynamic-template {
           case case_1 {
             leaf template-name {
               description "Name of point-to-point LSP template";
               type string {
                 length "1 .. 64";
               }
             }
           }
           case case_2 {
             leaf default-template {
               description "Use default parameters";
               type empty;
             }
           }
         }
       }
       leaf to {
         description "Address of egress router";
         type jt:ipv4addr;
       }
       leaf suffix {
         description "Suffix to generate names of members of container LSP";
         type string {
           length "1 .. 64";
         }
       }
       container splitting-merging {
         description "Do splitting and merging";
         // uses apply-advanced;
         leaf maximum-member-lsps {
           description "Maximum number of LSPs";
           type union {
             type string {
               pattern "<.*>|$.*";
             }
             type int32 {
               range "1 .. 64";
             }
           }
         }
         leaf minimum-member-lsps {
           description "Minimum number of LSPs";
           type union {
             type string {
               pattern "<.*>|$.*";
             }
             type int32 {
               range "1 .. 64";
             }
           }
         }
         leaf splitting-bandwidth {
           description "Maximum bandwidth threshold for splitting";
           units "bps";
           type string;
         }
         leaf merging-bandwidth {
           description "Minimum bandwidth threshold for merging";
           units "bps";
           type string;
         }
         leaf maximum-signaling-bandwidth {
           description "Maximum bandwidth for signaling during normalization";
           units "bps";
           type string;
         }
         leaf minimum-signaling-bandwidth {
           description "Minimum bandwidth for signaling during normalization";
           units "bps";
           type string;
         }
         leaf splitting-merging-threshold {
           description "Change in aggregate LSP utilization to trigger splitting or merging";
           default "10";
           units "percent";
           type union {
             type string {
               pattern "<.*>|$.*";
             }
             type uint32 {
               range "0 .. 100";
             }
           }
         }
        //  container normalization {
        //    description "Do normalization";
        //    // uses apply-advanced;
        //    leaf normalize-interval {
        //      description "Time to normalize container LSP";
        //      default "86400";
        //      units "seconds";
        //      type union {
        //        type string {
        //          pattern "<.*>|$.*";
        //        }
        //        type uint32 {
        //          range "300 .. 315360000";
        //        }
        //      }
        //    }
        //    leaf failover-normalization {
        //      description "Do pre-mature normalization in case some LSPs go down before next normalization";
        //      type empty;
        //    }
        //    leaf no-incremental-normalize {
        //      description "Do not normalize unless all LSPs are successfully signaled";
        //      type empty;
        //    }
        //    leaf normalization-retry-duration {
        //      description "Time before retrying the container LSP normalization";
        //      units "seconds";
        //      type union {
        //        type string {
        //          pattern "<.*>|$.*";
        //        }
        //        type uint32 {
        //          range "1 .. 86400";
        //        }
        //      }
        //    }
        //    leaf normalization-retry-limits {
        //      description "Maximum number of times to retry container LSP normalization";
        //      type union {
        //        type string {
        //          pattern "<.*>|$.*";
        //        }
        //        type uint32 {
        //          range "1 .. 1000";
        //        }
        //      }
        //    }
        //    leaf no-normalize-same-members {
        //      description "Do not normalize when we are not splitting or merging member LSPs";
        //      type empty;
        //    }
        //  }
        //  container sampling {
        //    description "Sampling information";
        //    // uses apply-advanced;
        //    leaf cut-off-threshold {
        //      description "Cut-off percentile to remove outliers from aggregate samples";
        //      default "0";
        //      type union {
        //        type string {
        //          pattern "<.*>|$.*";
        //        }
        //        type uint32 {
        //          range "0 .. 100";
        //        }
        //      }
        //    }
        //    choice sampling-mode {
        //      case case_1 {
        //        leaf use-average-aggregate {
        //          description "Use average of the samples";
        //          type empty;
        //        }
        //      }
        //      case case_2 {
        //        leaf use-percentile {
        //          description "Use a percentile of the samples";
        //          default "100";
        //          type union {
        //            type string {
        //              pattern "<.*>|$.*";
        //            }
        //            type uint32 {
        //              range "0 .. 100";
        //            }
        //          }
        //        }
        //      }
        //    }
        //  }
       }
      //  container lsp-external-controller {
      //    description "External path computing entity";
      //    // uses apply-advanced;
      //    leaf ctrler_name {
      //      description "Name of the external path computing entity";
      //      type string {
      //      }
      //    }
      //    leaf te-metric-bound {
      //      description "Maximum metric value, a path can have, for the metric-type TE";
      //      type union {
      //        type string {
      //          pattern "<.*>|$.*";
      //        }
      //        type uint32 {
      //          range "1 .. 4294967295";
      //        }
      //      }
      //    }
      //    leaf igp-metric-bound {
      //      description "Maximum metric value, a path can have, for the metric-type IGP";
      //      type union {
      //        type string {
      //          pattern "<.*>|$.*";
      //        }
      //        type uint32 {
      //          range "1 .. 4294967295";
      //        }
      //      }
      //    }
      //    leaf delay-metric-bound {
      //      description "Maximum metric value, a path can have, for the metric-type delay variation";
      //      type union {
      //        type string {
      //          pattern "<.*>|$.*";
      //        }
      //        type uint32 {
      //          range "1 .. 4294967295";
      //        }
      //      }
      //    }
      //    container diversity-association {
      //      description "Configure diversity association for LSP";
      //      // uses apply-advanced;
      //      leaf-list group {
      //        ordered-by user;
      //        description "Configure diversity association group";
      //        type string;
      //        max-elements 8;
      //      }
      //      leaf shortest-path-first {
      //        description "Enable priority computation";
      //        type empty;
      //      }
      //    }
      //    container te-policy-association {
      //      description "Configure te policy association for LSP";
      //      // uses apply-advanced;
      //      leaf-list group {
      //        ordered-by user;
      //        description "Configure te policy association group";
      //        type string;
      //        max-elements 8;
      //      }
      //    }
      //  }
     }
    //  list transit-lsp-association {
    //    key name;
    //    ordered-by user;
    //    description "Transit label switch path assoication";
    //    leaf name {
    //      description "Name of transit assocation LSP group";
    //      type string {
    //      }
    //    }
    //    // uses apply-advanced;
    //    leaf lsp-name-1 {
    //      description "Name of assocation LSP 1";
    //      type string {
    //      }
    //    }
    //    leaf from-1 {
    //      description "Address of associated LSP 1";
    //      type jt:ipv4addr;
    //    }
    //    leaf lsp-name-2 {
    //      description "Name of assocation LSP 2";
    //      type string {
    //      }
    //    }
    //    leaf from-2 {
    //      description "Address of associated LSP 2";
    //      type jt:ipv4addr;
    //    }
    //  }
     list path {
       key name;
       ordered-by user;
       description "Route of a label-switched path";
       leaf name {
         description "Name of label-switched path";
         type string {
         }
       }
       // uses apply-advanced;
       list path-list {
         key name;
         ordered-by user;
         description "List of routers in the label-switched path";
         leaf name {
           description "Address of next system in path";
           type string {
           }
         }
         leaf abstract {
           description "Next system in path is abstract";
           type empty;
         }
         choice loose_strict_none {
           case case_1 {
             leaf loose {
               description "Next hop might not be adjacent";
               type empty;
             }
           }
           case case_2 {
             leaf loose-link {
               description "Next hop link might not be adjacent";
               type empty;
             }
           }
           case case_3 {
             leaf strict {
               description "Next hop must be adjacent";
               type empty;
             }
           }
         }
       }
     }
    //  list constituent-list {
    //    key name;
    //    ordered-by user;
    //    description "MPLS constituent list for abstract hops";
    //    leaf name {
    //      description "Constituent list name";
    //      type string {
    //      }
    //    }
    //    // uses apply-advanced;
    //    leaf-list srlg {
    //      ordered-by user;
    //      description "SRLG Name";
    //      type string;
    //      max-elements 16;
    //    }
    //    leaf-list admin-group {
    //      ordered-by user;
    //      description "Administrative groups";
    //      type string;
    //      max-elements 16;
    //    }
    //    leaf-list admin-group-extended {
    //      ordered-by user;
    //      description "Extended administrative groups";
    //      type string;
    //      max-elements 16;
    //    }
    //  }
    //  list abstract-hop {
    //    key name;
    //    ordered-by user;
    //    description "MPLS abstract hop";
    //    leaf name {
    //      description "Abstract hop name";
    //      type string {
    //      }
    //    }
    //    // uses apply-advanced;
    //    leaf operator {
    //      description "Operation among constituent lists";
    //      type enumeration {
    //        enum "AND" {
    //          description "AND";
    //        }
    //        enum "OR" {
    //          description "OR";
    //        }
    //      }
    //    }
    //    list constituent-list {
    //      key name;
    //      ordered-by user;
    //      description "Building abstract hop using constituent lists";
    //      leaf name {
    //        description "Constituent list name";
    //        type string {
    //          length "1 .. 64";
    //        }
    //      }
    //      // uses apply-advanced;
    //      choice list-type {
    //        case case_1 {
    //          leaf include-any-list {
    //            description "Include any";
    //            type empty;
    //          }
    //        }
    //        case case_2 {
    //          leaf include-all-list {
    //            description "Include all";
    //            type empty;
    //          }
    //        }
    //        case case_3 {
    //          leaf exclude-any-list {
    //            description "Exclude any";
    //            type empty;
    //          }
    //        }
    //        case case_4 {
    //          leaf exclude-all-list {
    //            description "Exclude all";
    //            type empty;
    //          }
    //        }
    //      }
    //    }
    //  }
    //  container egress-protection {
    //    description "Egress router protection";
    //    // uses apply-advanced;
    //    list context-identifier {
    //      key name;
    //      description "Context identifier";
    //      leaf name {
    //        description "IP address";
    //        type jt:ipv4addr;
    //      }
    //      // uses apply-advanced;
    //      choice context-type {
    //        case case_1 {
    //          leaf primary {
    //            description "Primary";
    //            type empty;
    //          }
    //        }
    //        case case_2 {
    //          leaf protector {
    //            description "Protector";
    //            type empty;
    //          }
    //        }
    //      }
    //      leaf metric {
    //        description "IGP metric";
    //        type union {
    //          type string {
    //            pattern "<.*>|$.*";
    //          }
    //          type uint32 {
    //            range "2 .. 16777215";
    //          }
    //        }
    //      }
    //      leaf advertise-mode {
    //        description "Advertise mode";
    //        type enumeration {
    //          enum "stub-proxy" {
    //            description "Proxy";
    //          }
    //          enum "stub-alias" {
    //            description "Alias";
    //          }
    //        }
    //      }
    //      leaf-list admin-group {
    //        ordered-by user;
    //        description "Administrative groups";
    //        type string;
    //      }
    //    }
    //    container traceoptions {
    //      description "Trace options for egress-protection";
    //      // uses apply-advanced;
    //      container file {
    //        description "Trace file options";
    //        leaf filename {
    //          description "Name of file in which to write trace information";
    //          type string {
    //            length "1 .. 1024";
    //          }
    //        }
    //        leaf replace {
    //          description "Replace trace file rather than appending to it";
    //          status deprecated;
    //          type empty;
    //        }
    //        leaf size {
    //          description "Maximum trace file size";
    //          type string;
    //        }
    //        leaf files {
    //          description "Maximum number of trace files";
    //          default "10";
    //          type union {
    //            type string {
    //              pattern "<.*>|$.*";
    //            }
    //            type uint32 {
    //              range "2 .. 1000";
    //            }
    //          }
    //        }
    //        leaf no-stamp {
    //          description "Do not timestamp trace file";
    //          status deprecated;
    //          type empty;
    //        }
    //        choice world-readable-choice {
    //          leaf world-readable {
    //            description "Allow any user to read the log file";
    //            type empty;
    //          }
    //          leaf no-world-readable {
    //            description "Don't allow any user to read the log file";
    //            type empty;
    //          }
    //        }
    //      }
    //      list flag {
    //        key name;
    //        ordered-by user;
    //        description "Tracing parameters";
    //        leaf name {
    //          type enumeration {
    //            enum "state" {
    //              description "Trace state transitions";
    //            }
    //            enum "route" {
    //              description "Trace route transitions";
    //            }
    //            enum "error" {
    //              description "Trace error conditions";
    //            }
    //            enum "all" {
    //              description "Trace everything";
    //            }
    //          }
    //        }
    //      }
    //    }
    //  }
     container label-range {
       description "MPLS labels ranges";
       // uses apply-advanced;
       list lsi-label-range {
         key name;
         ordered-by user;
         description "LSI-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list dynamic-label-range {
         key name;
         ordered-by user;
         description "Dynamic-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list block-label-range {
         key name;
         ordered-by user;
         description "Block-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list srgb-label-range {
         key name;
         ordered-by user;
         description "SRGB-label-range";
         max-elements 1;
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       leaf label-limit {
         description "Limit for the number of concurrent active labels";
         type union {
           type string {
             pattern "<.*>|$.*";
           }
           type uint32;
         }
       }
       list static-label-range {
         key name;
         ordered-by user;
         description "Static-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
     }
     choice enable-disable {
       case case_1 {
         leaf disable {
           description "Disable MPLS";
           type empty;
         }
       }
     }
     container label-history {
       presence "enable label-history";
       description "MPLS label history recording";
       // uses apply-advanced;
       leaf max-entries {
         description "Limit for the number of history entry per label";
         type union {
           type string {
             pattern "<.*>|$.*";
           }
           type uint32;
         }
       }
     }
    //  container traceoptions {
    //    description "Trace options for MPLS";
    //    // uses apply-advanced;
    //    container file {
    //      description "Trace file options";
    //      leaf filename {
    //        description "Name of file in which to write trace information";
    //        type string {
    //          length "1 .. 1024";
    //        }
    //      }
    //      leaf replace {
    //        description "Replace trace file rather than appending to it";
    //        status deprecated;
    //        type empty;
    //      }
    //      leaf size {
    //        description "Maximum trace file size";
    //        type string;
    //      }
    //      leaf files {
    //        description "Maximum number of trace files";
    //        default "10";
    //        type union {
    //          type string {
    //            pattern "<.*>|$.*";
    //          }
    //          type uint32 {
    //            range "2 .. 1000";
    //          }
    //        }
    //      }
    //      leaf no-stamp {
    //        description "Do not timestamp trace file";
    //        status deprecated;
    //        type empty;
    //      }
    //      choice world-readable-choice {
    //        leaf world-readable {
    //          description "Allow any user to read the log file";
    //          type empty;
    //        }
    //        leaf no-world-readable {
    //          description "Don't allow any user to read the log file";
    //          type empty;
    //        }
    //      }
    //    }
    //    list flag {
    //      key name;
    //      ordered-by user;
    //      description "Tracing parameters";
    //      leaf name {
    //        type enumeration {
    //          enum "connection" {
    //            description "Trace CCC activity";
    //          }
    //          enum "connection-detail" {
    //            description "Trace CCC activity in detail";
    //          }
    //          enum "cspf" {
    //            description "Trace CSPF computation";
    //          }
    //          enum "cspf-node" {
    //            description "Trace nodes visited during CSPF";
    //          }
    //          enum "cspf-link" {
    //            description "Trace links visited during CSPF";
    //          }
    //          enum "cspf-abstract" {
    //            description "Trace abstract hop based CSPF details";
    //          }
    //          enum "state" {
    //            description "Trace state transitions";
    //          }
    //          enum "error" {
    //            description "Trace error conditions";
    //          }
    //          enum "lsping" {
    //            description "Trace LSP ping packets received";
    //          }
    //          enum "graceful-restart" {
    //            description "Trace graceful-restart-related events";
    //          }
    //          enum "nsr-synchronization" {
    //            description "Trace NSR synchronization events";
    //          }
    //          enum "nsr-synchronization-detail" {
    //            description "Trace NSR synchronization events in detail";
    //          }
    //          enum "static" {
    //            description "Trace static label-switched path";
    //          }
    //          enum "egress-protection" {
    //            description "Trace egress protection events";
    //          }
    //          enum "all" {
    //            description "Trace everything";
    //          }
    //          enum "autobw-state" {
    //            description "Trace autobandwidth events in mpls trace";
    //          }
    //          enum "externally-controlled-lsp" {
    //            description "Trace externally controlled LSP events in mpls trace";
    //          }
    //          enum "ted-import" {
    //            description "Trace leaking TED entries into lsdist.0 table";
    //          }
    //          enum "ted-export" {
    //            description "Trace leaking of entries from lsdist.0 table into TED";
    //          }
    //          enum "lsp-history" {
    //            description "Trace LSP history events";
    //          }
    //          enum "abstract-hop" {
    //            description "Trace abstract hop related events";
    //          }
    //          enum "remote-pce" {
    //            description "Trace cPCE events in mpls trace";
    //          }
    //        }
    //      }
    //    }
    //  }
    //  leaf ipv6-tunneling {
    //    description "Allow MPLS LSPs to be used for tunneling IPv6 traffic";
    //    type empty;
    //  }
     list interface {
       key name;
       ordered-by user;
       description "MPLS interface options";
       uses juniper-protocols-mpls-interface;
     }
     list static-label-switched-path {
       key name;
       ordered-by user;
       description "Static label-switched path";
       leaf name {
         description "Name of path";
         type string {
           length "1 .. 64";
         }
       }
       // uses apply-advanced;
       choice lsp-type {
         case case_1 {
           container bypass {
             description "Bypass ingress label-switched path";
             // uses apply-advanced;
             leaf bandwidth {
               description "Bandwidth to reserve";
               units "bps";
               type string;
             }
             leaf description {
               description "Text description of label-switched path";
               type string {
                 length "1 .. 80";
               }
             }
             leaf next-hop {
               description "IPv4 or IPv6 address or interface of next-hop router";
               type union {
                 type jt:ipaddr-or-interface;
                 type string {
                   pattern "<.*>|$.*";
                 }
               }
             }
             leaf next-table {
               description "Next-table for lookup";
               type string;
             }
             leaf push {
               description "Label to push";
               type union {
                 type string {
                   pattern "<.*>|$.*";
                 }
                 type uint32 {
                   range "0 .. 1048575";
                 }
               }
             }
             leaf to {
               description "Address of egress router";
               type jt:ipaddr;
             }
           }
         }
         case case_2 {
           list transit {
             key name;
             ordered-by user;
             description "Transit label-switched path";
             leaf name {
               description "Incoming label value";
               type union {
                 type string {
                   pattern "<.*>|$.*";
                 }
                 type uint32 {
                   range "16 .. 1048575";
                 }
               }
             }
             // uses apply-advanced;
             leaf bandwidth {
               description "Bandwidth to reserve";
               units "bps";
               type string;
             }
             leaf description {
               description "Text description of label-switched path";
               type string {
                 length "1 .. 80";
               }
             }
             container link-protection {
               description "Bypass link protection";
               leaf bypass-name {
                 description "Bypass label-switched path name";
                 type string {
                   length "1 .. 64";
                 }
               }
             }
             leaf next-hop {
               description "IPv4 or IPv6 address or interface of next-hop router";
               type union {
                 type jt:ipaddr-or-interface;
                 type string {
                   pattern "<.*>|$.*";
                 }
               }
             }
             leaf member-interface {
               description "AE member interface name";
               type union {
                 type jt:interface-unit;
                 type string {
                   pattern "<.*>|$.*";
                 }
               }
             }
             container node-protection {
               description "Bypass node protection";
               leaf bypass-name {
                 description "Bypass label-switched path name";
                 type string {
                   length "1 .. 64";
                 }
               }
               leaf next-next-label {
                 description "Label expected by next-next-hop";
                 type union {
                   type string {
                     pattern "<.*>|$.*";
                   }
                   type uint32 {
                     range "0 .. 1048575";
                   }
                 }
               }
             }
             choice label-action {
               case case_1 {
                 leaf swap {
                   description "Swap top label with this label";
                   type union {
                     type string {
                       pattern "<.*>|$.*";
                     }
                     type uint32 {
                       range "0 .. 1048575";
                     }
                   }
                 }
               }
               case case_2 {
                 leaf pop {
                   description "Pop the top label";
                   type empty;
                 }
               }
               case case_3 {
                 leaf stitch {
                   description "Swap top label with the resolved LSP";
                   type empty;
                 }
               }
             }
           }
         }
         case case_3 {
           container ingress {
             description "Ingress LSR configuration for a static LSP";
             // uses apply-advanced;
             leaf bandwidth {
               description "Bandwidth to reserve";
               units "bps";
               type string;
             }
             leaf class-of-service {
               description "Class-of-service value";
               type union {
                 type string {
                   pattern "<.*>|$.*";
                 }
                 type int32 {
                   range "0 .. 7";
                 }
               }
             }
             leaf description {
               description "Text description of label-switched path";
               type string {
                 length "1 .. 80";
               }
             }
             list install {
               key name;
               ordered-by user;
               description "Install prefix";
               leaf name {
                 description "Destination prefix";
                 type jt:ipv4prefix;
               }
               leaf active {
                 description "Install prefix into forwarding table";
                 type empty;
               }
             }
             leaf metric {
               description "Metric value";
               type union {
                 type string {
                   pattern "<.*>|$.*";
                 }
                 type uint32 {
                   range "1 .. 16777215";
                 }
               }
             }
             leaf next-hop {
               description "IPv4 address or interface of next-hop router";
               type union {
                 type jt:ipv4addr-or-interface;
                 type string {
                   pattern "<.*>|$.*";
                 }
               }
             }
             container link-protection {
               description "Bypass link protection";
               leaf bypass-name {
                 description "Bypass label-switched path name";
                 type string {
                   length "1 .. 64";
                 }
               }
             }
             container node-protection {
               description "Bypass node protection";
               leaf bypass-name {
                 description "Bypass label-switched path name";
                 type string {
                   length "1 .. 64";
                 }
               }
               leaf next-next-label {
                 description "Label expected by next-next-hop";
                 type union {
                   type string {
                     pattern "<.*>|$.*";
                   }
                   type uint32 {
                     range "0 .. 1048575";
                   }
                 }
               }
             }
             leaf no-install-to-address {
               description "Don't install host route 'to' address into routing tables";
               type empty;
             }
             container policing {
               description "Traffic policing for this LSP";
               leaf filter {
                 description "Name of filter to use for policing LSP traffic";
                 type string {
                 }
               }
               leaf no-auto-policing {
                 description "Turn off automatic policing for this LSP";
                 type empty;
               }
             }
             leaf preference {
               description "Preference value";
               type union {
                 type uint32;
                 type string {
                   pattern "<.*>|$.*";
                 }
               }
             }
             leaf to {
               description "Address of egress router";
               type jt:ipv4addr;
             }
             leaf push {
               description "Label to push";
               type union {
                 type string {
                   pattern "<.*>|$.*";
                 }
                 type uint32 {
                   range "0 .. 1048575";
                 }
               }
             }
             leaf entropy-label {
               description "Enable entropy label";
               type empty;
             }
           }
         }
         case case_4 {
           container segment {
             description "Segment for segment routing";
             // uses apply-advanced;
             leaf sid-label {
               description "Segment identifier (SID) label";
               type union {
                 type string {
                   pattern "<.*>|$.*";
                 }
                 type uint32 {
                   range "16 .. 1048575";
                 }
               }
             }
             leaf description {
               description "Text description of label-switched path";
               type string {
                 length "1 .. 80";
               }
             }
             leaf next-hop {
               description "IPv4 address or interface of next-hop router";
               type union {
                 type jt:ipv4addr-or-interface;
                 type string {
                   pattern "<.*>|$.*";
                 }
               }
             }
             choice label-action {
               case case_1 {
                 leaf swap {
                   description "Swap the SID label to this label";
                   type union {
                     type string {
                       pattern "<.*>|$.*";
                     }
                     type uint32 {
                       range "0 .. 1048575";
                     }
                   }
                 }
               }
               case case_2 {
                 leaf pop {
                   description "Pop the SID label";
                   type empty;
                 }
               }
             }
           }
         }
       }
     }
   }
  //  grouping admin_group_include_exclude {
  //    // uses apply-advanced;
  //    choice include-any-choice {
  //      case case_1 {
  //        leaf-list include-any {
  //          ordered-by user;
  //          description "Groups, one or more of which must be present";
  //          type string;
  //        }
  //      }
  //    }
  //    choice include-all-choice {
  //      case case_1 {
  //        leaf-list include-all {
  //          ordered-by user;
  //          description "Groups, all of which must be present";
  //          type string;
  //        }
  //      }
  //    }
  //    choice exclude-choice {
  //      case case_1 {
  //        leaf-list exclude {
  //          ordered-by user;
  //          description "Groups, all of which must be absent";
  //          type string;
  //        }
  //      }
  //    }
  //  }
   grouping bandwidth-type {
     // uses apply-advanced;
     leaf per-traffic-class-bandwidth {
       description "Bandwidth to reserve";
       units "bps";
       type string;
     }
     leaf ct0 {
       description "Bandwidth from traffic class 0";
       units "bps";
       type string;
     }
     leaf ct1 {
       description "Bandwidth from traffic class 1";
       units "bps";
       type string;
     }
     leaf ct2 {
       description "Bandwidth from traffic class 2";
       units "bps";
       type string;
     }
     leaf ct3 {
       description "Bandwidth from traffic class 3";
       units "bps";
       type string;
     }
   }
   grouping juniper-protocols-mpls-interface {
     leaf name {
       description "Interface name";
       type union {
         type jt:interface-name;
         type string {
           pattern "<.*>|$.*";
         }
       }
     }
     // uses apply-advanced;
     choice enable-disable {
       case case_1 {
         leaf disable {
           description "Disable MPLS on this interface";
           type empty;
         }
       }
     }
     leaf-list srlg {
       ordered-by user;
       description "SRLG Name";
       type string;
       max-elements 64;
     }
     leaf always-mark-connection-protection-tlv {
       description "Mark connection protection tlv on this interface";
       type empty;
     }
     leaf switch-away-lsps {
       description "Switch away protected LSPs to their bypass LSPs";
       type empty;
     }
     leaf-list admin-group {
       ordered-by user;
       description "Administrative groups";
       type string;
     }
     leaf-list admin-group-extended {
       ordered-by user;
       description "Extended administrative groups";
       type string;
     }
     container static {
       description "Static label-switch path related configurations";
       // uses apply-advanced;
       leaf protection-revert-time {
         description "FRR revert wait time, 0 means disable";
         units "seconds";
         type union {
           type string {
             pattern "<.*>|$.*";
           }
           type uint32 {
             range "0 .. 65535";
           }
         }
       }
     }
   }
  //  grouping juniper-protocols-msdp {
  //    // uses apply-advanced;
  //    leaf data-encapsulation {
  //      description "Set encapsulation of data packets";
  //      type enumeration {
  //        enum "disable" {
  //          description "Disable data encapsulation";
  //        }
  //        enum "enable" {
  //          description "Enable data encapsulation";
  //        }
  //      }
  //    }
  //    container rib-group {
  //      description "Routing table group";
  //      uses rib_group_inet_type;
  //    }
  //    container active-source-limit {
  //      description "Limit the number of active sources accepted";
  //      // uses apply-advanced;
  //      leaf maximum {
  //        description "Maximum number of active sources accepted";
  //        default "25000";
  //        type union {
  //          type string {
  //            pattern "<.*>|$.*";
  //          }
  //          type uint32 {
  //            range "1 .. 1000000";
  //          }
  //        }
  //      }
  //      leaf threshold {
  //        description "RED threshold for active source acceptance";
  //        default "24000";
  //        type union {
  //          type string {
  //            pattern "<.*>|$.*";
  //          }
  //          type uint32 {
  //            range "1 .. 1000000";
  //          }
  //        }
  //      }
  //      leaf log-warning {
  //        description "Percentage of maximum at which to start generating warnings";
  //        default "100";
  //        type union {
  //          type string {
  //            pattern "<.*>|$.*";
  //          }
  //          type uint32 {
  //            range "1 .. 100";
  //          }
  //        }
  //      }
  //      leaf log-interval {
  //        description "Time between log messages";
  //        type union {
  //          type string {
  //            pattern "<.*>|$.*";
  //          }
  //          type uint32 {
  //            range "6 .. 32767";
  //          }
  //        }
  //      }
  //    }
  //    choice enable-disable {
  //      case case_1 {
  //        leaf disable {
  //          description "Disable MSDP";
  //          type empty;
  //        }
  //      }
  //    }
  //    leaf-list export {
  //      ordered-by user;
  //      description "Export policy";
  //      type jt:policy-algebra;
  //    }
  //    leaf-list import {
  //      ordered-by user;
  //      description "Import policy";
  //      type jt:policy-algebra;
  //    }
  //    leaf local-address {
  //      description "Local address";
  //      type jt:ipv4addr;
  //    }
  //    container traceoptions {
  //      description "Trace options for MSDP";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "packets" {
  //              description "Trace all MSDP packets";
  //            }
  //            enum "route" {
  //              description "Trace routing information";
  //            }
  //            enum "nsr-synchronization" {
  //              description "Trace NSR synchronization events";
  //            }
  //            enum "source-active" {
  //              description "Trace source-active messages";
  //            }
  //            enum "source-active-request" {
  //              description "Trace source-active request messages";
  //            }
  //            enum "source-active-response" {
  //              description "Trace source-active response messages";
  //            }
  //            enum "keepalive" {
  //              description "Trace keepalive messages";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    list peer {
  //      key name;
  //      ordered-by user;
  //      description "Configure an MSDP peer";
  //      leaf name {
  //        description "Peer address";
  //        type jt:ipv4addr;
  //      }
  //      // uses apply-advanced;
  //      choice enable-disable {
  //        case case_1 {
  //          leaf disable {
  //            description "Disable MSDP";
  //            type empty;
  //          }
  //        }
  //      }
  //      leaf-list export {
  //        ordered-by user;
  //        description "Export policy";
  //        type jt:policy-algebra;
  //      }
  //      leaf-list import {
  //        ordered-by user;
  //        description "Import policy";
  //        type jt:policy-algebra;
  //      }
  //      leaf local-address {
  //        description "Local address";
  //        type jt:ipv4addr;
  //      }
  //      container traceoptions {
  //        description "Trace options for MSDP";
  //        // uses apply-advanced;
  //        container file {
  //          description "Trace file options";
  //          leaf filename {
  //            description "Name of file in which to write trace information";
  //            type string {
  //              length "1 .. 1024";
  //            }
  //          }
  //          leaf replace {
  //            description "Replace trace file rather than appending to it";
  //            status deprecated;
  //            type empty;
  //          }
  //          leaf size {
  //            description "Maximum trace file size";
  //            type string;
  //          }
  //          leaf files {
  //            description "Maximum number of trace files";
  //            default "10";
  //            type union {
  //              type string {
  //                pattern "<.*>|$.*";
  //              }
  //              type uint32 {
  //                range "2 .. 1000";
  //              }
  //            }
  //          }
  //          leaf no-stamp {
  //            description "Do not timestamp trace file";
  //            status deprecated;
  //            type empty;
  //          }
  //          choice world-readable-choice {
  //            leaf world-readable {
  //              description "Allow any user to read the log file";
  //              type empty;
  //            }
  //            leaf no-world-readable {
  //              description "Don't allow any user to read the log file";
  //              type empty;
  //            }
  //          }
  //        }
  //        list flag {
  //          key name;
  //          ordered-by user;
  //          description "Tracing parameters";
  //          leaf name {
  //            type enumeration {
  //              enum "packets" {
  //                description "Trace all MSDP packets";
  //              }
  //              enum "route" {
  //                description "Trace routing information";
  //              }
  //              enum "nsr-synchronization" {
  //                description "Trace NSR synchronization events";
  //              }
  //              enum "source-active" {
  //                description "Trace source-active messages";
  //              }
  //              enum "source-active-request" {
  //                description "Trace source-active request messages";
  //              }
  //              enum "source-active-response" {
  //                description "Trace source-active response messages";
  //              }
  //              enum "keepalive" {
  //                description "Trace keepalive messages";
  //              }
  //              enum "normal" {
  //                description "Trace normal events";
  //              }
  //              enum "general" {
  //                description "Trace general events";
  //              }
  //              enum "state" {
  //                description "Trace state transitions";
  //              }
  //              enum "policy" {
  //                description "Trace policy processing";
  //              }
  //              enum "task" {
  //                description "Trace routing protocol task processing";
  //              }
  //              enum "timer" {
  //                description "Trace routing protocol timer processing";
  //              }
  //              enum "all" {
  //                description "Trace everything";
  //              }
  //            }
  //          }
  //          leaf send {
  //            description "Trace transmitted packets";
  //            type empty;
  //          }
  //          leaf receive {
  //            description "Trace received packets";
  //            type empty;
  //          }
  //          leaf detail {
  //            description "Trace detailed information";
  //            type empty;
  //          }
  //          leaf disable {
  //            description "Disable this trace flag";
  //            type empty;
  //          }
  //        }
  //      }
  //      container active-source-limit {
  //        description "Limit the number of active sources accepted";
  //        // uses apply-advanced;
  //        leaf maximum {
  //          description "Maximum number of active sources accepted";
  //          default "25000";
  //          type union {
  //            type string {
  //              pattern "<.*>|$.*";
  //            }
  //            type uint32 {
  //              range "1 .. 1000000";
  //            }
  //          }
  //        }
  //        leaf threshold {
  //          description "RED threshold for active source acceptance";
  //          default "24000";
  //          type union {
  //            type string {
  //              pattern "<.*>|$.*";
  //            }
  //            type uint32 {
  //              range "1 .. 1000000";
  //            }
  //          }
  //        }
  //        leaf log-warning {
  //          description "Percentage of maximum at which to start generating warnings";
  //          default "100";
  //          type union {
  //            type string {
  //              pattern "<.*>|$.*";
  //            }
  //            type uint32 {
  //              range "1 .. 100";
  //            }
  //          }
  //        }
  //        leaf log-interval {
  //          description "Time between log messages";
  //          type union {
  //            type string {
  //              pattern "<.*>|$.*";
  //            }
  //            type uint32 {
  //              range "6 .. 32767";
  //            }
  //          }
  //        }
  //      }
  //      leaf keep-alive {
  //        description "Time limit for sending out periodic keep alive to peer";
  //        units "seconds";
  //        type union {
  //          type string {
  //            pattern "<.*>|$.*";
  //          }
  //          type uint32 {
  //            range "10 .. 60";
  //          }
  //        }
  //      }
  //      leaf hold-time {
  //        description "Max time to terminating a peer for having not received any message from ";
  //        units "seconds";
  //        type union {
  //          type string {
  //            pattern "<.*>|$.*";
  //          }
  //          type uint32 {
  //            range "15 .. 150";
  //          }
  //        }
  //      }
  //      leaf sa-hold-time {
  //        description "Max time for holding a sa message before timing out";
  //        units "seconds";
  //        type union {
  //          type string {
  //            pattern "<.*>|$.*";
  //          }
  //          type uint32 {
  //            range "75 .. 300";
  //          }
  //        }
  //      }
  //      leaf default-peer {
  //        description "Default RPF peer";
  //        type empty;
  //      }
  //      leaf authentication-key {
  //        description "MD5 authentication key";
  //        type string {
  //          length "1 .. 126";
  //        }
  //      }
  //    }
  //    leaf keep-alive {
  //      description "Time limit for sending out periodic keep alive to peer";
  //      units "seconds";
  //      type union {
  //        type string {
  //          pattern "<.*>|$.*";
  //        }
  //        type uint32 {
  //          range "10 .. 60";
  //        }
  //      }
  //    }
  //    leaf hold-time {
  //      description "Max time to terminating a peer for having not received any message from ";
  //      units "seconds";
  //      type union {
  //        type string {
  //          pattern "<.*>|$.*";
  //        }
  //        type uint32 {
  //          range "15 .. 150";
  //        }
  //      }
  //    }
  //    leaf sa-hold-time {
  //      description "Max time for holding a sa message before timing out";
  //      units "seconds";
  //      type union {
  //        type string {
  //          pattern "<.*>|$.*";
  //        }
  //        type uint32 {
  //          range "75 .. 300";
  //        }
  //      }
  //    }
  //    list source {
  //      key name;
  //      ordered-by user;
  //      description "Configure parameters for each source";
  //      leaf name {
  //        description "Source address or prefix";
  //        type jt:ipprefix;
  //      }
  //      // uses apply-advanced;
  //      container active-source-limit {
  //        description "Limit the number of active sources accepted";
  //        // uses apply-advanced;
  //        leaf maximum {
  //          description "Maximum number of active sources accepted";
  //          default "25000";
  //          type union {
  //            type string {
  //              pattern "<.*>|$.*";
  //            }
  //            type uint32 {
  //              range "1 .. 1000000";
  //            }
  //          }
  //        }
  //        leaf threshold {
  //          description "RED threshold for active source acceptance";
  //          default "24000";
  //          type union {
  //            type string {
  //              pattern "<.*>|$.*";
  //            }
  //            type uint32 {
  //              range "1 .. 1000000";
  //            }
  //          }
  //        }
  //        leaf log-warning {
  //          description "Percentage of maximum at which to start generating warnings";
  //          default "100";
  //          type union {
  //            type string {
  //              pattern "<.*>|$.*";
  //            }
  //            type uint32 {
  //              range "1 .. 100";
  //            }
  //          }
  //        }
  //        leaf log-interval {
  //          description "Time between log messages";
  //          type union {
  //            type string {
  //              pattern "<.*>|$.*";
  //            }
  //            type uint32 {
  //              range "6 .. 32767";
  //            }
  //          }
  //        }
  //      }
  //    }
  //    list group {
  //      key name;
  //      ordered-by user;
  //      description "Configure MSDP peer groups";
  //      leaf name {
  //        description "MSDP peer group name";
  //        type string;
  //      }
  //      // uses apply-advanced;
  //      leaf mode {
  //        description "MSDP group source-active flooding mode";
  //        default "standard";
  //        type enumeration {
  //          enum "standard" {
  //            description "Use standard MSDP source-active flooding rules";
  //          }
  //          enum "mesh-group" {
  //            description "Group peers are mesh group members";
  //          }
  //        }
  //      }
  //      choice enable-disable {
  //        case case_1 {
  //          leaf disable {
  //            description "Disable MSDP";
  //            type empty;
  //          }
  //        }
  //      }
  //      leaf-list export {
  //        ordered-by user;
  //        description "Export policy";
  //        type jt:policy-algebra;
  //      }
  //      leaf-list import {
  //        ordered-by user;
  //        description "Import policy";
  //        type jt:policy-algebra;
  //      }
  //      leaf local-address {
  //        description "Local address";
  //        type jt:ipv4addr;
  //      }
  //      container traceoptions {
  //        description "Trace options for MSDP";
  //        // uses apply-advanced;
  //        container file {
  //          description "Trace file options";
  //          leaf filename {
  //            description "Name of file in which to write trace information";
  //            type string {
  //              length "1 .. 1024";
  //            }
  //          }
  //          leaf replace {
  //            description "Replace trace file rather than appending to it";
  //            status deprecated;
  //            type empty;
  //          }
  //          leaf size {
  //            description "Maximum trace file size";
  //            type string;
  //          }
  //          leaf files {
  //            description "Maximum number of trace files";
  //            default "10";
  //            type union {
  //              type string {
  //                pattern "<.*>|$.*";
  //              }
  //              type uint32 {
  //                range "2 .. 1000";
  //              }
  //            }
  //          }
  //          leaf no-stamp {
  //            description "Do not timestamp trace file";
  //            status deprecated;
  //            type empty;
  //          }
  //          choice world-readable-choice {
  //            leaf world-readable {
  //              description "Allow any user to read the log file";
  //              type empty;
  //            }
  //            leaf no-world-readable {
  //              description "Don't allow any user to read the log file";
  //              type empty;
  //            }
  //          }
  //        }
  //        list flag {
  //          key name;
  //          ordered-by user;
  //          description "Tracing parameters";
  //          leaf name {
  //            type enumeration {
  //              enum "packets" {
  //                description "Trace all MSDP packets";
  //              }
  //              enum "route" {
  //                description "Trace routing information";
  //              }
  //              enum "nsr-synchronization" {
  //                description "Trace NSR synchronization events";
  //              }
  //              enum "source-active" {
  //                description "Trace source-active messages";
  //              }
  //              enum "source-active-request" {
  //                description "Trace source-active request messages";
  //              }
  //              enum "source-active-response" {
  //                description "Trace source-active response messages";
  //              }
  //              enum "keepalive" {
  //                description "Trace keepalive messages";
  //              }
  //              enum "normal" {
  //                description "Trace normal events";
  //              }
  //              enum "general" {
  //                description "Trace general events";
  //              }
  //              enum "state" {
  //                description "Trace state transitions";
  //              }
  //              enum "policy" {
  //                description "Trace policy processing";
  //              }
  //              enum "task" {
  //                description "Trace routing protocol task processing";
  //              }
  //              enum "timer" {
  //                description "Trace routing protocol timer processing";
  //              }
  //              enum "all" {
  //                description "Trace everything";
  //              }
  //            }
  //          }
  //          leaf send {
  //            description "Trace transmitted packets";
  //            type empty;
  //          }
  //          leaf receive {
  //            description "Trace received packets";
  //            type empty;
  //          }
  //          leaf detail {
  //            description "Trace detailed information";
  //            type empty;
  //          }
  //          leaf disable {
  //            description "Disable this trace flag";
  //            type empty;
  //          }
  //        }
  //      }
  //      list peer {
  //        key name;
  //        ordered-by user;
  //        description "Configure an MSDP peer";
  //        leaf name {
  //          description "Peer address";
  //          type jt:ipv4addr;
  //        }
  //        // uses apply-advanced;
  //        choice enable-disable {
  //          case case_1 {
  //            leaf disable {
  //              description "Disable MSDP";
  //              type empty;
  //            }
  //          }
  //        }
  //        leaf-list export {
  //          ordered-by user;
  //          description "Export policy";
  //          type jt:policy-algebra;
  //        }
  //        leaf-list import {
  //          ordered-by user;
  //          description "Import policy";
  //          type jt:policy-algebra;
  //        }
  //        leaf local-address {
  //          description "Local address";
  //          type jt:ipv4addr;
  //        }
  //        container traceoptions {
  //          description "Trace options for MSDP";
  //          // uses apply-advanced;
  //          container file {
  //            description "Trace file options";
  //            leaf filename {
  //              description "Name of file in which to write trace information";
  //              type string {
  //                length "1 .. 1024";
  //              }
  //            }
  //            leaf replace {
  //              description "Replace trace file rather than appending to it";
  //              status deprecated;
  //              type empty;
  //            }
  //            leaf size {
  //              description "Maximum trace file size";
  //              type string;
  //            }
  //            leaf files {
  //              description "Maximum number of trace files";
  //              default "10";
  //              type union {
  //                type string {
  //                  pattern "<.*>|$.*";
  //                }
  //                type uint32 {
  //                  range "2 .. 1000";
  //                }
  //              }
  //            }
  //            leaf no-stamp {
  //              description "Do not timestamp trace file";
  //              status deprecated;
  //              type empty;
  //            }
  //            choice world-readable-choice {
  //              leaf world-readable {
  //                description "Allow any user to read the log file";
  //                type empty;
  //              }
  //              leaf no-world-readable {
  //                description "Don't allow any user to read the log file";
  //                type empty;
  //              }
  //            }
  //          }
  //          list flag {
  //            key name;
  //            ordered-by user;
  //            description "Tracing parameters";
  //            leaf name {
  //              type enumeration {
  //                enum "packets" {
  //                  description "Trace all MSDP packets";
  //                }
  //                enum "route" {
  //                  description "Trace routing information";
  //                }
  //                enum "nsr-synchronization" {
  //                  description "Trace NSR synchronization events";
  //                }
  //                enum "source-active" {
  //                  description "Trace source-active messages";
  //                }
  //                enum "source-active-request" {
  //                  description "Trace source-active request messages";
  //                }
  //                enum "source-active-response" {
  //                  description "Trace source-active response messages";
  //                }
  //                enum "keepalive" {
  //                  description "Trace keepalive messages";
  //                }
  //                enum "normal" {
  //                  description "Trace normal events";
  //                }
  //                enum "general" {
  //                  description "Trace general events";
  //                }
  //                enum "state" {
  //                  description "Trace state transitions";
  //                }
  //                enum "policy" {
  //                  description "Trace policy processing";
  //                }
  //                enum "task" {
  //                  description "Trace routing protocol task processing";
  //                }
  //                enum "timer" {
  //                  description "Trace routing protocol timer processing";
  //                }
  //                enum "all" {
  //                  description "Trace everything";
  //                }
  //              }
  //            }
  //            leaf send {
  //              description "Trace transmitted packets";
  //              type empty;
  //            }
  //            leaf receive {
  //              description "Trace received packets";
  //              type empty;
  //            }
  //            leaf detail {
  //              description "Trace detailed information";
  //              type empty;
  //            }
  //            leaf disable {
  //              description "Disable this trace flag";
  //              type empty;
  //            }
  //          }
  //        }
  //        container active-source-limit {
  //          description "Limit the number of active sources accepted";
  //          // uses apply-advanced;
  //          leaf maximum {
  //            description "Maximum number of active sources accepted";
  //            default "25000";
  //            type union {
  //              type string {
  //                pattern "<.*>|$.*";
  //              }
  //              type uint32 {
  //                range "1 .. 1000000";
  //              }
  //            }
  //          }
  //          leaf threshold {
  //            description "RED threshold for active source acceptance";
  //            default "24000";
  //            type union {
  //              type string {
  //                pattern "<.*>|$.*";
  //              }
  //              type uint32 {
  //                range "1 .. 1000000";
  //              }
  //            }
  //          }
  //          leaf log-warning {
  //            description "Percentage of maximum at which to start generating warnings";
  //            default "100";
  //            type union {
  //              type string {
  //                pattern "<.*>|$.*";
  //              }
  //              type uint32 {
  //                range "1 .. 100";
  //              }
  //            }
  //          }
  //          leaf log-interval {
  //            description "Time between log messages";
  //            type union {
  //              type string {
  //                pattern "<.*>|$.*";
  //              }
  //              type uint32 {
  //                range "6 .. 32767";
  //              }
  //            }
  //          }
  //        }
  //        leaf keep-alive {
  //          description "Time limit for sending out periodic keep alive to peer";
  //          units "seconds";
  //          type union {
  //            type string {
  //              pattern "<.*>|$.*";
  //            }
  //            type uint32 {
  //              range "10 .. 60";
  //            }
  //          }
  //        }
  //        leaf hold-time {
  //          description "Max time to terminating a peer for having not received any message from ";
  //          units "seconds";
  //          type union {
  //            type string {
  //              pattern "<.*>|$.*";
  //            }
  //            type uint32 {
  //              range "15 .. 150";
  //            }
  //          }
  //        }
  //        leaf sa-hold-time {
  //          description "Max time for holding a sa message before timing out";
  //          units "seconds";
  //          type union {
  //            type string {
  //              pattern "<.*>|$.*";
  //            }
  //            type uint32 {
  //              range "75 .. 300";
  //            }
  //          }
  //        }
  //        leaf default-peer {
  //          description "Default RPF peer";
  //          type empty;
  //        }
  //        leaf authentication-key {
  //          description "MD5 authentication key";
  //          type string {
  //            length "1 .. 126";
  //          }
  //        }
  //      }
  //    }
  //  }
  //  grouping juniper-protocols-mstp {
  //    // uses apply-advanced;
  //    choice enable-disable {
  //      case case_1 {
  //        leaf disable {
  //          description "Disable MSTP";
  //          type empty;
  //        }
  //      }
  //    }
  //    leaf bpdu-destination-mac-address {
  //      description "Destination MAC address in the spanning tree BPDUs";
  //      type enumeration {
  //        enum "provider-bridge-group" {
  //          description "802.1ad provider bridge group address";
  //        }
  //      }
  //    }
  //    leaf configuration-name {
  //      description "Configuration name (part of MST configuration identifier)";
  //      type string {
  //        length "1 .. 32";
  //      }
  //    }
  //    leaf revision-level {
  //      description "Revision level (part of MST configuration identifier)";
  //      type union {
  //        type uint16;
  //        type string {
  //          pattern "<.*>|$.*";
  //        }
  //      }
  //    }
  //    leaf max-hops {
  //      description "Maximum number of hops";
  //      type union {
  //        type string {
  //          pattern "<.*>|$.*";
  //        }
  //        type uint16 {
  //          range "1 .. 255";
  //        }
  //      }
  //    }
  //    leaf max-age {
  //      description "Maximum age of received protocol bpdu";
  //      units "seconds";
  //      type union {
  //        type string {
  //          pattern "<.*>|$.*";
  //        }
  //        type uint16 {
  //          range "6 .. 40";
  //        }
  //      }
  //    }
  //    leaf hello-time {
  //      description "Time interval between configuration BPDUs";
  //      units "seconds";
  //      type union {
  //        type string {
  //          pattern "<.*>|$.*";
  //        }
  //        type uint16 {
  //          range "1 .. 10";
  //        }
  //      }
  //    }
  //    leaf forward-delay {
  //      description "Time spent in listening or learning state";
  //      units "seconds";
  //      type union {
  //        type string {
  //          pattern "<.*>|$.*";
  //        }
  //        type uint16 {
  //          range "4 .. 30";
  //        }
  //      }
  //    }
  //    leaf system-identifier {
  //      description "Sytem identifier to represent this node";
  //      type jt:mac-unicast;
  //    }
  //    container traceoptions {
  //      description "Tracing options for debugging protocol operation";
  //      uses stp-trace-options;
  //    }
  //    leaf bridge-priority {
  //      description "Priority of the bridge (in increments of 4k - 0,4k,8k,..60k)";
  //      type string {
  //      }
  //    }
  //    leaf backup-bridge-priority {
  //      description "Priority of the bridge (in increments of 4k - 4k,8k,..60k)";
  //      type string {
  //      }
  //    }
  //    leaf bpdu-block-on-edge {
  //      description "Block BPDU on all interfaces configured as edge (BPDU Protect)";
  //      type empty;
  //    }
  //    leaf vpls-flush-on-topology-change {
  //      description "Enable VPLS MAC flush on root protected CE interface receving topology change";
  //      type empty;
  //    }
  //    leaf priority-hold-time {
  //      description "Hold time before switching to primary priority when core domain becomes up";
  //      units "seconds";
  //      type union {
  //        type string {
  //          pattern "<.*>|$.*";
  //        }
  //        type uint16 {
  //          range "1 .. 255";
  //        }
  //      }
  //    }
  //    list system-id {
  //      key name;
  //      ordered-by user;
  //      description "System ID to IP mapping";
  //      uses system-id-ip-map;
  //    }
  //    list interface {
  //      key name;
  //      description "Interface options";
  //      uses mstp-interface;
  //    }
  //    list msti {
  //      key name;
  //      description "Per-MSTI options";
  //      leaf name {
  //        type union {
  //          type string {
  //            pattern "<.*>|$.*";
  //          }
  //          type int32 {
  //            range "1 .. 64";
  //          }
  //        }
  //      }
  //      // uses apply-advanced;
  //      leaf bridge-priority {
  //        description "Priority of the bridge (in increments of 4k - 0,4k,8k,..60k)";
  //        type string {
  //        }
  //      }
  //      leaf backup-bridge-priority {
  //        description "Priority of the bridge (in increments of 4k - 4k,8k,..60k)";
  //        type string {
  //        }
  //      }
  //      leaf-list vlan {
  //        ordered-by user;
  //        description "VLAN ID or VLAN ID range [1..4094]";
  //        type string;
  //      }
  //      list interface {
  //        key name;
  //        description "Interface options";
  //        uses mstp-interface;
  //      }
  //    }
  //  }
  //  grouping juniper-protocols-mvpn {
  //    description "BGP-MVPN configuration";
  //    // uses apply-advanced;
  //    container traceoptions {
  //      description "Trace options for BGP-MVPN";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "error" {
  //              description "Trace errors";
  //            }
  //            enum "nlri" {
  //              description "Trace MVPN advertisements";
  //            }
  //            enum "topology" {
  //              description "Trace MVPN topology changes";
  //            }
  //            enum "tunnel" {
  //              description "Trace provider tunnel events";
  //            }
  //            enum "umh" {
  //              description "Trace Upstream Multicast Hop (UMH) events";
  //            }
  //            enum "intra-as-ad" {
  //              description "Trace MVPN intra-AS auto discovery routes";
  //            }
  //            enum "inter-as-ad" {
  //              description "Trace MVPN inter-AS auto discovery routes";
  //            }
  //            enum "spmsi-ad" {
  //              description "Trace MVPN SPMSI auto discovery routes";
  //            }
  //            enum "leaf-ad" {
  //              description "Trace MVPN leaf auto discovery routes";
  //            }
  //            enum "source-active" {
  //              description "Trace MVPN source active routes";
  //            }
  //            enum "cmcast-join" {
  //              description "Trace MVPN c-multicast join routes";
  //            }
  //            enum "mdt-safi-ad" {
  //              description "Trace MVPN MDT SAFI auto discovery routes";
  //            }
  //            enum "mvpn-limit" {
  //              description "Trace MVPN spmsi and cmcast limit events";
  //            }
  //            enum "nsr-synchronization" {
  //              description "Trace NSR synchronization events";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    container autodiscovery-only {
  //      description "Use MVPN exclusively for PE router autodiscovery";
  //      status deprecated;
  //      // uses apply-advanced;
  //      container intra-as {
  //        description "Intra-AS autodiscovery options";
  //        // uses apply-advanced;
  //        leaf inclusive {
  //          description "Inclusive provider tunnel autodiscovery";
  //          type empty;
  //        }
  //      }
  //    }
  //    container family {
  //      description "BGP-MVPN address family";
  //      // uses apply-advanced;
  //      container any {
  //        presence "enable any";
  //        description "BGP-MVPN properties for all families";
  //        // uses apply-advanced;
  //        leaf disable {
  //          description "Disable all families";
  //          type empty;
  //        }
  //      }
  //      container inet {
  //        description "IPv4 BGP-MVPN properties";
  //        // uses apply-advanced;
  //        container autodiscovery-only {
  //          description "Use MVPN exclusively for PE router autodiscovery";
  //          // uses apply-advanced;
  //          container intra-as {
  //            description "Intra-AS autodiscovery options";
  //            // uses apply-advanced;
  //            leaf inclusive {
  //              description "Inclusive provider tunnel autodiscovery";
  //              type empty;
  //            }
  //          }
  //        }
  //        leaf disable {
  //          description "Disable family IPv4";
  //          type empty;
  //        }
  //      }
  //      container inet6 {
  //        presence "enable inet6";
  //        description "IPv6 BGP-MVPN properties";
  //        // uses apply-advanced;
  //        container autodiscovery-only {
  //          description "Use MVPN exclusively for PE router autodiscovery";
  //          // uses apply-advanced;
  //          container intra-as {
  //            description "Intra-AS autodiscovery options";
  //            // uses apply-advanced;
  //            leaf inclusive {
  //              description "Inclusive provider tunnel autodiscovery";
  //              type empty;
  //            }
  //          }
  //        }
  //        leaf disable {
  //          description "Disable family IPv6";
  //          type empty;
  //        }
  //      }
  //    }
  //    choice sender-receiver-site-choice {
  //      case case_1 {
  //        leaf receiver-site {
  //          description "MVPN instance has sites only with multicast receivers";
  //          type empty;
  //        }
  //      }
  //      case case_2 {
  //        leaf sender-site {
  //          description "MVPN instance has sites only with multicast sources";
  //          type empty;
  //        }
  //      }
  //    }
  //    leaf unicast-umh-election {
  //      description "Upstream Multicast Hop election based on unicast route preference";
  //      type empty;
  //    }
  //    container static-umh {
  //      description "Upstream Multicast Hop election based on static configuration";
  //      // uses apply-advanced;
  //      leaf primary {
  //        description "Primary Upstream Multicast Hop";
  //        type jt:ipv4addr;
  //      }
  //      leaf backup {
  //        description "Secondary Upstream Multicast Hop";
  //        type jt:ipv4addr;
  //      }
  //      choice source-tree_choice {
  //        case case_1 {
  //          leaf source-tree {
  //            description "Mandatory attribute - static-umh applies only to MVPN source-tree c-multicast joins";
  //            type empty;
  //          }
  //        }
  //      }
  //    }
  //    leaf cmcast-joins-limit-inet {
  //      description "Maximum number of cmcast entries for v4";
  //      type union {
  //        type string {
  //          pattern "<.*>|$.*";
  //        }
  //        type uint32 {
  //          range "0 .. 15000";
  //        }
  //      }
  //    }
  //    leaf cmcast-joins-limit-inet6 {
  //      description "Maximum number of cmcast entries for v6";
  //      type union {
  //        type string {
  //          pattern "<.*>|$.*";
  //        }
  //        type uint32 {
  //          range "0 .. 15000";
  //        }
  //      }
  //    }
  //    container mvpn-mode {
  //      description "MVPN mode of operation";
  //      // uses apply-advanced;
  //      choice mode {
  //        case case_1 {
  //          container rpt-spt {
  //            presence "enable rpt-spt";
  //            description "MVPN works in multicast RPT and SPT mode";
  //            // uses apply-advanced;
  //            leaf spt-switch-timer {
  //              description "Timeout before a PE router switches between RPT and SPT";
  //              units "seconds";
  //              type union {
  //                type string {
  //                  pattern "<.*>|$.*";
  //                }
  //                type uint32 {
  //                  range "0 .. 60";
  //                }
  //              }
  //            }
  //          }
  //        }
  //        case case_2 {
  //          container spt-only {
  //            presence "enable spt-only";
  //            description "MVPN works in multicast SPT only mode (default mode)";
  //            // uses apply-advanced;
  //            container source-active-advertisement {
  //              description "Attributes associated with advertising Source-Active A-D routes";
  //              // uses apply-advanced;
  //              leaf dampen {
  //                description "Time to wait before re-advertising source-active route";
  //                units "minutes";
  //                type union {
  //                  type string {
  //                    pattern "<.*>|$.*";
  //                  }
  //                  type uint32 {
  //                    range "1 .. 30";
  //                  }
  //                }
  //              }
  //              leaf min-rate {
  //                description "Minimum traffic rate required to advertise Source-Active route";
  //                units "bits per second";
  //                type string;
  //              }
  //            }
  //            leaf convert-sa-to-msdp {
  //              description "Turn on MVPN SA route to MSDP SA conversion";
  //              type empty;
  //            }
  //          }
  //        }
  //      }
  //    }
  //    container route-target {
  //      description "Configure route-targets for MVPN routes";
  //      // uses apply-advanced;
  //      container import-target {
  //        description "Target communities used when importing routes";
  //        // uses apply-advanced;
  //        container unicast {
  //          presence "enable unicast";
  //          description "Use the same target community as configured for unicast";
  //          choice receiver-sender-target-choice {
  //            case case_1 {
  //              leaf receiver {
  //                description "Target community used when importing receiver site routes";
  //                type empty;
  //              }
  //            }
  //            case case_2 {
  //              leaf sender {
  //                description "Target community used when importing sender site routes";
  //                type empty;
  //              }
  //            }
  //          }
  //        }
  //        container target {
  //          presence "enable target";
  //          description "Target community";
  //          leaf target-value {
  //            type string {
  //            }
  //          }
  //          choice receiver-sender-target-choice {
  //            case case_1 {
  //              leaf receiver {
  //                description "Target community used when importing receiver site routes";
  //                type empty;
  //              }
  //            }
  //            case case_2 {
  //              leaf sender {
  //                description "Target community used when importing sender site routes";
  //                type empty;
  //              }
  //            }
  //          }
  //        }
  //      }
  //      container export-target {
  //        description "Target communities used when exporting routes";
  //        // uses apply-advanced;
  //        leaf unicast {
  //          description "Use the same target community as configured for unicast";
  //          type empty;
  //        }
  //        leaf target {
  //          description "Target community";
  //          type string {
  //          }
  //        }
  //      }
  //    }
  //    container mvpn-join-load-balance {
  //      description "MVPN Join Load Balancing Algorithm";
  //      // uses apply-advanced;
  //      choice algorithm {
  //        case case_1 {
  //          container bytewise-xor-hash {
  //            presence "enable bytewise-xor-hash";
  //            description "Upstream selection using bytewise XOR hash";
  //          }
  //        }
  //      }
  //    }
  //    leaf install-discard {
  //      description "Install MVPN discard forwarding entries";
  //      type empty;
  //    }
  //    leaf sender-based-rpf {
  //      description "Forward multicast traffic only from a selected sender PE";
  //      type empty;
  //    }
  //    container hot-root-standby {
  //      description "MVPN live-live - hot root standby";
  //      // uses apply-advanced;
  //      choice tree {
  //        case case_1 {
  //          container source-tree {
  //            presence "enable source-tree";
  //            description "MVPN live-live - hot root standby for source tree";
  //          }
  //        }
  //      }
  //      container min-rate {
  //        description "Minimum traffic rate for the provider tunnel below which switchover is initiated (in bps)";
  //        // uses apply-advanced;
  //        leaf rate {
  //          description "Minium traffic rate for the provider tunnel below which switchover is initiated (in bps)";
  //          units "bits per second";
  //          type string;
  //        }
  //        leaf revert-delay {
  //          description "Time to delay updating of multicast routes to allow for multicast convergence";
  //          units "seconds";
  //          type union {
  //            type string {
  //              pattern "<.*>|$.*";
  //            }
  //            type uint32 {
  //              range "0 .. 360";
  //            }
  //          }
  //        }
  //      }
  //    }
  //    leaf hierarchical-nexthop {
  //      description "Enable hierarchical nexthop usage";
  //      type empty;
  //    }
  //    leaf no-nexthop-sharing-for-selective-tunnel {
  //      description "Disable Tunnel nexthops from getting shared for selective tunnel";
  //      type empty;
  //    }
  //    container inter-region-template {
  //      description "MVPN inter-region tunnel mapping template";
  //      // uses apply-advanced;
  //      list template {
  //        key name;
  //        ordered-by user;
  //        description "Define a inter-region template";
  //        leaf name {
  //          description "MVPN Template Name";
  //          type string;
  //        }
  //        // uses apply-advanced;
  //        list region {
  //          key name;
  //          ordered-by user;
  //          description "BGP peer group names used as region";
  //          leaf name {
  //            description "Region name";
  //            type string;
  //          }
  //          // uses apply-advanced;
  //          choice tunnel-type {
  //            case case_1 {
  //              container rsvp-te {
  //                description "RSVP-TE point-to-multipoint LSP for flooding";
  //                // uses apply-advanced;
  //                choice static-or-dynamic {
  //                  case case_1 {
  //                    leaf static-lsp {
  //                      description "Name of point-to-multipoint LSP";
  //                      type string {
  //                      }
  //                    }
  //                  }
  //                  case case_2 {
  //                    container label-switched-path-template {
  //                      description "Template for dynamic point-to-multipoint LSP parameters";
  //                      // uses apply-advanced;
  //                      choice dynamic-template {
  //                        case case_1 {
  //                          leaf template-name {
  //                            description "Name of point-to-multipoint LSP template";
  //                            type string {
  //                            }
  //                          }
  //                        }
  //                        case case_2 {
  //                          leaf default-template {
  //                            description "Use default parameters";
  //                            type empty;
  //                          }
  //                        }
  //                      }
  //                    }
  //                  }
  //                }
  //              }
  //            }
  //            case case_2 {
  //              container ldp-p2mp {
  //                presence "enable ldp-p2mp";
  //                description "LDP point-to-multipoint LSP for flooding";
  //              }
  //            }
  //            case case_3 {
  //              container ingress-replication {
  //                description "Ingress replication tunnel";
  //                // uses apply-advanced;
  //                leaf create-new-ucast-tunnel {
  //                  description "Create new unicast tunnel for ingress replication";
  //                  type empty;
  //                }
  //                container label-switched-path {
  //                  presence "enable label-switched-path";
  //                  description "Point-to-point LSP unicast tunnel";
  //                  // uses apply-advanced;
  //                  container label-switched-path-template {
  //                    description "Template for dynamic point-to-point LSP parameters";
  //                    // uses apply-advanced;
  //                    choice dynamic-template {
  //                      case case_1 {
  //                        leaf template-name {
  //                          description "Name of point-to-point LSP template";
  //                          type string {
  //                          }
  //                        }
  //                      }
  //                      case case_2 {
  //                        leaf default-template {
  //                          description "Use default parameters";
  //                          type empty;
  //                        }
  //                      }
  //                    }
  //                  }
  //                }
  //              }
  //            }
  //            case case_4 {
  //              leaf incoming {
  //                description "Same as incoming provider tunnel";
  //                type empty;
  //              }
  //            }
  //          }
  //        }
  //        container all-regions {
  //          description "Used for all regions not specified";
  //          // uses apply-advanced;
  //          choice tunnel-type {
  //            case case_1 {
  //              container rsvp-te {
  //                description "RSVP-TE point-to-multipoint LSP for flooding";
  //                // uses apply-advanced;
  //                choice static-or-dynamic {
  //                  case case_1 {
  //                    leaf static-lsp {
  //                      description "Name of point-to-multipoint LSP";
  //                      type string {
  //                      }
  //                    }
  //                  }
  //                  case case_2 {
  //                    container label-switched-path-template {
  //                      description "Template for dynamic point-to-multipoint LSP parameters";
  //                      // uses apply-advanced;
  //                      choice dynamic-template {
  //                        case case_1 {
  //                          leaf template-name {
  //                            description "Name of point-to-multipoint LSP template";
  //                            type string {
  //                            }
  //                          }
  //                        }
  //                        case case_2 {
  //                          leaf default-template {
  //                            description "Use default parameters";
  //                            type empty;
  //                          }
  //                        }
  //                      }
  //                    }
  //                  }
  //                }
  //              }
  //            }
  //            case case_2 {
  //              container ldp-p2mp {
  //                presence "enable ldp-p2mp";
  //                description "LDP point-to-multipoint LSP for flooding";
  //              }
  //            }
  //            case case_3 {
  //              container ingress-replication {
  //                description "Ingress replication tunnel";
  //                // uses apply-advanced;
  //                leaf create-new-ucast-tunnel {
  //                  description "Create new unicast tunnel for ingress replication";
  //                  type empty;
  //                }
  //                container label-switched-path {
  //                  presence "enable label-switched-path";
  //                  description "Point-to-point LSP unicast tunnel";
  //                  // uses apply-advanced;
  //                  container label-switched-path-template {
  //                    description "Template for dynamic point-to-point LSP parameters";
  //                    // uses apply-advanced;
  //                    choice dynamic-template {
  //                      case case_1 {
  //                        leaf template-name {
  //                          description "Name of point-to-point LSP template";
  //                          type string {
  //                          }
  //                        }
  //                      }
  //                      case case_2 {
  //                        leaf default-template {
  //                          description "Use default parameters";
  //                          type empty;
  //                        }
  //                      }
  //                    }
  //                  }
  //                }
  //              }
  //            }
  //            case case_4 {
  //              leaf incoming {
  //                description "Same as incoming provider tunnel";
  //                type empty;
  //              }
  //            }
  //          }
  //        }
  //      }
  //    }
  //    leaf source-redundancy {
  //      description "Assume all the sources for a particular group is sending same data";
  //      type empty;
  //    }
  //    container umh-selection-additional-input {
  //      description "Additional parameters to consider during UMH";
  //      // uses apply-advanced;
  //      leaf source-active-preference {
  //        description "Use the preference set in the source active route";
  //        type empty;
  //      }
  //      leaf tunnel-status {
  //        description "Use the RSVP tunnel status";
  //        type empty;
  //      }
  //    }
  //  }
  //  grouping juniper-protocols-mvrp {
  //    description "MVRP Configuration";
  //    // uses apply-advanced;
  //    container traceoptions {
  //      description "Tracing options for MVRP";
  //      uses mrp-trace-options;
  //    }
  //    leaf join-timer {
  //      description "Join timer interval";
  //      default "200";
  //      units "milliseconds";
  //      type union {
  //        type string {
  //          pattern "<.*>|$.*";
  //        }
  //        type uint16 {
  //          range "100 .. 500";
  //        }
  //      }
  //    }
  //    leaf leave-timer {
  //      description "Leave timer interval";
  //      default "800";
  //      units "milliseconds";
  //      type union {
  //        type string {
  //          pattern "<.*>|$.*";
  //        }
  //        type uint16 {
  //          range "300 .. 1000";
  //        }
  //      }
  //    }
  //    leaf leaveall-timer {
  //      description "Leaveall timer interval";
  //      default "10";
  //      units "seconds";
  //      type union {
  //        type string {
  //          pattern "<.*>|$.*";
  //        }
  //        type uint16 {
  //          range "10 .. 60";
  //        }
  //      }
  //    }
  //    leaf no-dynamic-vlan {
  //      description "Disable dynamic VLAN creation";
  //      type empty;
  //    }
  //    leaf no-attribute-length-in-pdu {
  //      description "No attribute length while sending pdu ";
  //      type empty;
  //    }
  //    leaf bpdu-destination-mac-address {
  //      description "Destination MAC address in the MVRP BPDUs";
  //      type enumeration {
  //        enum "provider-bridge-group" {
  //          description "802.1ad provider bridge group address";
  //        }
  //      }
  //    }
  //    list interface {
  //      key name;
  //      ordered-by user;
  //      description "Configure interface options";
  //      leaf name {
  //        description "Interface name";
  //        type union {
  //          type jt:interface-device;
  //          type string {
  //            pattern "<.*>|$.*";
  //          }
  //        }
  //      }
  //      // uses apply-advanced;
  //      leaf join-timer {
  //        description "Join timer interval";
  //        units "milliseconds";
  //        type union {
  //          type string {
  //            pattern "<.*>|$.*";
  //          }
  //          type uint16 {
  //            range "100 .. 500";
  //          }
  //        }
  //      }
  //      leaf leave-timer {
  //        description "Leave timer interval";
  //        units "milliseconds";
  //        type union {
  //          type string {
  //            pattern "<.*>|$.*";
  //          }
  //          type uint16 {
  //            range "300 .. 1000";
  //          }
  //        }
  //      }
  //      leaf leaveall-timer {
  //        description "Leaveall timer interval";
  //        units "seconds";
  //        type union {
  //          type string {
  //            pattern "<.*>|$.*";
  //          }
  //          type uint16 {
  //            range "10 .. 60";
  //          }
  //        }
  //      }
  //      leaf point-to-point {
  //        description "Port is point to point";
  //        type empty;
  //      }
  //      leaf registration {
  //        description "Registration mode";
  //        default "normal";
  //        type enumeration {
  //          enum "normal" {
  //            description "Normal registration mode";
  //          }
  //          enum "restricted" {
  //            description "Restricted registration mode";
  //          }
  //          enum "forbidden" {
  //            description "Forbidden registration mode";
  //          }
  //        }
  //      }
  //    }
  //  }
   grouping juniper-protocols-ospf {
     // uses apply-advanced;
     list topology {
       key name;
       ordered-by user;
       description "Topology parameters";
       leaf name {
         description "Topology name";
         type string;
       }
       // uses apply-advanced;
       leaf disable {
         description "Disable this topology";
         type empty;
       }
       leaf topology-id {
         description "Topology identifier";
         type union {
           type string {
             pattern "<.*>|$.*";
           }
           type uint8 {
             range "32 .. 127";
           }
         }
       }
       leaf overload {
         description "Set the overload mode (repel transit traffic)";
         type empty;
       }
       leaf rib-group {
         description "Routing table group for importing routes";
         type string;
       }
       container spf-options {
         description "Configure options for SPF";
         // uses apply-advanced;
         container microloop-avoidance {
           description "Configure microloop avoidance mechanism";
           // uses apply-advanced;
           container post-convergence-path {
             presence "enable post-convergence-path";
             description "Temporarily install post-convergence path for routes potentially affected by microloops";
             // uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Maximum number of labels installed for post-convergence paths";
               type union {
                 type string {
                   pattern "<.*>|$.*";
                 }
                 type uint32 {
                   range "2 .. 8";
                 }
               }
             }
           }
         }
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
       }
       container backup-spf-options {
         description "Configure options for backup SPF";
         // uses apply-advanced;
         container remote-backup-calculation {
           presence "enable remote-backup-calculation";
           description "Calculate Remote LFA backup nexthops";
           // uses apply-advanced;
           container pq-nodes-nearest-to-source {
             description "PQ nodes selection based upon nearest to source";
             // uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           description "Calculate post-convergence backup paths";
           // uses apply-advanced;
           leaf maximum-labels {
             description "Maximum number of labels installed for post-convergence paths";
             type union {
               type string {
                 pattern "<.*>|$.*";
               }
               type uint32 {
                 range "2 .. 8";
               }
             }
           }
           leaf maximum-backup-paths {
             description "Maximum number of equal-cost post-convergence paths installed";
             type union {
               type string {
                 pattern "<.*>|$.*";
               }
               type uint32 {
                 range "1 .. 8";
               }
             }
           }
         }
         leaf use-source-packet-routing {
           description "Use spring backup paths for inet.0 routes";
           type empty;
         }
         leaf disable {
           description "Do not run backup SPF";
           type empty;
         }
         leaf no-install {
           description "Do not install backup nexthops into the RIB";
           type empty;
         }
         leaf downstream-paths-only {
           description "Use only downstream backup paths";
           type empty;
         }
         container per-prefix-calculation {
           description "Calculate backup nexthops for non-best prefix originators";
           // uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           type empty;
         }
       }
       leaf prefix-export-limit {
         description "Maximum number of prefixes that can be exported";
         type union {
           type string {
             pattern "<.*>|$.*";
           }
           type uint32 {
             range "0 .. 4294967295";
           }
         }
       }
     }
     container spf-options {
       description "Configure options for SPF";
       // uses apply-advanced;
       container microloop-avoidance {
         description "Configure microloop avoidance mechanism";
         // uses apply-advanced;
         container post-convergence-path {
           presence "enable post-convergence-path";
           description "Temporarily install post-convergence path for routes potentially affected by microloops";
           // uses apply-advanced;
           leaf delay {
             description "Time after which temporary post-convergence paths are removed";
             units "milliseconds";
             type union {
               type string {
                 pattern "<.*>|$.*";
               }
               type uint32 {
                 range "500 .. 60000";
               }
             }
           }
           leaf maximum-labels {
             description "Maximum number of labels installed for post-convergence paths";
             type union {
               type string {
                 pattern "<.*>|$.*";
               }
               type uint32 {
                 range "2 .. 8";
               }
             }
           }
         }
       }
       leaf delay {
         description "Time to wait before running an SPF";
         units "milliseconds";
         type union {
           type string {
             pattern "<.*>|$.*";
           }
           type uint32 {
             range "50 .. 8000";
           }
         }
       }
       leaf holddown {
         description "Time to hold down before running an SPF";
         units "milliseconds";
         type union {
           type string {
             pattern "<.*>|$.*";
           }
           type uint32 {
             range "2000 .. 20000";
           }
         }
       }
       leaf rapid-runs {
         description "Number of maximum rapid SPF runs before holddown";
         type union {
           type string {
             pattern "<.*>|$.*";
           }
           type uint32 {
             range "1 .. 10";
           }
         }
       }
       leaf no-ignore-our-externals {
         description "Do not ignore self-generated external and NSSA LSAs";
         type empty;
       }
     }
     container backup-spf-options {
       description "Configure options for backup SPF";
       // uses apply-advanced;
       container remote-backup-calculation {
         presence "enable remote-backup-calculation";
         description "Calculate Remote LFA backup nexthops";
         // uses apply-advanced;
         container pq-nodes-nearest-to-source {
           description "PQ nodes selection based upon nearest to source";
           // uses apply-advanced;
           leaf percent {
             description "Selection percentage for nearest to source";
             type union {
               type string {
                 pattern "<.*>|$.*";
               }
               type uint32 {
                 range "10 .. 100";
               }
             }
           }
         }
       }
       container use-post-convergence-lfa {
         presence "enable use-post-convergence-lfa";
         description "Calculate post-convergence backup paths";
         // uses apply-advanced;
         leaf maximum-labels {
           description "Maximum number of labels installed for post-convergence paths";
           type union {
             type string {
               pattern "<.*>|$.*";
             }
             type uint32 {
               range "2 .. 8";
             }
           }
         }
         leaf maximum-backup-paths {
           description "Maximum number of equal-cost post-convergence paths installed";
           type union {
             type string {
               pattern "<.*>|$.*";
             }
             type uint32 {
               range "1 .. 8";
             }
           }
         }
       }
       leaf use-source-packet-routing {
         description "Use spring backup paths for inet.0 routes";
         type empty;
       }
       leaf disable {
         description "Do not run backup SPF";
         type empty;
       }
       leaf no-install {
         description "Do not install backup nexthops into the RIB";
         type empty;
       }
       leaf downstream-paths-only {
         description "Use only downstream backup paths";
         type empty;
       }
       container per-prefix-calculation {
         description "Calculate backup nexthops for non-best prefix originators";
         // uses apply-advanced;
         leaf stubs {
           description "Per prefix calculation for stubs only";
           type empty;
         }
         leaf summary {
           description "Per prefix calculation for summary originators only";
           type empty;
         }
         leaf externals {
           description "Per prefix calculation for externals";
           type empty;
         }
         leaf all {
           description "Per prefix calculation for all";
           type empty;
         }
       }
       leaf node-link-degradation {
         description "Degrade to link protection when nodelink protection not available";
         type empty;
       }
     }
     container traffic-engineering {
       presence "enable traffic-engineering";
       description "Configure traffic engineering attributes";
       // uses apply-advanced;
       leaf no-topology {
         description "Disable dissemination of TE link-state topology information";
         type empty;
       }
       leaf multicast-rpf-routes {
         description "Install routes for multicast RPF checks into inet.2";
         type empty;
       }
       leaf l3-unicast-topology {
         description "Download IGP topology into TED";
         type empty;
       }
       container ignore-lsp-metrics {
         presence "enable ignore-lsp-metrics";
         description "Ignore label-switched path metrics when doing shortcuts";
         // uses apply-advanced;
         leaf unconfigured-only {
           description "Ignore lsp metrics for unconfigured only";
           type empty;
         }
       }
       container shortcuts {
         presence "enable shortcuts";
         description "Use label-switched paths as next hops, if possible";
         // uses apply-advanced;
         leaf ignore-lsp-metrics {
           description "Ignore label-switched path metrics when doing shortcuts";
           status deprecated;
           type empty;
         }
         leaf lsp-metric-into-summary {
           description "Advertise LSP metric into summary LSAs";
           type empty;
         }
         list family {
           key name;
           ordered-by user;
           description "Address family specific traffic-engineering attributes";
           leaf name {
             type enumeration {
               enum "inet" {
                 description "IPv4 family";
               }
               enum "inet-mpls" {
                 description "IPv4-MPLS family";
               }
             }
           }
           // uses apply-advanced;
         }
       }
       leaf advertise-unnumbered-interfaces {
         description "Advertise unnumbered interfaces";
         type empty;
       }
       leaf credibility-protocol-preference {
         description "TED protocol credibility follows protocol preference";
         type empty;
       }
       container advertisement {
         description "Advertise TE parameters even if RSVP is not turned on";
         // uses apply-advanced;
         leaf always {
           description "Advertise TE parameters in TE LSAs";
           type empty;
         }
       }
       container tunnel-source-protocol {
         description "Protocols from which to pick label-switched paths";
         // uses apply-advanced;
         container rsvp {
           presence "enable rsvp";
           description "Pick label-switched paths from rsvp";
           // uses apply-advanced;
           leaf preference {
             description "Preference for label-switched paths from this protocol";
             type union {
               type string {
                 pattern "<.*>|$.*";
               }
               type uint32 {
                 range "1 .. 255";
               }
             }
           }
         }
         container spring-te {
           presence "enable spring-te";
           description "Pick label-switched paths from spring-te";
           // uses apply-advanced;
           leaf preference {
             description "Preference for label-switched paths from this protocol";
             type union {
               type string {
                 pattern "<.*>|$.*";
               }
               type uint32 {
                 range "1 .. 255";
               }
             }
           }
         }
       }
     }
    //  container source-packet-routing {
    //    presence "enable source-packet-routing";
    //    description "Enable source packet routing (SPRING)";
    //    // uses apply-advanced;
    //    container adjacency-segment {
    //      description "Attributes for adjacency segments in spring";
    //      // uses apply-advanced;
    //      leaf hold-time {
    //        description "Retain time of Adjacency segment after isolating from an interface";
    //        type union {
    //          type string {
    //            pattern "<.*>|$.*";
    //          }
    //          type uint32 {
    //            range "180000 .. 900000";
    //          }
    //        }
    //      }
    //    }
    //    leaf-list prefix-segment {
    //      ordered-by user;
    //      description "Prefix Segment policy";
    //      type jt:policy-algebra;
    //    }
    //    leaf explicit-null {
    //      description "Set E and P bits in all Prefix SID advertisements";
    //      type empty;
    //    }
    //    container node-segment {
    //      presence "enable node-segment";
    //      description "Enable support for Node segments in SPRING";
    //      // uses apply-advanced;
    //      leaf ipv4-index {
    //        description "Set ipv4 node segment index";
    //        type union {
    //          type string {
    //            pattern "<.*>|$.*";
    //          }
    //          type uint32 {
    //            range "0 .. 199999";
    //          }
    //        }
    //      }
    //      leaf index-range {
    //        description "Set range of node segment indices allowed";
    //        type union {
    //          type string {
    //            pattern "<.*>|$.*";
    //          }
    //          type uint32 {
    //            range "32 .. 16385";
    //          }
    //        }
    //      }
    //    }
    //    container srgb {
    //      description "Set the SRGB global block in SPRING";
    //      leaf start-label {
    //        description "Start range for SRGB label block";
    //        type union {
    //          type string {
    //            pattern "<.*>|$.*";
    //          }
    //          type uint32;
    //        }
    //      }
    //      leaf index-range {
    //        description "Index to the SRGB start label block";
    //        type union {
    //          type string {
    //            pattern "<.*>|$.*";
    //          }
    //          type uint32;
    //        }
    //      }
    //    }
    //    leaf mapping-server {
    //      description "Mapping server name";
    //      type string;
    //    }
    //    leaf install-prefix-sid-for-best-route {
    //      description "For best route install a exact prefix sid route";
    //      type empty;
    //    }
    //    leaf ldp-stitching {
    //      description "Enable SR to LDP stitching";
    //      type empty;
    //    }
    //    leaf-list flex-algorithm {
    //      description "Flex-algorithms we would like to participate in";
    //      type union {
    //        type string {
    //          pattern "<.*>|$.*";
    //        }
    //        type uint32 {
    //          range "128 .. 255";
    //        }
    //      }
    //      max-elements 16;
    //    }
    //    leaf strict-asla-based-flex-algorithm {
    //      description "Flex-Algorithm to ignore links not having ASLA sub-TLVs";
    //      type empty;
    //    }
    //    container sensor-based-stats {
    //      description "Configure sensor based stats in SPRING";
    //      // uses apply-advanced;
    //      container per-interface-per-member-link {
    //        description "Configure sensor based stats per nexthop";
    //        leaf ingress {
    //          description "Enable sensor based stats on ingress interface";
    //          type empty;
    //        }
    //        leaf egress {
    //          description "Enable sensor based stats on egress interface";
    //          type empty;
    //        }
    //      }
    //      container per-sid {
    //        description "Configure sensor based stats per spring route";
    //        leaf ingress {
    //          description "Enable sensor based stats for per-sid ingress accounting";
    //          type empty;
    //        }
    //        leaf egress {
    //          description "Enable sensor based stats for IP-MPLS egress accounting";
    //          type empty;
    //        }
    //      }
    //    }
    //  }
     list area {
       key name;
       ordered-by user;
       description "Configure an OSPF area";
       leaf name {
         description "Area ID";
         type jt:areaid;
       }
       // uses apply-advanced;
       choice stub-option {
         case case_1 {
           container stub {
             presence "enable stub";
             description "Configure a stub area";
             leaf default-metric {
               description "Metric for the default route in this stub area";
               type union {
                 type string {
                   pattern "<.*>|$.*";
                 }
                 type uint32 {
                   range "1 .. 16777215";
                 }
               }
             }
             choice summaries-choice {
               leaf summaries {
                 description "Flood summary LSAs into this stub area";
                 type empty;
               }
               leaf no-summaries {
                 description "Don't flood summary LSAs into this stub area";
                 type empty;
               }
             }
           }
         }
         case case_2 {
           container nssa {
             presence "enable nssa";
             description "Configure a not-so-stubby area";
             // uses apply-advanced;
             container default-lsa {
               presence "enable default-lsa";
               description "Configure a default LSA";
               // uses apply-advanced;
               leaf default-metric {
                 description "Metric for the default route in this area";
                 type union {
                   type string {
                     pattern "<.*>|$.*";
                   }
                   type uint32 {
                     range "1 .. 16777215";
                   }
                 }
               }
               leaf metric-type {
                 description "External metric type for the default type 7 LSA";
                 type union {
                   type string {
                     pattern "<.*>|$.*";
                   }
                   type uint32 {
                     range "1 .. 2";
                   }
                 }
               }
               leaf type-7 {
                 description "Flood type 7 default LSA if no-summaries is configured";
                 type empty;
               }
             }
             leaf default-metric {
               description "Metric for the default route in this area";
               status deprecated;
               type union {
                 type string {
                   pattern "<.*>|$.*";
                 }
                 type uint32 {
                   range "1 .. 16777215";
                 }
               }
             }
             leaf metric-type {
               description "External metric type for the default type 7 LSA";
               status deprecated;
               type union {
                 type string {
                   pattern "<.*>|$.*";
                 }
                 type uint32 {
                   range "1 .. 2";
                 }
               }
             }
             choice summaries-choice {
               leaf summaries {
                 description "Flood summary LSAs into this NSSA area";
                 type empty;
               }
               leaf no-summaries {
                 description "Don't flood summary LSAs into this NSSA area";
                 type empty;
               }
             }
             list area-range {
               key name;
               ordered-by user;
               description "Configure NSSA area ranges";
               leaf name {
                 description "Range to summarize NSSA routes in this area";
                 type jt:ipprefix;
               }
               // uses apply-advanced;
               leaf restrict {
                 description "Restrict advertisement of this area range";
                 type empty;
               }
               leaf exact {
                 description "Enforce exact match for advertisement of this area range";
                 type empty;
               }
               container override-metric {
                 presence "enable override-metric";
                 description "Override the dynamic metric for this area-range";
                 // uses apply-advanced;
                 leaf metric {
                   description "Metric value";
                   type union {
                     type string {
                       pattern "<.*>|$.*";
                     }
                     type uint32 {
                       range "1 .. 16777215";
                     }
                   }
                 }
                 leaf metric-type {
                   description "Set the metric type for the override metric";
                   default "1";
                   type union {
                     type string {
                       pattern "<.*>|$.*";
                     }
                     type uint32 {
                       range "1 .. 2";
                     }
                   }
                 }
               }
             }
           }
         }
       }
       list area-range {
         key name;
         ordered-by user;
         description "Configure area ranges";
         leaf name {
           description "Range to summarize routes in this area";
           type jt:ipprefix;
         }
         // uses apply-advanced;
         leaf restrict {
           description "Restrict advertisement of this area range";
           type empty;
         }
         leaf exact {
           description "Enforce exact match for advertisement of this area range";
           type empty;
         }
         leaf override-metric {
           description "Override the dynamic metric for this area-range";
           type union {
             type string {
               pattern "<.*>|$.*";
             }
             type uint32 {
               range "1 .. 16777215";
             }
           }
         }
       }
       leaf-list network-summary-export {
         ordered-by user;
         description "Export policy for Type 3 Summary LSAs";
         type jt:policy-algebra;
       }
       leaf-list network-summary-import {
         ordered-by user;
         description "Import policy for Type 3 Summary LSAs";
         type jt:policy-algebra;
       }
       leaf-list inter-area-prefix-export {
         ordered-by user;
         description "Export policy for Inter Area Prefix LSAs";
         type jt:policy-algebra;
       }
       leaf-list inter-area-prefix-import {
         ordered-by user;
         description "Import policy for Inter Area Prefix LSAs";
         type jt:policy-algebra;
       }
       leaf authentication-type {
         description "Authentication type";
         status deprecated;
         type enumeration {
           enum "none" {
             description "No authentication";
             status deprecated;
           }
           enum "simple" {
             description "Simple password authentication";
             status deprecated;
           }
           enum "md5" {
             description "MD5 authentication";
             status deprecated;
           }
         }
       }
       list virtual-link {
         key "neighbor-id transit-area";
         ordered-by user;
         description "Configure virtual links";
         leaf neighbor-id {
           description "Router ID of a virtual neighbor";
           type jt:ipv4addr;
         }
         leaf transit-area {
           description "Transit area in common with virtual neighbor";
           type jt:areaid;
         }
         // uses apply-advanced;
         choice enable-disable {
           case case_1 {
             leaf disable {
               description "Disable this virtual link";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
        //  choice auth {
        //    case case_1 {
        //      container authentication {
        //        uses juniper-ospf-authentication;
        //      }
        //    }
        //    case case_2 {
        //      container authentication-key {
        //        description "Authentication key";
        //        status deprecated;
        //        leaf keyname {
        //          description "Authentication key value";
        //          type jt:unreadable;
        //        }
        //        leaf key-id {
        //          description "Key ID for MD5 authentication";
        //          type union {
        //            type string {
        //              pattern "<.*>|$.*";
        //            }
        //            type uint32 {
        //              range "0 .. 255";
        //            }
        //          }
        //        }
        //      }
        //    }
        //  }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           type string {
             length "1 .. 32";
           }
         }
         list topology {
           key name;
           ordered-by user;
           description "Topology specific attributes";
           leaf name {
             description "Topology name";
             type string;
           }
           // uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             // uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
      //  list sham-link-remote {
      //    key name;
      //    ordered-by user;
      //    description "Configure parameters for remote sham link endpoint";
      //    leaf name {
      //      description "Remote sham link endpoint address";
      //      type jt:ipaddr;
      //    }
      //    // uses apply-advanced;
      //    leaf metric {
      //      description "Sham link metric";
      //      type union {
      //        type string {
      //          pattern "<.*>|$.*";
      //        }
      //        type uint16 {
      //          range "1 .. 65535";
      //        }
      //      }
      //    }
      //    leaf ipsec-sa {
      //      description "IPSec security association name";
      //      type string {
      //        length "1 .. 32";
      //      }
      //    }
      //    leaf demand-circuit {
      //      description "Interface functions as a demand circuit";
      //      type empty;
      //    }
      //    leaf flood-reduction {
      //      description "Enable flood reduction";
      //      type empty;
      //    }
      //    list topology {
      //      key name;
      //      ordered-by user;
      //      description "Topology specific attributes";
      //      leaf name {
      //        description "Topology name";
      //        type string;
      //      }
      //      // uses apply-advanced;
      //      leaf disable {
      //        description "Disable this topology";
      //        type empty;
      //      }
      //      leaf metric {
      //        description "Topology metric";
      //        type union {
      //          type string {
      //            pattern "<.*>|$.*";
      //          }
      //          type uint16 {
      //            range "1 .. 65535";
      //          }
      //        }
      //      }
      //      container bandwidth-based-metrics {
      //        description "Configure bandwidth based metrics";
      //        // uses apply-advanced;
      //        list bandwidth {
      //          key name;
      //          description "Bandwidth threshold";
      //          leaf name {
      //            type string;
      //          }
      //          leaf metric {
      //            description "Metric associated with specified bandwidth";
      //            type union {
      //              type string {
      //                pattern "<.*>|$.*";
      //              }
      //              type uint16 {
      //                range "1 .. 65535";
      //              }
      //            }
      //          }
      //        }
      //      }
      //    }
      //  }
       list interface {
         key name;
         ordered-by user;
         description "Include an interface in this area";
         leaf name {
           description "Interface name";
           type union {
             type jt:ipv4addr-or-interface;
             type string {
               pattern "<.*>|$.*";
             }
           }
         }
         // uses apply-advanced;
         choice enable-disable {
           case case_1 {
             leaf disable {
               description "Disable OSPF on this interface";
               type empty;
             }
           }
         }
         leaf interface-type {
           description "Type of interface";
           type enumeration {
             enum "nbma" {
               description "Nonbroadcast multiaccess";
             }
             enum "p2mp" {
               description "Point-to-multipoint NBMA";
             }
             enum "p2p" {
               description "Point-to-point";
             }
             enum "p2mp-over-lan" {
               description "Point-to-multipoint over LAN mode";
             }
           }
         }
         choice protection-type {
           case case_1 {
             leaf link-protection {
               description "Protect interface from link faults only";
               type empty;
             }
           }
           case case_2 {
             leaf node-link-protection {
               description "Protect interface from both link and node faults";
               type empty;
             }
           }
         }
         leaf no-eligible-backup {
           description "Not eligible to backup traffic from protected interfaces";
           type empty;
         }
         leaf no-eligible-remote-backup {
           description "Not eligible for Remote-LFA backup traffic from protected interfaces";
           type empty;
         }
         container passive {
           presence "enable passive";
           description "Do not run OSPF, but advertise it";
           // uses apply-advanced;
           container traffic-engineering {
             description "Advertise TE link information";
             // uses apply-advanced;
             leaf remote-node-id {
               description "Remote address of the link";
               type jt:ipaddr;
             }
             leaf remote-node-router-id {
               description "TE Router-ID of the remote node";
               type jt:ipv4addr;
             }
           }
         }
         leaf secondary {
           description "Treat interface as secondary";
           type empty;
         }
         leaf own-router-lsa {
           description "Generate a separate router LSA for this interface";
           type empty;
         }
         container bandwidth-based-metrics {
           description "Configure bandwidth based metrics";
           // uses apply-advanced;
           list bandwidth {
             key name;
             description "Bandwidth threshold";
             leaf name {
               type string;
             }
             leaf metric {
               description "Metric associated with specified bandwidth";
               type union {
                 type string {
                   pattern "<.*>|$.*";
                 }
                 type uint16 {
                   range "1 .. 65535";
                 }
               }
             }
           }
         }
         leaf metric {
           description "Interface metric";
           type union {
             type string {
               pattern "<.*>|$.*";
             }
             type uint16 {
               range "1 .. 65535";
             }
           }
         }
         leaf priority {
           description "Designated router priority";
           type union {
             type string {
               pattern "<.*>|$.*";
             }
             type uint32 {
               range "0 .. 255";
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
        //  choice auth {
        //    case case_1 {
        //      container authentication {
        //        uses juniper-ospf-authentication;
        //      }
        //    }
        //    case case_2 {
        //      container authentication-key {
        //        description "Authentication key";
        //        status deprecated;
        //        leaf keyname {
        //          description "Authentication key value";
        //          type jt:unreadable;
        //        }
        //        leaf key-id {
        //          description "Key ID for MD5 authentication";
        //          type union {
        //            type string {
        //              pattern "<.*>|$.*";
        //            }
        //            type uint32 {
        //              range "0 .. 255";
        //            }
        //          }
        //        }
        //      }
        //    }
        //  }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           type string {
             length "1 .. 32";
           }
         }
         list topology {
           key name;
           ordered-by user;
           description "Topology specific attributes";
           leaf name {
             description "Topology name";
             type string;
           }
           // uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             // uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
         leaf transmit-interval {
           description "OSPF packet transmit interval (milliseconds)";
           status deprecated;
           type union {
             type string {
               pattern "<.*>|$.*";
             }
             type uint32 {
               range "1 .. 4294967295";
             }
           }
         }
         container bfd-liveness-detection {
           description "Bidirectional Forwarding Detection options";
           // uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 9000";
               }
             }
           }
           choice adaptation-choice {
             case case_1 {
               leaf no-adaptation {
                 description "Disable adaptation";
                 type empty;
               }
             }
           }
           container transmit-interval {
             description "Transmit-interval options";
             // uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             // uses apply-advanced;
             leaf threshold {
               description "High detection-time triggering a trap";
               units "milliseconds";
               type union {
                 type uint32;
                 type string {
                   pattern "<.*>|$.*";
                 }
               }
             }
           }
           container authentication {
             description "Authentication options";
             // uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           container echo {
             description "Echo mode parameters";
             // uses apply-advanced;
             leaf minimum-interval {
               description "Minimum transmit and receive interval";
               units "milliseconds";
               type union {
                 type string {
                   pattern "<.*>|$.*";
                 }
                 type uint32 {
                   range "100 .. 255000";
                 }
               }
             }
           }
           container echo-lite {
             description "Echo-lite more parameters";
             // uses apply-advanced;
             leaf minimum-interval {
               description "Minimum transmit and receive interval";
               units "milliseconds";
               type union {
                 type string {
                   pattern "<.*>|$.*";
                 }
                 type uint32 {
                   range "100 .. 255000";
                 }
               }
             }
           }
           leaf full-neighbors-only {
             description "Setup BFD sessions only to Full neighbors";
             type empty;
           }
           leaf holddown-interval {
             description "Time to hold the session-UP notification to the client";
             units "milliseconds";
             type union {
               type string {
                 pattern "<.*>|$.*";
               }
               type uint32 {
                 range "0 .. 255000";
               }
             }
           }
         }
         leaf dynamic-neighbors {
           description "Learn neighbors dynamically on a p2mp interface";
           type empty;
         }
         leaf no-advertise-adjacency-segment {
           description "Do not advertise an adjacency segment for this interface";
           type empty;
         }
         list neighbor {
           key name;
           ordered-by user;
           description "NBMA neighbor";
           leaf name {
             description "Address of neighbor";
             type jt:ipaddr;
           }
           leaf eligible {
             description "Eligible to be DR on an NBMA network";
             type empty;
           }
         }
         leaf poll-interval {
           description "Poll interval for NBMA interfaces";
           type union {
             type string {
               pattern "<.*>|$.*";
             }
             type uint32 {
               range "1 .. 65535";
             }
           }
         }
         leaf no-interface-state-traps {
           description "Do not send interface state change traps";
           type empty;
         }
         leaf strict-bfd {
           description "Enable strict bfd over this interface";
           type empty;
         }
         container post-convergence-lfa {
           presence "enable post-convergence-lfa";
           description "Protect interface using post-convergence backup path";
           // uses apply-advanced;
           container node-protection {
             presence "enable node-protection";
             description "Compute backup path assuming node failure";
             // uses apply-advanced;
             leaf cost {
               description "Cost for node protection";
               type union {
                 type string {
                   pattern "<.*>|$.*";
                 }
                 type uint16 {
                   range "1 .. 65535";
                 }
               }
             }
           }
           leaf srlg-protection {
             description "Compute backup path assuming SRLG failure";
             type empty;
           }
           leaf fate-sharing-protection {
             description "Compute backup path assuming fate-sharing group failure";
             type empty;
           }
         }
         leaf te-metric {
           description "Traffic engineering metric";
           type union {
             type string {
               pattern "<.*>|$.*";
             }
             type uint32 {
               range "1 .. 4294967295";
             }
           }
         }
         container ldp-synchronization {
           description "Advertise maximum metric until LDP is operational";
           presence "enable ldp-synchronization";
           uses ldp-sync-obj;
         }
         container ipv4-adjacency-segment {
           description "Configure ipv4 adjacency segment";
           // uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         list lan-neighbor {
           key name;
           ordered-by user;
           description "Configuration specific to a LAN neighbor";
           leaf name {
             description "Address of neighbor";
             type jt:ipaddr;
           }
           // uses apply-advanced;
           container ipv4-adjacency-segment {
             description "Configure ipv4 adjacency segment";
             // uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
         }
         leaf delay-metric {
           description "Delay metric";
           units "microseconds";
           type union {
             type string {
               pattern "<.*>|$.*";
             }
             type uint32 {
               range "0 .. 16777215";
             }
           }
         }
         container delay-measurement {
           presence "enable delay-measurement";
           description "Enable delay measurement";
           // uses apply-advanced;
           leaf probe-interval {
             description "Probe interval";
             units "seconds";
             type union {
               type string {
                 pattern "<.*>|$.*";
               }
               type uint32 {
                 range "1 .. 255";
               }
             }
           }
           leaf probe-count {
             description "Probe count";
             type union {
               type string {
                 pattern "<.*>|$.*";
               }
               type uint32 {
                 range "1 .. 15";
               }
             }
           }
           container advertisement {
             description "Delay advertisement";
             // uses apply-advanced;
             container periodic {
               description "Periodic advertisement parameters";
               // uses apply-advanced;
               leaf threshold {
                 description "Threshold";
                 units "percentage";
                 type union {
                   type string {
                     pattern "<.*>|$.*";
                   }
                   type uint32 {
                     range "0 .. 100";
                   }
                 }
               }
               leaf interval {
                 description "Interval";
                 units "seconds";
                 type union {
                   type string {
                     pattern "<.*>|$.*";
                   }
                   type uint32 {
                     range "30 .. 3600";
                   }
                 }
               }
             }
             container accelerated {
               presence "enable accelerated";
               description "Accelerated advertisement parameters";
               // uses apply-advanced;
               leaf threshold {
                 description "Threshold";
                 units "percentage";
                 type union {
                   type string {
                     pattern "<.*>|$.*";
                   }
                   type uint32 {
                     range "0 .. 100";
                   }
                 }
               }
             }
           }
         }
         container application-specific {
           description "Advertise application-specific TE attributes";
           // uses apply-advanced;
           list attribute-group {
             key name;
             ordered-by user;
             description "Link attribute group name";
             max-elements 1;
             leaf name {
               description "Link attribute group name";
               type string;
             }
             // uses apply-advanced;
             leaf te-metric {
               description "Traffic engineering metric for this attribute group";
               type union {
                 type string {
                   pattern "<.*>|$.*";
                 }
                 type uint32 {
                   range "1 .. 4294967295";
                 }
               }
             }
             leaf-list admin-group {
               ordered-by user;
               description "Administrative groups for this attribute-group";
               type string;
               max-elements 16;
             }
             leaf delay-metric {
               description "Delay metric for this attribute-group";
               units "microseconds";
               type union {
                 type string {
                   pattern "<.*>|$.*";
                 }
                 type uint32 {
                   range "0 .. 16777215";
                 }
               }
             }
             leaf advertise-interface-delay {
               description "Use interface specific static/dynamic delay values as applicable in ASLA Sub-TLVs";
               type empty;
             }
             container application {
               description "Standard Applications part of this attribute-group";
               // uses apply-advanced;
               leaf flex-algorithm {
                 description "Set X flag in standard application bit mask";
                 type empty;
               }
             }
           }
         }
       }
       leaf no-context-identifier-advertisement {
         description "Disable context identifier advertisments in this area";
         type empty;
       }
       list peer-interface {
         key name;
         ordered-by user;
         description "Configuration for peer interface";
         leaf name {
           description "Name of peer interface";
           type string;
         }
         // uses apply-advanced;
         choice enable-disable {
           case case_1 {
             leaf disable {
               description "Disable OSPF on this control peer";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
        //  choice auth {
        //    case case_1 {
        //      container authentication {
        //        uses juniper-ospf-authentication;
        //      }
        //    }
        //    case case_2 {
        //      container authentication-key {
        //        description "Authentication key";
        //        status deprecated;
        //        leaf keyname {
        //          description "Authentication key value";
        //          type jt:unreadable;
        //        }
        //        leaf key-id {
        //          description "Key ID for MD5 authentication";
        //          type union {
        //            type string {
        //              pattern "<.*>|$.*";
        //            }
        //            type uint32 {
        //              range "0 .. 255";
        //            }
        //          }
        //        }
        //      }
        //    }
        //  }
         leaf demand-circuit {
           description "Interface functions as a demand circuit";
           type empty;
         }
         leaf flood-reduction {
           description "Enable flood reduction";
           type empty;
         }
         leaf no-neighbor-down-notification {
           description "Don't inform other protocols about neighbor down events";
           type empty;
         }
       }
       leaf no-source-packet-routing {
         description "Disable SPRING in this area";
         type empty;
       }
       list context-identifier {
         key name;
         ordered-by user;
         description "Configure context identifier in support of edge protection";
         leaf name {
           description "Context identifier";
           type jt:ipv4addr;
         }
         // uses apply-advanced;
       }
       list label-switched-path {
         key name;
         ordered-by user;
         description "Configuration for advertisement of a label-switched path";
         leaf name {
           description "Name of label-switched path to be advertised";
           type string {
             length "1 .. 64";
           }
         }
         // uses apply-advanced;
         choice enable-disable {
           case case_1 {
             leaf disable {
               description "Disable OSPF on this label-switched path";
               type empty;
             }
           }
         }
         leaf metric {
           description "Interface metric";
           type union {
             type string {
               pattern "<.*>|$.*";
             }
             type uint16 {
               range "1 .. 65535";
             }
           }
         }
         list topology {
           key name;
           ordered-by user;
           description "Topology specific attributes";
           leaf name {
             description "Topology name";
             type string;
           }
           // uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             // uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
     }
     choice enable-disable {
       case case_1 {
         leaf disable {
           description "Disable OSPF";
           type empty;
         }
       }
     }
     container traceoptions {
       description "Trace options for OSPF";
       // uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
      //  list flag {
      //    key name;
      //    ordered-by user;
      //    description "Tracing parameters";
      //    leaf name {
      //      type enumeration {
      //        enum "spf" {
      //          description "Trace SPF calculations";
      //        }
      //        enum "error" {
      //          description "Trace errored packets";
      //        }
      //        enum "event" {
      //          description "Trace OSPF state machine events";
      //        }
      //        enum "packet-dump" {
      //          description "Dump the contents of selected packet types";
      //        }
      //        enum "flooding" {
      //          description "Trace LSA flooding";
      //        }
      //        enum "lsa-analysis" {
      //          description "Trace LSA analysis";
      //        }
      //        enum "packets" {
      //          description "Trace all OSPF packets";
      //        }
      //        enum "hello" {
      //          description "Trace hello packets";
      //        }
      //        enum "database-description" {
      //          description "Trace database description packets";
      //        }
      //        enum "lsa-request" {
      //          description "Trace LSA request packets";
      //        }
      //        enum "lsa-update" {
      //          description "Trace LSA update packets";
      //        }
      //        enum "lsa-ack" {
      //          description "Trace LSA acknowledgment packets";
      //        }
      //        enum "ldp-synchronization" {
      //          description "Trace synchronization between OSPF and LDP";
      //        }
      //        enum "on-demand" {
      //          description "Trace demand circuit extensions";
      //        }
      //        enum "nsr-synchronization" {
      //          description "Trace NSR synchronization events";
      //        }
      //        enum "graceful-restart" {
      //          description "Trace graceful restart";
      //        }
      //        enum "restart-signaling" {
      //          description "Trace restart signaling";
      //        }
      //        enum "traffic-statistics" {
      //          description "Trace Segment Routing Traffic Statistics";
      //        }
      //        enum "backup-spf" {
      //          description "Trace backup SPF (LFA) specific events";
      //        }
      //        enum "source-packet-routing" {
      //          description "Trace source packet routing (SPRING) events";
      //        }
      //        enum "post-convergence-lfa" {
      //          description "Trace post-convergence-lfa related events";
      //        }
      //        enum "flex-algorithm" {
      //          description "Trace flex-algorithm related events";
      //        }
      //        enum "rmopd" {
      //          description "Trace rmopd interactions";
      //        }
      //        enum "route" {
      //          description "Trace routing information";
      //        }
      //        enum "normal" {
      //          description "Trace normal events";
      //        }
      //        enum "general" {
      //          description "Trace general events";
      //        }
      //        enum "state" {
      //          description "Trace state transitions";
      //        }
      //        enum "policy" {
      //          description "Trace policy processing";
      //        }
      //        enum "task" {
      //          description "Trace routing protocol task processing";
      //        }
      //        enum "timer" {
      //          description "Trace routing protocol timer processing";
      //        }
      //        enum "all" {
      //          description "Trace everything";
      //        }
      //      }
      //    }
      //    leaf send {
      //      description "Trace transmitted packets";
      //      type empty;
      //    }
      //    leaf receive {
      //      description "Trace received packets";
      //      type empty;
      //    }
      //    leaf detail {
      //      description "Trace detailed information";
      //      type empty;
      //    }
      //    leaf disable {
      //      description "Disable this trace flag";
      //      type empty;
      //    }
      //  }
     }
     leaf prefix-export-limit {
       description "Maximum number of prefixes that can be exported";
       type union {
         type string {
           pattern "<.*>|$.*";
         }
         type uint32 {
           range "0 .. 4294967295";
         }
       }
     }
     container rib-groups {
       description "Routing table groups for importing OSPF routes";
       // uses apply-advanced;
       leaf inet {
         description "Name of the IPv4/v6 routing table group";
         type string;
       }
       leaf inet3 {
         description "Name of the IPv4/v6 inet.3 routing table group";
         type string;
       }
     }
     leaf job-stats {
       description "Collect job statistics";
       type empty;
     }
     container overload {
       presence "enable overload";
       description "Set the overload mode (repel transit traffic)";
       // uses apply-advanced;
       leaf timeout {
         description "Time after which overload mode is reset";
         units "seconds";
         type union {
           type string {
             pattern "<.*>|$.*";
           }
           type uint32 {
             range "60 .. 3600";
           }
         }
       }
       leaf allow-route-leaking {
         description "Allow routes to be leaked when overload is configured";
         type empty;
       }
       leaf stub-network {
         description "Advertise Stub Network with maximum metric";
         type empty;
       }
       leaf intra-area-prefix {
         description "Advertise Intra Area Prefix with maximum metric";
         type empty;
       }
       leaf as-external {
         description "Advertise As External with maximum usable metric";
         type empty;
       }
     }
    //  container database-protection {
    //    presence "enable database-protection";
    //    description "Configure database protection attributes";
    //    // uses apply-advanced;
    //    leaf maximum-lsa {
    //      description "Maximum allowed non self-generated LSAs";
    //      type union {
    //        type string {
    //          pattern "<.*>|$.*";
    //        }
    //        type uint32 {
    //          range "1 .. 1000000";
    //        }
    //      }
    //    }
    //    leaf warning-only {
    //      description "Emit only a warning when LSA maximum limit is exceeded";
    //      type empty;
    //    }
    //    leaf warning-threshold {
    //      description "Percentage of LSA maximum above which to trigger warning";
    //      units "percent";
    //      type union {
    //        type string {
    //          pattern "<.*>|$.*";
    //        }
    //        type uint8 {
    //          range "30 .. 100";
    //        }
    //      }
    //    }
    //    leaf ignore-count {
    //      description "Maximum number of times to go into ignore state";
    //      type union {
    //        type string {
    //          pattern "<.*>|$.*";
    //        }
    //        type uint8 {
    //          range "1 .. 32";
    //        }
    //      }
    //    }
    //    leaf ignore-time {
    //      description "Time to stay in ignore state and ignore all neighbors";
    //      units "seconds";
    //      type union {
    //        type string {
    //          pattern "<.*>|$.*";
    //        }
    //        type uint16 {
    //          range "30 .. 3600";
    //        }
    //      }
    //    }
    //    leaf reset-time {
    //      description "Time after which the ignore count gets reset to zero";
    //      units "seconds";
    //      type union {
    //        type string {
    //          pattern "<.*>|$.*";
    //        }
    //        type uint32 {
    //          range "60 .. 86400";
    //        }
    //      }
    //    }
    //  }
     container graceful-restart {
       description "Configure graceful restart attributes";
       // uses apply-advanced;
       choice enable-disable {
         case case_1 {
           leaf disable {
             description "Disable OSPF graceful restart capability";
             type empty;
           }
         }
       }
       leaf restart-duration {
         description "Time for all neighbors to become full";
         units "seconds";
         type union {
           type string {
             pattern "<.*>|$.*";
           }
           type uint32 {
             range "1 .. 3600";
           }
         }
       }
       leaf notify-duration {
         description "Time to send all max-aged grace LSAs";
         units "seconds";
         type union {
           type string {
             pattern "<.*>|$.*";
           }
           type uint32 {
             range "1 .. 3600";
           }
         }
       }
       container helper-disable {
         presence "enable helper-disable";
         description "Disable graceful restart helper capability";
         // uses apply-advanced;
         choice disable-choices {
           case case_1 {
             leaf standard {
               description "Disable helper-mode for rfc3623 based GR";
               type empty;
             }
           }
           case case_2 {
             leaf restart-signaling {
               description "Disable helper mode for restart-signaling ";
               type empty;
             }
           }
           case case_3 {
             leaf both {
               description "Disable helper mode for both the types of GR";
               type empty;
             }
           }
         }
       }
       leaf no-strict-lsa-checking {
         description "Do not abort graceful helper mode upon LSA changes";
         type empty;
       }
     }
     leaf route-type-community {
       description "Specify BGP extended community value to encode OSPF route type";
       type enumeration {
         enum "iana" {
           description "BGP extended community value used is 0x0306";
         }
         enum "vendor" {
           description "Vendor BGP extended community value used is 0x8000";
         }
       }
     }
     container domain-id {
       description "Configure domain ID";
       choice domain_id_or_disable {
         case case_1 {
           leaf domain-id {
             description "Domain ID";
             type string;
           }
         }
         case case_2 {
           leaf disable {
             description "Disable domain ID";
             type empty;
           }
         }
       }
     }
     choice domain_vpn_tag_or_disable {
       case case_1 {
         leaf domain-vpn-tag {
           description "Domain VPN tag for external LSA";
           type union {
             type string {
               pattern "<.*>|$.*";
             }
             type uint32 {
               range "0 .. 4294967295";
             }
           }
         }
       }
       case case_2 {
         leaf no-domain-vpn-tag {
           description "Disable domain VPN tag";
           type empty;
         }
       }
     }
     leaf preference {
       description "Preference of internal routes";
       type union {
         type uint32;
         type string {
           pattern "<.*>|$.*";
         }
       }
     }
     leaf external-preference {
       description "Preference of external routes";
       type union {
         type uint32;
         type string {
           pattern "<.*>|$.*";
         }
       }
     }
     leaf labeled-preference {
       description "Preference of labeled routes";
       type union {
         type uint32;
         type string {
           pattern "<.*>|$.*";
         }
       }
     }
     leaf-list export {
       ordered-by user;
       description "Export policy";
       type jt:policy-algebra;
     }
     leaf-list import {
       ordered-by user;
       description "Import policy (for external routes or setting priority)";
       type jt:policy-algebra;
     }
     leaf reference-bandwidth {
       description "Bandwidth for calculating metric defaults";
       type string;
     }
     leaf lsa-refresh-interval {
       description "LSA refresh interval (minutes)";
       default "50";
       type union {
         type string {
           pattern "<.*>|$.*";
         }
         type uint32 {
           range "25 .. 50";
         }
       }
     }
     leaf spf-delay {
       description "Time to wait before running an SPF";
       status deprecated;
       units "milliseconds";
       type union {
         type string {
           pattern "<.*>|$.*";
         }
         type uint32 {
           range "50 .. 8000";
         }
       }
     }
     leaf no-rfc-1583 {
       description "Disable RFC1583 compatibility";
       type empty;
     }
     leaf forwarding-address-to-broadcast {
       description "Set forwarding address in Type 5 LSA in broadcast network";
       type empty;
     }
     choice nssa-abr-option {
       case case_1 {
         leaf no-nssa-abr {
           description "Disable full NSSA functionality at ABR";
           type empty;
         }
       }
     }
     container sham-link {
       presence "enable sham-link";
       description "Configure parameters for sham links";
       // uses apply-advanced;
       leaf local {
         description "Local sham link endpoint address";
         type jt:ipaddr;
       }
       leaf no-advertise-local {
         description "Don't advertise local sham link endpoint as stub in router LSA";
         status deprecated;
         type empty;
       }
     }
   }
  //  grouping juniper-ospf-authentication {
  //    description "Authentication information";
  //    // uses apply-advanced;
  //    choice authentication-type {
  //      case case_1 {
  //        leaf simple-password {
  //          description "Authentication key";
  //          type jt:unreadable;
  //        }
  //      }
  //      case case_2 {
  //        list md5 {
  //          key name;
  //          ordered-by user;
  //          description "MD5 authentication key";
  //          leaf name {
  //            description "Key ID for MD5 authentication";
  //            type union {
  //              type string {
  //                pattern "<.*>|$.*";
  //              }
  //              type uint32 {
  //                range "0 .. 255";
  //              }
  //            }
  //          }
  //          leaf key {
  //            description "MD5 authentication key value";
  //            type jt:unreadable;
  //          }
  //          leaf start-time {
  //            description "Start time for key transmission (YYYY-MM-DD.HH:MM)";
  //            type jt:time;
  //          }
  //        }
  //      }
  //      case case_3 {
  //        list multi-active-md5 {
  //          key name;
  //          ordered-by user;
  //          description "Authentication Multiple active MD5 keys";
  //          leaf name {
  //            description "Key ID for MD5 authentication";
  //            type union {
  //              type string {
  //                pattern "<.*>|$.*";
  //              }
  //              type uint32 {
  //                range "0 .. 255";
  //              }
  //            }
  //          }
  //          leaf key {
  //            description "MD5 authentication key value";
  //            type jt:unreadable;
  //          }
  //          leaf delete-if-not-inuse {
  //            description "Delete this key if not in use";
  //            type empty;
  //          }
  //        }
  //      }
  //      case case_4 {
  //        leaf keychain {
  //          description "Key chain name";
  //          type string {
  //            length "1 .. 128";
  //          }
  //        }
  //      }
  //    }
  //  }
  //  grouping juniper-protocols-ospf3 {
  //    list realm {
  //      key name;
  //      ordered-by user;
  //      description "OSPFv3 realm configuration";
  //      leaf name {
  //        description "OSPFv3 realm name";
  //        type enumeration {
  //          enum "ipv6-unicast" {
  //            description "IPv6 unicast realm";
  //          }
  //          enum "ipv6-multicast" {
  //            description "IPv6 multicast realm";
  //          }
  //          enum "ipv4-unicast" {
  //            description "IPv4 unicast realm";
  //          }
  //          enum "ipv4-multicast" {
  //            description "IPv4 multicast realm";
  //          }
  //        }
  //      }
  //      // uses apply-advanced;
  //      list topology {
  //        key name;
  //        ordered-by user;
  //        description "Topology parameters";
  //        leaf name {
  //          description "Topology name";
  //          type string;
  //        }
  //        // uses apply-advanced;
  //        leaf disable {
  //          description "Disable this topology";
  //          type empty;
  //        }
  //        leaf topology-id {
  //          description "Topology identifier";
  //          type union {
  //            type string {
  //              pattern "<.*>|$.*";
  //            }
  //            type uint8 {
  //              range "32 .. 127";
  //            }
  //          }
  //        }
  //        leaf overload {
  //          description "Set the overload mode (repel transit traffic)";
  //          type empty;
  //        }
  //        leaf rib-group {
  //          description "Routing table group for importing routes";
  //          type string;
  //        }
  //        container spf-options {
  //          description "Configure options for SPF";
  //          // uses apply-advanced;
  //          container microloop-avoidance {
  //            description "Configure microloop avoidance mechanism";
  //            // uses apply-advanced;
  //            container post-convergence-path {
  //              presence "enable post-convergence-path";
  //              description "Temporarily install post-convergence path for routes potentially affected by microloops";
  //              // uses apply-advanced;
  //              leaf delay {
  //                description "Time after which temporary post-convergence paths are removed";
  //                units "milliseconds";
  //                type union {
  //                  type string {
  //                    pattern "<.*>|$.*";
  //                  }
  //                  type uint32 {
  //                    range "500 .. 60000";
  //                  }
  //                }
  //              }
  //              leaf maximum-labels {
  //                description "Maximum number of labels installed for post-convergence paths";
  //                type union {
  //                  type string {
  //                    pattern "<.*>|$.*";
  //                  }
  //                  type uint32 {
  //                    range "2 .. 8";
  //                  }
  //                }
  //              }
  //            }
  //          }
  //          leaf delay {
  //            description "Time to wait before running an SPF";
  //            units "milliseconds";
  //            type union {
  //              type string {
  //                pattern "<.*>|$.*";
  //              }
  //              type uint32 {
  //                range "50 .. 8000";
  //              }
  //            }
  //          }
  //          leaf holddown {
  //            description "Time to hold down before running an SPF";
  //            units "milliseconds";
  //            type union {
  //              type string {
  //                pattern "<.*>|$.*";
  //              }
  //              type uint32 {
  //                range "2000 .. 20000";
  //              }
  //            }
  //          }
  //          leaf rapid-runs {
  //            description "Number of maximum rapid SPF runs before holddown";
  //            type union {
  //              type string {
  //                pattern "<.*>|$.*";
  //              }
  //              type uint32 {
  //                range "1 .. 10";
  //              }
  //            }
  //          }
  //          leaf no-ignore-our-externals {
  //            description "Do not ignore self-generated external and NSSA LSAs";
  //            type empty;
  //          }
  //        }
  //        container backup-spf-options {
  //          description "Configure options for backup SPF";
  //          // uses apply-advanced;
  //          container remote-backup-calculation {
  //            presence "enable remote-backup-calculation";
  //            description "Calculate Remote LFA backup nexthops";
  //            // uses apply-advanced;
  //            container pq-nodes-nearest-to-source {
  //              description "PQ nodes selection based upon nearest to source";
  //              // uses apply-advanced;
  //              leaf percent {
  //                description "Selection percentage for nearest to source";
  //                type union {
  //                  type string {
  //                    pattern "<.*>|$.*";
  //                  }
  //                  type uint32 {
  //                    range "10 .. 100";
  //                  }
  //                }
  //              }
  //            }
  //          }
  //          container use-post-convergence-lfa {
  //            presence "enable use-post-convergence-lfa";
  //            description "Calculate post-convergence backup paths";
  //            // uses apply-advanced;
  //            leaf maximum-labels {
  //              description "Maximum number of labels installed for post-convergence paths";
  //              type union {
  //                type string {
  //                  pattern "<.*>|$.*";
  //                }
  //                type uint32 {
  //                  range "2 .. 8";
  //                }
  //              }
  //            }
  //            leaf maximum-backup-paths {
  //              description "Maximum number of equal-cost post-convergence paths installed";
  //              type union {
  //                type string {
  //                  pattern "<.*>|$.*";
  //                }
  //                type uint32 {
  //                  range "1 .. 8";
  //                }
  //              }
  //            }
  //          }
  //          leaf use-source-packet-routing {
  //            description "Use spring backup paths for inet.0 routes";
  //            type empty;
  //          }
  //          leaf disable {
  //            description "Do not run backup SPF";
  //            type empty;
  //          }
  //          leaf no-install {
  //            description "Do not install backup nexthops into the RIB";
  //            type empty;
  //          }
  //          leaf downstream-paths-only {
  //            description "Use only downstream backup paths";
  //            type empty;
  //          }
  //          container per-prefix-calculation {
  //            description "Calculate backup nexthops for non-best prefix originators";
  //            // uses apply-advanced;
  //            leaf stubs {
  //              description "Per prefix calculation for stubs only";
  //              type empty;
  //            }
  //            leaf summary {
  //              description "Per prefix calculation for summary originators only";
  //              type empty;
  //            }
  //            leaf externals {
  //              description "Per prefix calculation for externals";
  //              type empty;
  //            }
  //            leaf all {
  //              description "Per prefix calculation for all";
  //              type empty;
  //            }
  //          }
  //          leaf node-link-degradation {
  //            description "Degrade to link protection when nodelink protection not available";
  //            type empty;
  //          }
  //        }
  //        leaf prefix-export-limit {
  //          description "Maximum number of prefixes that can be exported";
  //          type union {
  //            type string {
  //              pattern "<.*>|$.*";
  //            }
  //            type uint32 {
  //              range "0 .. 4294967295";
  //            }
  //          }
  //        }
  //      }
  //      container spf-options {
  //        description "Configure options for SPF";
  //        // uses apply-advanced;
  //        container microloop-avoidance {
  //          description "Configure microloop avoidance mechanism";
  //          // uses apply-advanced;
  //          container post-convergence-path {
  //            presence "enable post-convergence-path";
  //            description "Temporarily install post-convergence path for routes potentially affected by microloops";
  //            // uses apply-advanced;
  //            leaf delay {
  //              description "Time after which temporary post-convergence paths are removed";
  //              units "milliseconds";
  //              type union {
  //                type string {
  //                  pattern "<.*>|$.*";
  //                }
  //                type uint32 {
  //                  range "500 .. 60000";
  //                }
  //              }
  //            }
  //            leaf maximum-labels {
  //              description "Maximum number of labels installed for post-convergence paths";
  //              type union {
  //                type string {
  //                  pattern "<.*>|$.*";
  //                }
  //                type uint32 {
  //                  range "2 .. 8";
  //                }
  //              }
  //            }
  //          }
  //        }
  //        leaf delay {
  //          description "Time to wait before running an SPF";
  //          units "milliseconds";
  //          type union {
  //            type string {
  //              pattern "<.*>|$.*";
  //            }
  //            type uint32 {
  //              range "50 .. 8000";
  //            }
  //          }
  //        }
  //        leaf holddown {
  //          description "Time to hold down before running an SPF";
  //          units "milliseconds";
  //          type union {
  //            type string {
  //              pattern "<.*>|$.*";
  //            }
  //            type uint32 {
  //              range "2000 .. 20000";
  //            }
  //          }
  //        }
  //        leaf rapid-runs {
  //          description "Number of maximum rapid SPF runs before holddown";
  //          type union {
  //            type string {
  //              pattern "<.*>|$.*";
  //            }
  //            type uint32 {
  //              range "1 .. 10";
  //            }
  //          }
  //        }
  //        leaf no-ignore-our-externals {
  //          description "Do not ignore self-generated external and NSSA LSAs";
  //          type empty;
  //        }
  //      }
  //      container backup-spf-options {
  //        description "Configure options for backup SPF";
  //        // uses apply-advanced;
  //        container remote-backup-calculation {
  //          presence "enable remote-backup-calculation";
  //          description "Calculate Remote LFA backup nexthops";
  //          // uses apply-advanced;
  //          container pq-nodes-nearest-to-source {
  //            description "PQ nodes selection based upon nearest to source";
  //            // uses apply-advanced;
  //            leaf percent {
  //              description "Selection percentage for nearest to source";
  //              type union {
  //                type string {
  //                  pattern "<.*>|$.*";
  //                }
  //                type uint32 {
  //                  range "10 .. 100";
  //                }
  //              }
  //            }
  //          }
  //        }
  //        container use-post-convergence-lfa {
  //          presence "enable use-post-convergence-lfa";
  //          description "Calculate post-convergence backup paths";
  //          // uses apply-advanced;
  //          leaf maximum-labels {
  //            description "Maximum number of labels installed for post-convergence paths";
  //            type union {
  //              type string {
  //                pattern "<.*>|$.*";
  //              }
  //              type uint32 {
  //                range "2 .. 8";
  //              }
  //            }
  //          }
  //          leaf maximum-backup-paths {
  //            description "Maximum number of equal-cost post-convergence paths installed";
  //            type union {
  //              type string {
  //                pattern "<.*>|$.*";
  //              }
  //              type uint32 {
  //                range "1 .. 8";
  //              }
  //            }
  //          }
  //        }
  //        leaf use-source-packet-routing {
  //          description "Use spring backup paths for inet.0 routes";
  //          type empty;
  //        }
  //        leaf disable {
  //          description "Do not run backup SPF";
  //          type empty;
  //        }
  //        leaf no-install {
  //          description "Do not install backup nexthops into the RIB";
  //          type empty;
  //        }
  //        leaf downstream-paths-only {
  //          description "Use only downstream backup paths";
  //          type empty;
  //        }
  //        container per-prefix-calculation {
  //          description "Calculate backup nexthops for non-best prefix originators";
  //          // uses apply-advanced;
  //          leaf stubs {
  //            description "Per prefix calculation for stubs only";
  //            type empty;
  //          }
  //          leaf summary {
  //            description "Per prefix calculation for summary originators only";
  //            type empty;
  //          }
  //          leaf externals {
  //            description "Per prefix calculation for externals";
  //            type empty;
  //          }
  //          leaf all {
  //            description "Per prefix calculation for all";
  //            type empty;
  //          }
  //        }
  //        leaf node-link-degradation {
  //          description "Degrade to link protection when nodelink protection not available";
  //          type empty;
  //        }
  //      }
  //      container traffic-engineering {
  //        presence "enable traffic-engineering";
  //        description "Configure traffic engineering attributes";
  //        // uses apply-advanced;
  //        leaf no-topology {
  //          description "Disable dissemination of TE link-state topology information";
  //          type empty;
  //        }
  //        leaf multicast-rpf-routes {
  //          description "Install routes for multicast RPF checks into inet.2";
  //          type empty;
  //        }
  //        leaf l3-unicast-topology {
  //          description "Download IGP topology into TED";
  //          type empty;
  //        }
  //        container ignore-lsp-metrics {
  //          presence "enable ignore-lsp-metrics";
  //          description "Ignore label-switched path metrics when doing shortcuts";
  //          // uses apply-advanced;
  //          leaf unconfigured-only {
  //            description "Ignore lsp metrics for unconfigured only";
  //            type empty;
  //          }
  //        }
  //        container shortcuts {
  //          presence "enable shortcuts";
  //          description "Use label-switched paths as next hops, if possible";
  //          // uses apply-advanced;
  //          leaf ignore-lsp-metrics {
  //            description "Ignore label-switched path metrics when doing shortcuts";
  //            status deprecated;
  //            type empty;
  //          }
  //          leaf lsp-metric-into-summary {
  //            description "Advertise LSP metric into summary LSAs";
  //            type empty;
  //          }
  //          list family {
  //            key name;
  //            ordered-by user;
  //            description "Address family specific traffic-engineering attributes";
  //            leaf name {
  //              type enumeration {
  //                enum "inet" {
  //                  description "IPv4 family";
  //                }
  //                enum "inet-mpls" {
  //                  description "IPv4-MPLS family";
  //                }
  //              }
  //            }
  //            // uses apply-advanced;
  //          }
  //        }
  //        leaf advertise-unnumbered-interfaces {
  //          description "Advertise unnumbered interfaces";
  //          type empty;
  //        }
  //        leaf credibility-protocol-preference {
  //          description "TED protocol credibility follows protocol preference";
  //          type empty;
  //        }
  //        container advertisement {
  //          description "Advertise TE parameters even if RSVP is not turned on";
  //          // uses apply-advanced;
  //          leaf always {
  //            description "Advertise TE parameters in TE LSAs";
  //            type empty;
  //          }
  //        }
  //        container tunnel-source-protocol {
  //          description "Protocols from which to pick label-switched paths";
  //          // uses apply-advanced;
  //          container rsvp {
  //            presence "enable rsvp";
  //            description "Pick label-switched paths from rsvp";
  //            // uses apply-advanced;
  //            leaf preference {
  //              description "Preference for label-switched paths from this protocol";
  //              type union {
  //                type string {
  //                  pattern "<.*>|$.*";
  //                }
  //                type uint32 {
  //                  range "1 .. 255";
  //                }
  //              }
  //            }
  //          }
  //          container spring-te {
  //            presence "enable spring-te";
  //            description "Pick label-switched paths from spring-te";
  //            // uses apply-advanced;
  //            leaf preference {
  //              description "Preference for label-switched paths from this protocol";
  //              type union {
  //                type string {
  //                  pattern "<.*>|$.*";
  //                }
  //                type uint32 {
  //                  range "1 .. 255";
  //                }
  //              }
  //            }
  //          }
  //        }
  //      }
  //      container source-packet-routing {
  //        presence "enable source-packet-routing";
  //        description "Enable source packet routing (SPRING)";
  //        // uses apply-advanced;
  //        container adjacency-segment {
  //          description "Attributes for adjacency segments in spring";
  //          // uses apply-advanced;
  //          leaf hold-time {
  //            description "Retain time of Adjacency segment after isolating from an interface";
  //            type union {
  //              type string {
  //                pattern "<.*>|$.*";
  //              }
  //              type uint32 {
  //                range "180000 .. 900000";
  //              }
  //            }
  //          }
  //        }
  //        leaf-list prefix-segment {
  //          ordered-by user;
  //          description "Prefix Segment policy";
  //          type jt:policy-algebra;
  //        }
  //        leaf explicit-null {
  //          description "Set E and P bits in all Prefix SID advertisements";
  //          type empty;
  //        }
  //        container node-segment {
  //          presence "enable node-segment";
  //          description "Enable support for Node segments in SPRING";
  //          // uses apply-advanced;
  //          leaf ipv4-index {
  //            description "Set ipv4 node segment index";
  //            type union {
  //              type string {
  //                pattern "<.*>|$.*";
  //              }
  //              type uint32 {
  //                range "0 .. 199999";
  //              }
  //            }
  //          }
  //          leaf index-range {
  //            description "Set range of node segment indices allowed";
  //            type union {
  //              type string {
  //                pattern "<.*>|$.*";
  //              }
  //              type uint32 {
  //                range "32 .. 16385";
  //              }
  //            }
  //          }
  //        }
  //        container srgb {
  //          description "Set the SRGB global block in SPRING";
  //          leaf start-label {
  //            description "Start range for SRGB label block";
  //            type union {
  //              type string {
  //                pattern "<.*>|$.*";
  //              }
  //              type uint32;
  //            }
  //          }
  //          leaf index-range {
  //            description "Index to the SRGB start label block";
  //            type union {
  //              type string {
  //                pattern "<.*>|$.*";
  //              }
  //              type uint32;
  //            }
  //          }
  //        }
  //        leaf mapping-server {
  //          description "Mapping server name";
  //          type string;
  //        }
  //        leaf install-prefix-sid-for-best-route {
  //          description "For best route install a exact prefix sid route";
  //          type empty;
  //        }
  //        leaf ldp-stitching {
  //          description "Enable SR to LDP stitching";
  //          type empty;
  //        }
  //        leaf-list flex-algorithm {
  //          description "Flex-algorithms we would like to participate in";
  //          type union {
  //            type string {
  //              pattern "<.*>|$.*";
  //            }
  //            type uint32 {
  //              range "128 .. 255";
  //            }
  //          }
  //          max-elements 16;
  //        }
  //        leaf strict-asla-based-flex-algorithm {
  //          description "Flex-Algorithm to ignore links not having ASLA sub-TLVs";
  //          type empty;
  //        }
  //        container sensor-based-stats {
  //          description "Configure sensor based stats in SPRING";
  //          // uses apply-advanced;
  //          container per-interface-per-member-link {
  //            description "Configure sensor based stats per nexthop";
  //            leaf ingress {
  //              description "Enable sensor based stats on ingress interface";
  //              type empty;
  //            }
  //            leaf egress {
  //              description "Enable sensor based stats on egress interface";
  //              type empty;
  //            }
  //          }
  //          container per-sid {
  //            description "Configure sensor based stats per spring route";
  //            leaf ingress {
  //              description "Enable sensor based stats for per-sid ingress accounting";
  //              type empty;
  //            }
  //            leaf egress {
  //              description "Enable sensor based stats for IP-MPLS egress accounting";
  //              type empty;
  //            }
  //          }
  //        }
  //      }
  //      list area {
  //        key name;
  //        ordered-by user;
  //        description "Configure an OSPF area";
  //        leaf name {
  //          description "Area ID";
  //          type jt:areaid;
  //        }
  //        // uses apply-advanced;
  //        choice stub-option {
  //          case case_1 {
  //            container stub {
  //              presence "enable stub";
  //              description "Configure a stub area";
  //              leaf default-metric {
  //                description "Metric for the default route in this stub area";
  //                type union {
  //                  type string {
  //                    pattern "<.*>|$.*";
  //                  }
  //                  type uint32 {
  //                    range "1 .. 16777215";
  //                  }
  //                }
  //              }
  //              choice summaries-choice {
  //                leaf summaries {
  //                  description "Flood summary LSAs into this stub area";
  //                  type empty;
  //                }
  //                leaf no-summaries {
  //                  description "Don't flood summary LSAs into this stub area";
  //                  type empty;
  //                }
  //              }
  //            }
  //          }
  //          case case_2 {
  //            container nssa {
  //              presence "enable nssa";
  //              description "Configure a not-so-stubby area";
  //              // uses apply-advanced;
  //              container default-lsa {
  //                presence "enable default-lsa";
  //                description "Configure a default LSA";
  //                // uses apply-advanced;
  //                leaf default-metric {
  //                  description "Metric for the default route in this area";
  //                  type union {
  //                    type string {
  //                      pattern "<.*>|$.*";
  //                    }
  //                    type uint32 {
  //                      range "1 .. 16777215";
  //                    }
  //                  }
  //                }
  //                leaf metric-type {
  //                  description "External metric type for the default type 7 LSA";
  //                  type union {
  //                    type string {
  //                      pattern "<.*>|$.*";
  //                    }
  //                    type uint32 {
  //                      range "1 .. 2";
  //                    }
  //                  }
  //                }
  //                leaf type-7 {
  //                  description "Flood type 7 default LSA if no-summaries is configured";
  //                  type empty;
  //                }
  //              }
  //              leaf default-metric {
  //                description "Metric for the default route in this area";
  //                status deprecated;
  //                type union {
  //                  type string {
  //                    pattern "<.*>|$.*";
  //                  }
  //                  type uint32 {
  //                    range "1 .. 16777215";
  //                  }
  //                }
  //              }
  //              leaf metric-type {
  //                description "External metric type for the default type 7 LSA";
  //                status deprecated;
  //                type union {
  //                  type string {
  //                    pattern "<.*>|$.*";
  //                  }
  //                  type uint32 {
  //                    range "1 .. 2";
  //                  }
  //                }
  //              }
  //              choice summaries-choice {
  //                leaf summaries {
  //                  description "Flood summary LSAs into this NSSA area";
  //                  type empty;
  //                }
  //                leaf no-summaries {
  //                  description "Don't flood summary LSAs into this NSSA area";
  //                  type empty;
  //                }
  //              }
  //              list area-range {
  //                key name;
  //                ordered-by user;
  //                description "Configure NSSA area ranges";
  //                leaf name {
  //                  description "Range to summarize NSSA routes in this area";
  //                  type jt:ipprefix;
  //                }
  //                // uses apply-advanced;
  //                leaf restrict {
  //                  description "Restrict advertisement of this area range";
  //                  type empty;
  //                }
  //                leaf exact {
  //                  description "Enforce exact match for advertisement of this area range";
  //                  type empty;
  //                }
  //                container override-metric {
  //                  presence "enable override-metric";
  //                  description "Override the dynamic metric for this area-range";
  //                  // uses apply-advanced;
  //                  leaf metric {
  //                    description "Metric value";
  //                    type union {
  //                      type string {
  //                        pattern "<.*>|$.*";
  //                      }
  //                      type uint32 {
  //                        range "1 .. 16777215";
  //                      }
  //                    }
  //                  }
  //                  leaf metric-type {
  //                    description "Set the metric type for the override metric";
  //                    default "1";
  //                    type union {
  //                      type string {
  //                        pattern "<.*>|$.*";
  //                      }
  //                      type uint32 {
  //                        range "1 .. 2";
  //                      }
  //                    }
  //                  }
  //                }
  //              }
  //            }
  //          }
  //        }
  //        list area-range {
  //          key name;
  //          ordered-by user;
  //          description "Configure area ranges";
  //          leaf name {
  //            description "Range to summarize routes in this area";
  //            type jt:ipprefix;
  //          }
  //          // uses apply-advanced;
  //          leaf restrict {
  //            description "Restrict advertisement of this area range";
  //            type empty;
  //          }
  //          leaf exact {
  //            description "Enforce exact match for advertisement of this area range";
  //            type empty;
  //          }
  //          leaf override-metric {
  //            description "Override the dynamic metric for this area-range";
  //            type union {
  //              type string {
  //                pattern "<.*>|$.*";
  //              }
  //              type uint32 {
  //                range "1 .. 16777215";
  //              }
  //            }
  //          }
  //        }
  //        leaf-list network-summary-export {
  //          ordered-by user;
  //          description "Export policy for Type 3 Summary LSAs";
  //          type jt:policy-algebra;
  //        }
  //        leaf-list network-summary-import {
  //          ordered-by user;
  //          description "Import policy for Type 3 Summary LSAs";
  //          type jt:policy-algebra;
  //        }
  //        leaf-list inter-area-prefix-export {
  //          ordered-by user;
  //          description "Export policy for Inter Area Prefix LSAs";
  //          type jt:policy-algebra;
  //        }
  //        leaf-list inter-area-prefix-import {
  //          ordered-by user;
  //          description "Import policy for Inter Area Prefix LSAs";
  //          type jt:policy-algebra;
  //        }
  //        leaf authentication-type {
  //          description "Authentication type";
  //          status deprecated;
  //          type enumeration {
  //            enum "none" {
  //              description "No authentication";
  //              status deprecated;
  //            }
  //            enum "simple" {
  //              description "Simple password authentication";
  //              status deprecated;
  //            }
  //            enum "md5" {
  //              description "MD5 authentication";
  //              status deprecated;
  //            }
  //          }
  //        }
  //        list virtual-link {
  //          key "neighbor-id transit-area";
  //          ordered-by user;
  //          description "Configure virtual links";
  //          leaf neighbor-id {
  //            description "Router ID of a virtual neighbor";
  //            type jt:ipv4addr;
  //          }
  //          leaf transit-area {
  //            description "Transit area in common with virtual neighbor";
  //            type jt:areaid;
  //          }
  //          // uses apply-advanced;
  //          choice enable-disable {
  //            case case_1 {
  //              leaf disable {
  //                description "Disable this virtual link";
  //                type empty;
  //              }
  //            }
  //          }
  //          leaf retransmit-interval {
  //            description "Retransmission interval (seconds)";
  //            type union {
  //              type string {
  //                pattern "<.*>|$.*";
  //              }
  //              type uint32 {
  //                range "1 .. 65535";
  //              }
  //            }
  //          }
  //          leaf transit-delay {
  //            description "Transit delay (seconds)";
  //            type union {
  //              type string {
  //                pattern "<.*>|$.*";
  //              }
  //              type uint32 {
  //                range "1 .. 65535";
  //              }
  //            }
  //          }
  //          leaf hello-interval {
  //            description "Hello interval (seconds)";
  //            type union {
  //              type string {
  //                pattern "<.*>|$.*";
  //              }
  //              type uint32 {
  //                range "1 .. 255";
  //              }
  //            }
  //          }
  //          leaf dead-interval {
  //            description "Dead interval (seconds)";
  //            type union {
  //              type string {
  //                pattern "<.*>|$.*";
  //              }
  //              type uint32 {
  //                range "1 .. 65535";
  //              }
  //            }
  //          }
  //          leaf mtu {
  //            description "Maximum OSPF packet size";
  //            type union {
  //              type string {
  //                pattern "<.*>|$.*";
  //              }
  //              type uint32 {
  //                range "128 .. 65535";
  //              }
  //            }
  //          }
  //          choice auth {
  //            case case_1 {
  //              container authentication {
  //                uses juniper-ospf-authentication;
  //              }
  //            }
  //            case case_2 {
  //              container authentication-key {
  //                description "Authentication key";
  //                status deprecated;
  //                leaf keyname {
  //                  description "Authentication key value";
  //                  type jt:unreadable;
  //                }
  //                leaf key-id {
  //                  description "Key ID for MD5 authentication";
  //                  type union {
  //                    type string {
  //                      pattern "<.*>|$.*";
  //                    }
  //                    type uint32 {
  //                      range "0 .. 255";
  //                    }
  //                  }
  //                }
  //              }
  //            }
  //          }
  //          leaf demand-circuit {
  //            description "Interface functions as a demand circuit";
  //            type empty;
  //          }
  //          leaf flood-reduction {
  //            description "Enable flood reduction";
  //            type empty;
  //          }
  //          leaf no-neighbor-down-notification {
  //            description "Don't inform other protocols about neighbor down events";
  //            type empty;
  //          }
  //          leaf ipsec-sa {
  //            description "IPSec security association name";
  //            type string {
  //              length "1 .. 32";
  //            }
  //          }
  //          list topology {
  //            key name;
  //            ordered-by user;
  //            description "Topology specific attributes";
  //            leaf name {
  //              description "Topology name";
  //              type string;
  //            }
  //            // uses apply-advanced;
  //            leaf disable {
  //              description "Disable this topology";
  //              type empty;
  //            }
  //            leaf metric {
  //              description "Topology metric";
  //              type union {
  //                type string {
  //                  pattern "<.*>|$.*";
  //                }
  //                type uint16 {
  //                  range "1 .. 65535";
  //                }
  //              }
  //            }
  //            container bandwidth-based-metrics {
  //              description "Configure bandwidth based metrics";
  //              // uses apply-advanced;
  //              list bandwidth {
  //                key name;
  //                description "Bandwidth threshold";
  //                leaf name {
  //                  type string;
  //                }
  //                leaf metric {
  //                  description "Metric associated with specified bandwidth";
  //                  type union {
  //                    type string {
  //                      pattern "<.*>|$.*";
  //                    }
  //                    type uint16 {
  //                      range "1 .. 65535";
  //                    }
  //                  }
  //                }
  //              }
  //            }
  //          }
  //        }
  //        list sham-link-remote {
  //          key name;
  //          ordered-by user;
  //          description "Configure parameters for remote sham link endpoint";
  //          leaf name {
  //            description "Remote sham link endpoint address";
  //            type jt:ipaddr;
  //          }
  //          // uses apply-advanced;
  //          leaf metric {
  //            description "Sham link metric";
  //            type union {
  //              type string {
  //                pattern "<.*>|$.*";
  //              }
  //              type uint16 {
  //                range "1 .. 65535";
  //              }
  //            }
  //          }
  //          leaf ipsec-sa {
  //            description "IPSec security association name";
  //            type string {
  //              length "1 .. 32";
  //            }
  //          }
  //          leaf demand-circuit {
  //            description "Interface functions as a demand circuit";
  //            type empty;
  //          }
  //          leaf flood-reduction {
  //            description "Enable flood reduction";
  //            type empty;
  //          }
  //          list topology {
  //            key name;
  //            ordered-by user;
  //            description "Topology specific attributes";
  //            leaf name {
  //              description "Topology name";
  //              type string;
  //            }
  //            // uses apply-advanced;
  //            leaf disable {
  //              description "Disable this topology";
  //              type empty;
  //            }
  //            leaf metric {
  //              description "Topology metric";
  //              type union {
  //                type string {
  //                  pattern "<.*>|$.*";
  //                }
  //                type uint16 {
  //                  range "1 .. 65535";
  //                }
  //              }
  //            }
  //            container bandwidth-based-metrics {
  //              description "Configure bandwidth based metrics";
  //              // uses apply-advanced;
  //              list bandwidth {
  //                key name;
  //                description "Bandwidth threshold";
  //                leaf name {
  //                  type string;
  //                }
  //                leaf metric {
  //                  description "Metric associated with specified bandwidth";
  //                  type union {
  //                    type string {
  //                      pattern "<.*>|$.*";
  //                    }
  //                    type uint16 {
  //                      range "1 .. 65535";
  //                    }
  //                  }
  //                }
  //              }
  //            }
  //          }
  //        }
  //        list interface {
  //          key name;
  //          ordered-by user;
  //          description "Include an interface in this area";
  //          leaf name {
  //            description "Interface name";
  //            type union {
  //              type jt:ipv4addr-or-interface;
  //              type string {
  //                pattern "<.*>|$.*";
  //              }
  //            }
  //          }
  //          // uses apply-advanced;
  //          choice enable-disable {
  //            case case_1 {
  //              leaf disable {
  //                description "Disable OSPF on this interface";
  //                type empty;
  //              }
  //            }
  //          }
  //          leaf interface-type {
  //            description "Type of interface";
  //            type enumeration {
  //              enum "nbma" {
  //                description "Nonbroadcast multiaccess";
  //              }
  //              enum "p2mp" {
  //                description "Point-to-multipoint NBMA";
  //              }
  //              enum "p2p" {
  //                description "Point-to-point";
  //              }
  //              enum "p2mp-over-lan" {
  //                description "Point-to-multipoint over LAN mode";
  //              }
  //            }
  //          }
  //          choice protection-type {
  //            case case_1 {
  //              leaf link-protection {
  //                description "Protect interface from link faults only";
  //                type empty;
  //              }
  //            }
  //            case case_2 {
  //              leaf node-link-protection {
  //                description "Protect interface from both link and node faults";
  //                type empty;
  //              }
  //            }
  //          }
  //          leaf no-eligible-backup {
  //            description "Not eligible to backup traffic from protected interfaces";
  //            type empty;
  //          }
  //          leaf no-eligible-remote-backup {
  //            description "Not eligible for Remote-LFA backup traffic from protected interfaces";
  //            type empty;
  //          }
  //          container passive {
  //            presence "enable passive";
  //            description "Do not run OSPF, but advertise it";
  //            // uses apply-advanced;
  //            container traffic-engineering {
  //              description "Advertise TE link information";
  //              // uses apply-advanced;
  //              leaf remote-node-id {
  //                description "Remote address of the link";
  //                type jt:ipaddr;
  //              }
  //              leaf remote-node-router-id {
  //                description "TE Router-ID of the remote node";
  //                type jt:ipv4addr;
  //              }
  //            }
  //          }
  //          leaf secondary {
  //            description "Treat interface as secondary";
  //            type empty;
  //          }
  //          leaf own-router-lsa {
  //            description "Generate a separate router LSA for this interface";
  //            type empty;
  //          }
  //          container bandwidth-based-metrics {
  //            description "Configure bandwidth based metrics";
  //            // uses apply-advanced;
  //            list bandwidth {
  //              key name;
  //              description "Bandwidth threshold";
  //              leaf name {
  //                type string;
  //              }
  //              leaf metric {
  //                description "Metric associated with specified bandwidth";
  //                type union {
  //                  type string {
  //                    pattern "<.*>|$.*";
  //                  }
  //                  type uint16 {
  //                    range "1 .. 65535";
  //                  }
  //                }
  //              }
  //            }
  //          }
  //          leaf metric {
  //            description "Interface metric";
  //            type union {
  //              type string {
  //                pattern "<.*>|$.*";
  //              }
  //              type uint16 {
  //                range "1 .. 65535";
  //              }
  //            }
  //          }
  //          leaf priority {
  //            description "Designated router priority";
  //            type union {
  //              type string {
  //                pattern "<.*>|$.*";
  //              }
  //              type uint32 {
  //                range "0 .. 255";
  //              }
  //            }
  //          }
  //          leaf retransmit-interval {
  //            description "Retransmission interval (seconds)";
  //            type union {
  //              type string {
  //                pattern "<.*>|$.*";
  //              }
  //              type uint32 {
  //                range "1 .. 65535";
  //              }
  //            }
  //          }
  //          leaf transit-delay {
  //            description "Transit delay (seconds)";
  //            type union {
  //              type string {
  //                pattern "<.*>|$.*";
  //              }
  //              type uint32 {
  //                range "1 .. 65535";
  //              }
  //            }
  //          }
  //          leaf hello-interval {
  //            description "Hello interval (seconds)";
  //            type union {
  //              type string {
  //                pattern "<.*>|$.*";
  //              }
  //              type uint32 {
  //                range "1 .. 255";
  //              }
  //            }
  //          }
  //          leaf dead-interval {
  //            description "Dead interval (seconds)";
  //            type union {
  //              type string {
  //                pattern "<.*>|$.*";
  //              }
  //              type uint32 {
  //                range "1 .. 65535";
  //              }
  //            }
  //          }
  //          leaf mtu {
  //            description "Maximum OSPF packet size";
  //            type union {
  //              type string {
  //                pattern "<.*>|$.*";
  //              }
  //              type uint32 {
  //                range "128 .. 65535";
  //              }
  //            }
  //          }
  //          choice auth {
  //            case case_1 {
  //              container authentication {
  //                uses juniper-ospf-authentication;
  //              }
  //            }
  //            case case_2 {
  //              container authentication-key {
  //                description "Authentication key";
  //                status deprecated;
  //                leaf keyname {
  //                  description "Authentication key value";
  //                  type jt:unreadable;
  //                }
  //                leaf key-id {
  //                  description "Key ID for MD5 authentication";
  //                  type union {
  //                    type string {
  //                      pattern "<.*>|$.*";
  //                    }
  //                    type uint32 {
  //                      range "0 .. 255";
  //                    }
  //                  }
  //                }
  //              }
  //            }
  //          }
  //          leaf demand-circuit {
  //            description "Interface functions as a demand circuit";
  //            type empty;
  //          }
  //          leaf flood-reduction {
  //            description "Enable flood reduction";
  //            type empty;
  //          }
  //          leaf no-neighbor-down-notification {
  //            description "Don't inform other protocols about neighbor down events";
  //            type empty;
  //          }
  //          leaf ipsec-sa {
  //            description "IPSec security association name";
  //            type string {
  //              length "1 .. 32";
  //            }
  //          }
  //          list topology {
  //            key name;
  //            ordered-by user;
  //            description "Topology specific attributes";
  //            leaf name {
  //              description "Topology name";
  //              type string;
  //            }
  //            // uses apply-advanced;
  //            leaf disable {
  //              description "Disable this topology";
  //              type empty;
  //            }
  //            leaf metric {
  //              description "Topology metric";
  //              type union {
  //                type string {
  //                  pattern "<.*>|$.*";
  //                }
  //                type uint16 {
  //                  range "1 .. 65535";
  //                }
  //              }
  //            }
  //            container bandwidth-based-metrics {
  //              description "Configure bandwidth based metrics";
  //              // uses apply-advanced;
  //              list bandwidth {
  //                key name;
  //                description "Bandwidth threshold";
  //                leaf name {
  //                  type string;
  //                }
  //                leaf metric {
  //                  description "Metric associated with specified bandwidth";
  //                  type union {
  //                    type string {
  //                      pattern "<.*>|$.*";
  //                    }
  //                    type uint16 {
  //                      range "1 .. 65535";
  //                    }
  //                  }
  //                }
  //              }
  //            }
  //          }
  //          leaf transmit-interval {
  //            description "OSPF packet transmit interval (milliseconds)";
  //            status deprecated;
  //            type union {
  //              type string {
  //                pattern "<.*>|$.*";
  //              }
  //              type uint32 {
  //                range "1 .. 4294967295";
  //              }
  //            }
  //          }
  //          container bfd-liveness-detection {
  //            description "Bidirectional Forwarding Detection options";
  //            // uses apply-advanced;
  //            leaf version {
  //              description "BFD protocol version number";
  //              default "automatic";
  //              type enumeration {
  //                enum "0" {
  //                  description "BFD version 0 (deprecated)";
  //                }
  //                enum "1" {
  //                  description "BFD version 1";
  //                }
  //                enum "automatic" {
  //                  description "Choose BFD version automatically";
  //                }
  //              }
  //            }
  //            leaf minimum-interval {
  //              description "Minimum transmit and receive interval";
  //              units "milliseconds";
  //              type union {
  //                type string {
  //                  pattern "<.*>|$.*";
  //                }
  //                type uint32 {
  //                  range "1 .. 255000";
  //                }
  //              }
  //            }
  //            leaf minimum-transmit-interval {
  //              description "Minimum transmit interval";
  //              status deprecated;
  //              units "milliseconds";
  //              type union {
  //                type string {
  //                  pattern "<.*>|$.*";
  //                }
  //                type uint32 {
  //                  range "1 .. 255000";
  //                }
  //              }
  //            }
  //            leaf minimum-receive-interval {
  //              description "Minimum receive interval";
  //              units "milliseconds";
  //              type union {
  //                type string {
  //                  pattern "<.*>|$.*";
  //                }
  //                type uint32 {
  //                  range "1 .. 255000";
  //                }
  //              }
  //            }
  //            leaf multiplier {
  //              description "Detection time multiplier";
  //              default "3";
  //              type union {
  //                type string {
  //                  pattern "<.*>|$.*";
  //                }
  //                type uint32 {
  //                  range "1 .. 255";
  //                }
  //              }
  //            }
  //            leaf inline-disable {
  //              description "Disable inline mode for this BFD session";
  //              type empty;
  //            }
  //            leaf pdu-size {
  //              description "BFD transport protocol payload size";
  //              default "24";
  //              type union {
  //                type string {
  //                  pattern "<.*>|$.*";
  //                }
  //                type uint32 {
  //                  range "24 .. 9000";
  //                }
  //              }
  //            }
  //            choice adaptation-choice {
  //              case case_1 {
  //                leaf no-adaptation {
  //                  description "Disable adaptation";
  //                  type empty;
  //                }
  //              }
  //            }
  //            container transmit-interval {
  //              description "Transmit-interval options";
  //              // uses apply-advanced;
  //              leaf minimum-interval {
  //                description "Minimum transmit interval";
  //                units "milliseconds";
  //                type union {
  //                  type string {
  //                    pattern "<.*>|$.*";
  //                  }
  //                  type uint32 {
  //                    range "1 .. 255000";
  //                  }
  //                }
  //              }
  //              leaf threshold {
  //                description "High transmit interval triggering a trap";
  //                units "milliseconds";
  //                type union {
  //                  type uint32;
  //                  type string {
  //                    pattern "<.*>|$.*";
  //                  }
  //                }
  //              }
  //            }
  //            container detection-time {
  //              description "Detection-time options";
  //              // uses apply-advanced;
  //              leaf threshold {
  //                description "High detection-time triggering a trap";
  //                units "milliseconds";
  //                type union {
  //                  type uint32;
  //                  type string {
  //                    pattern "<.*>|$.*";
  //                  }
  //                }
  //              }
  //            }
  //            container authentication {
  //              description "Authentication options";
  //              // uses apply-advanced;
  //              leaf key-chain {
  //                description "Key chain name";
  //                type string;
  //              }
  //              leaf algorithm {
  //                description "Algorithm name";
  //                type enumeration {
  //                  enum "simple-password" {
  //                    description "Simple password";
  //                  }
  //                  enum "keyed-md5" {
  //                    description "Keyed message Digest 5";
  //                  }
  //                  enum "meticulous-keyed-md5" {
  //                    description "Meticulous keyed message Digest 5";
  //                  }
  //                  enum "keyed-sha-1" {
  //                    description "Keyed secure hash algorithm (SHA1) ";
  //                  }
  //                  enum "meticulous-keyed-sha-1" {
  //                    description "Meticulous keyed secure hash algorithm (SHA1) ";
  //                  }
  //                }
  //              }
  //              leaf loose-check {
  //                description "Verify authentication only if authentication is negotiated";
  //                type empty;
  //              }
  //            }
  //            container echo {
  //              description "Echo mode parameters";
  //              // uses apply-advanced;
  //              leaf minimum-interval {
  //                description "Minimum transmit and receive interval";
  //                units "milliseconds";
  //                type union {
  //                  type string {
  //                    pattern "<.*>|$.*";
  //                  }
  //                  type uint32 {
  //                    range "100 .. 255000";
  //                  }
  //                }
  //              }
  //            }
  //            container echo-lite {
  //              description "Echo-lite more parameters";
  //              // uses apply-advanced;
  //              leaf minimum-interval {
  //                description "Minimum transmit and receive interval";
  //                units "milliseconds";
  //                type union {
  //                  type string {
  //                    pattern "<.*>|$.*";
  //                  }
  //                  type uint32 {
  //                    range "100 .. 255000";
  //                  }
  //                }
  //              }
  //            }
  //            leaf full-neighbors-only {
  //              description "Setup BFD sessions only to Full neighbors";
  //              type empty;
  //            }
  //            leaf holddown-interval {
  //              description "Time to hold the session-UP notification to the client";
  //              units "milliseconds";
  //              type union {
  //                type string {
  //                  pattern "<.*>|$.*";
  //                }
  //                type uint32 {
  //                  range "0 .. 255000";
  //                }
  //              }
  //            }
  //          }
  //          leaf dynamic-neighbors {
  //            description "Learn neighbors dynamically on a p2mp interface";
  //            type empty;
  //          }
  //          leaf no-advertise-adjacency-segment {
  //            description "Do not advertise an adjacency segment for this interface";
  //            type empty;
  //          }
  //          list neighbor {
  //            key name;
  //            ordered-by user;
  //            description "NBMA neighbor";
  //            leaf name {
  //              description "Address of neighbor";
  //              type jt:ipaddr;
  //            }
  //            leaf eligible {
  //              description "Eligible to be DR on an NBMA network";
  //              type empty;
  //            }
  //          }
  //          leaf poll-interval {
  //            description "Poll interval for NBMA interfaces";
  //            type union {
  //              type string {
  //                pattern "<.*>|$.*";
  //              }
  //              type uint32 {
  //                range "1 .. 65535";
  //              }
  //            }
  //          }
  //          leaf no-interface-state-traps {
  //            description "Do not send interface state change traps";
  //            type empty;
  //          }
  //          leaf strict-bfd {
  //            description "Enable strict bfd over this interface";
  //            type empty;
  //          }
  //          container post-convergence-lfa {
  //            presence "enable post-convergence-lfa";
  //            description "Protect interface using post-convergence backup path";
  //            // uses apply-advanced;
  //            container node-protection {
  //              presence "enable node-protection";
  //              description "Compute backup path assuming node failure";
  //              // uses apply-advanced;
  //              leaf cost {
  //                description "Cost for node protection";
  //                type union {
  //                  type string {
  //                    pattern "<.*>|$.*";
  //                  }
  //                  type uint16 {
  //                    range "1 .. 65535";
  //                  }
  //                }
  //              }
  //            }
  //            leaf srlg-protection {
  //              description "Compute backup path assuming SRLG failure";
  //              type empty;
  //            }
  //            leaf fate-sharing-protection {
  //              description "Compute backup path assuming fate-sharing group failure";
  //              type empty;
  //            }
  //          }
  //          leaf te-metric {
  //            description "Traffic engineering metric";
  //            type union {
  //              type string {
  //                pattern "<.*>|$.*";
  //              }
  //              type uint32 {
  //                range "1 .. 4294967295";
  //              }
  //            }
  //          }
  //          container ldp-synchronization {
  //            description "Advertise maximum metric until LDP is operational";
  //            presence "enable ldp-synchronization";
  //            uses ldp-sync-obj;
  //          }
  //          container ipv4-adjacency-segment {
  //            description "Configure ipv4 adjacency segment";
  //            // uses apply-advanced;
  //            container protected {
  //              description "Adjacency SID is eligible for protection";
  //              choice adjsid-type {
  //                case case_1 {
  //                  container index {
  //                    description "Adjacency SID indexed from SRGB";
  //                    leaf index-number {
  //                      type union {
  //                        type string {
  //                          pattern "<.*>|$.*";
  //                        }
  //                        type uint32 {
  //                          range "0 .. 199999";
  //                        }
  //                      }
  //                    }
  //                  }
  //                }
  //                case case_2 {
  //                  leaf label {
  //                    description "Adjacency SID from static label pool";
  //                    type union {
  //                      type string {
  //                        pattern "<.*>|$.*";
  //                      }
  //                      type uint32 {
  //                        range "16 .. 1048575";
  //                      }
  //                    }
  //                  }
  //                }
  //                case case_3 {
  //                  leaf dynamic {
  //                    description "Dynamically allocate an adjacency segment";
  //                    type empty;
  //                  }
  //                }
  //              }
  //            }
  //            container unprotected {
  //              description "Adjacency SID uneligible for protection";
  //              choice adjsid-type {
  //                case case_1 {
  //                  container index {
  //                    description "Adjacency SID indexed from SRGB";
  //                    leaf index-number {
  //                      type union {
  //                        type string {
  //                          pattern "<.*>|$.*";
  //                        }
  //                        type uint32 {
  //                          range "0 .. 199999";
  //                        }
  //                      }
  //                    }
  //                  }
  //                }
  //                case case_2 {
  //                  leaf label {
  //                    description "Adjacency SID from static label pool";
  //                    type union {
  //                      type string {
  //                        pattern "<.*>|$.*";
  //                      }
  //                      type uint32 {
  //                        range "16 .. 1048575";
  //                      }
  //                    }
  //                  }
  //                }
  //                case case_3 {
  //                  leaf dynamic {
  //                    description "Dynamically allocate an adjacency segment";
  //                    type empty;
  //                  }
  //                }
  //              }
  //            }
  //          }
  //          list lan-neighbor {
  //            key name;
  //            ordered-by user;
  //            description "Configuration specific to a LAN neighbor";
  //            leaf name {
  //              description "Address of neighbor";
  //              type jt:ipaddr;
  //            }
  //            // uses apply-advanced;
  //            container ipv4-adjacency-segment {
  //              description "Configure ipv4 adjacency segment";
  //              // uses apply-advanced;
  //              container protected {
  //                description "Adjacency SID is eligible for protection";
  //                choice adjsid-type {
  //                  case case_1 {
  //                    container index {
  //                      description "Adjacency SID indexed from SRGB";
  //                      leaf index-number {
  //                        type union {
  //                          type string {
  //                            pattern "<.*>|$.*";
  //                          }
  //                          type uint32 {
  //                            range "0 .. 199999";
  //                          }
  //                        }
  //                      }
  //                    }
  //                  }
  //                  case case_2 {
  //                    leaf label {
  //                      description "Adjacency SID from static label pool";
  //                      type union {
  //                        type string {
  //                          pattern "<.*>|$.*";
  //                        }
  //                        type uint32 {
  //                          range "16 .. 1048575";
  //                        }
  //                      }
  //                    }
  //                  }
  //                  case case_3 {
  //                    leaf dynamic {
  //                      description "Dynamically allocate an adjacency segment";
  //                      type empty;
  //                    }
  //                  }
  //                }
  //              }
  //              container unprotected {
  //                description "Adjacency SID uneligible for protection";
  //                choice adjsid-type {
  //                  case case_1 {
  //                    container index {
  //                      description "Adjacency SID indexed from SRGB";
  //                      leaf index-number {
  //                        type union {
  //                          type string {
  //                            pattern "<.*>|$.*";
  //                          }
  //                          type uint32 {
  //                            range "0 .. 199999";
  //                          }
  //                        }
  //                      }
  //                    }
  //                  }
  //                  case case_2 {
  //                    leaf label {
  //                      description "Adjacency SID from static label pool";
  //                      type union {
  //                        type string {
  //                          pattern "<.*>|$.*";
  //                        }
  //                        type uint32 {
  //                          range "16 .. 1048575";
  //                        }
  //                      }
  //                    }
  //                  }
  //                  case case_3 {
  //                    leaf dynamic {
  //                      description "Dynamically allocate an adjacency segment";
  //                      type empty;
  //                    }
  //                  }
  //                }
  //              }
  //            }
  //          }
  //          leaf delay-metric {
  //            description "Delay metric";
  //            units "microseconds";
  //            type union {
  //              type string {
  //                pattern "<.*>|$.*";
  //              }
  //              type uint32 {
  //                range "0 .. 16777215";
  //              }
  //            }
  //          }
  //          container delay-measurement {
  //            presence "enable delay-measurement";
  //            description "Enable delay measurement";
  //            // uses apply-advanced;
  //            leaf probe-interval {
  //              description "Probe interval";
  //              units "seconds";
  //              type union {
  //                type string {
  //                  pattern "<.*>|$.*";
  //                }
  //                type uint32 {
  //                  range "1 .. 255";
  //                }
  //              }
  //            }
  //            leaf probe-count {
  //              description "Probe count";
  //              type union {
  //                type string {
  //                  pattern "<.*>|$.*";
  //                }
  //                type uint32 {
  //                  range "1 .. 15";
  //                }
  //              }
  //            }
  //            container advertisement {
  //              description "Delay advertisement";
  //              // uses apply-advanced;
  //              container periodic {
  //                description "Periodic advertisement parameters";
  //                // uses apply-advanced;
  //                leaf threshold {
  //                  description "Threshold";
  //                  units "percentage";
  //                  type union {
  //                    type string {
  //                      pattern "<.*>|$.*";
  //                    }
  //                    type uint32 {
  //                      range "0 .. 100";
  //                    }
  //                  }
  //                }
  //                leaf interval {
  //                  description "Interval";
  //                  units "seconds";
  //                  type union {
  //                    type string {
  //                      pattern "<.*>|$.*";
  //                    }
  //                    type uint32 {
  //                      range "30 .. 3600";
  //                    }
  //                  }
  //                }
  //              }
  //              container accelerated {
  //                presence "enable accelerated";
  //                description "Accelerated advertisement parameters";
  //                // uses apply-advanced;
  //                leaf threshold {
  //                  description "Threshold";
  //                  units "percentage";
  //                  type union {
  //                    type string {
  //                      pattern "<.*>|$.*";
  //                    }
  //                    type uint32 {
  //                      range "0 .. 100";
  //                    }
  //                  }
  //                }
  //              }
  //            }
  //          }
  //          container application-specific {
  //            description "Advertise application-specific TE attributes";
  //            // uses apply-advanced;
  //            list attribute-group {
  //              key name;
  //              ordered-by user;
  //              description "Link attribute group name";
  //              max-elements 1;
  //              leaf name {
  //                description "Link attribute group name";
  //                type string;
  //              }
  //              // uses apply-advanced;
  //              leaf te-metric {
  //                description "Traffic engineering metric for this attribute group";
  //                type union {
  //                  type string {
  //                    pattern "<.*>|$.*";
  //                  }
  //                  type uint32 {
  //                    range "1 .. 4294967295";
  //                  }
  //                }
  //              }
  //              leaf-list admin-group {
  //                ordered-by user;
  //                description "Administrative groups for this attribute-group";
  //                type string;
  //                max-elements 16;
  //              }
  //              leaf delay-metric {
  //                description "Delay metric for this attribute-group";
  //                units "microseconds";
  //                type union {
  //                  type string {
  //                    pattern "<.*>|$.*";
  //                  }
  //                  type uint32 {
  //                    range "0 .. 16777215";
  //                  }
  //                }
  //              }
  //              leaf advertise-interface-delay {
  //                description "Use interface specific static/dynamic delay values as applicable in ASLA Sub-TLVs";
  //                type empty;
  //              }
  //              container application {
  //                description "Standard Applications part of this attribute-group";
  //                // uses apply-advanced;
  //                leaf flex-algorithm {
  //                  description "Set X flag in standard application bit mask";
  //                  type empty;
  //                }
  //              }
  //            }
  //          }
  //        }
  //        leaf no-context-identifier-advertisement {
  //          description "Disable context identifier advertisments in this area";
  //          type empty;
  //        }
  //        list peer-interface {
  //          key name;
  //          ordered-by user;
  //          description "Configuration for peer interface";
  //          leaf name {
  //            description "Name of peer interface";
  //            type string;
  //          }
  //          // uses apply-advanced;
  //          choice enable-disable {
  //            case case_1 {
  //              leaf disable {
  //                description "Disable OSPF on this control peer";
  //                type empty;
  //              }
  //            }
  //          }
  //          leaf retransmit-interval {
  //            description "Retransmission interval (seconds)";
  //            type union {
  //              type string {
  //                pattern "<.*>|$.*";
  //              }
  //              type uint32 {
  //                range "1 .. 65535";
  //              }
  //            }
  //          }
  //          leaf transit-delay {
  //            description "Transit delay (seconds)";
  //            type union {
  //              type string {
  //                pattern "<.*>|$.*";
  //              }
  //              type uint32 {
  //                range "1 .. 65535";
  //              }
  //            }
  //          }
  //          leaf hello-interval {
  //            description "Hello interval (seconds)";
  //            type union {
  //              type string {
  //                pattern "<.*>|$.*";
  //              }
  //              type uint32 {
  //                range "1 .. 255";
  //              }
  //            }
  //          }
  //          leaf dead-interval {
  //            description "Dead interval (seconds)";
  //            type union {
  //              type string {
  //                pattern "<.*>|$.*";
  //              }
  //              type uint32 {
  //                range "1 .. 65535";
  //              }
  //            }
  //          }
  //          leaf mtu {
  //            description "Maximum OSPF packet size";
  //            type union {
  //              type string {
  //                pattern "<.*>|$.*";
  //              }
  //              type uint32 {
  //                range "128 .. 65535";
  //              }
  //            }
  //          }
  //          choice auth {
  //            case case_1 {
  //              container authentication {
  //                uses juniper-ospf-authentication;
  //              }
  //            }
  //            case case_2 {
  //              container authentication-key {
  //                description "Authentication key";
  //                status deprecated;
  //                leaf keyname {
  //                  description "Authentication key value";
  //                  type jt:unreadable;
  //                }
  //                leaf key-id {
  //                  description "Key ID for MD5 authentication";
  //                  type union {
  //                    type string {
  //                      pattern "<.*>|$.*";
  //                    }
  //                    type uint32 {
  //                      range "0 .. 255";
  //                    }
  //                  }
  //                }
  //              }
  //            }
  //          }
  //          leaf demand-circuit {
  //            description "Interface functions as a demand circuit";
  //            type empty;
  //          }
  //          leaf flood-reduction {
  //            description "Enable flood reduction";
  //            type empty;
  //          }
  //          leaf no-neighbor-down-notification {
  //            description "Don't inform other protocols about neighbor down events";
  //            type empty;
  //          }
  //        }
  //        leaf no-source-packet-routing {
  //          description "Disable SPRING in this area";
  //          type empty;
  //        }
  //        list context-identifier {
  //          key name;
  //          ordered-by user;
  //          description "Configure context identifier in support of edge protection";
  //          leaf name {
  //            description "Context identifier";
  //            type jt:ipv4addr;
  //          }
  //          // uses apply-advanced;
  //        }
  //        list label-switched-path {
  //          key name;
  //          ordered-by user;
  //          description "Configuration for advertisement of a label-switched path";
  //          leaf name {
  //            description "Name of label-switched path to be advertised";
  //            type string {
  //              length "1 .. 64";
  //            }
  //          }
  //          // uses apply-advanced;
  //          choice enable-disable {
  //            case case_1 {
  //              leaf disable {
  //                description "Disable OSPF on this label-switched path";
  //                type empty;
  //              }
  //            }
  //          }
  //          leaf metric {
  //            description "Interface metric";
  //            type union {
  //              type string {
  //                pattern "<.*>|$.*";
  //              }
  //              type uint16 {
  //                range "1 .. 65535";
  //              }
  //            }
  //          }
  //          list topology {
  //            key name;
  //            ordered-by user;
  //            description "Topology specific attributes";
  //            leaf name {
  //              description "Topology name";
  //              type string;
  //            }
  //            // uses apply-advanced;
  //            leaf disable {
  //              description "Disable this topology";
  //              type empty;
  //            }
  //            leaf metric {
  //              description "Topology metric";
  //              type union {
  //                type string {
  //                  pattern "<.*>|$.*";
  //                }
  //                type uint16 {
  //                  range "1 .. 65535";
  //                }
  //              }
  //            }
  //            container bandwidth-based-metrics {
  //              description "Configure bandwidth based metrics";
  //              // uses apply-advanced;
  //              list bandwidth {
  //                key name;
  //                description "Bandwidth threshold";
  //                leaf name {
  //                  type string;
  //                }
  //                leaf metric {
  //                  description "Metric associated with specified bandwidth";
  //                  type union {
  //                    type string {
  //                      pattern "<.*>|$.*";
  //                    }
  //                    type uint16 {
  //                      range "1 .. 65535";
  //                    }
  //                  }
  //                }
  //              }
  //            }
  //          }
  //        }
  //      }
  //      choice enable-disable {
  //        case case_1 {
  //          leaf disable {
  //            description "Disable OSPF";
  //            type empty;
  //          }
  //        }
  //      }
  //      container traceoptions {
  //        description "Trace options for OSPF";
  //        // uses apply-advanced;
  //        container file {
  //          description "Trace file options";
  //          leaf filename {
  //            description "Name of file in which to write trace information";
  //            type string {
  //              length "1 .. 1024";
  //            }
  //          }
  //          leaf replace {
  //            description "Replace trace file rather than appending to it";
  //            status deprecated;
  //            type empty;
  //          }
  //          leaf size {
  //            description "Maximum trace file size";
  //            type string;
  //          }
  //          leaf files {
  //            description "Maximum number of trace files";
  //            default "10";
  //            type union {
  //              type string {
  //                pattern "<.*>|$.*";
  //              }
  //              type uint32 {
  //                range "2 .. 1000";
  //              }
  //            }
  //          }
  //          leaf no-stamp {
  //            description "Do not timestamp trace file";
  //            status deprecated;
  //            type empty;
  //          }
  //          choice world-readable-choice {
  //            leaf world-readable {
  //              description "Allow any user to read the log file";
  //              type empty;
  //            }
  //            leaf no-world-readable {
  //              description "Don't allow any user to read the log file";
  //              type empty;
  //            }
  //          }
  //        }
  //        list flag {
  //          key name;
  //          ordered-by user;
  //          description "Tracing parameters";
  //          leaf name {
  //            type enumeration {
  //              enum "spf" {
  //                description "Trace SPF calculations";
  //              }
  //              enum "error" {
  //                description "Trace errored packets";
  //              }
  //              enum "event" {
  //                description "Trace OSPF state machine events";
  //              }
  //              enum "packet-dump" {
  //                description "Dump the contents of selected packet types";
  //              }
  //              enum "flooding" {
  //                description "Trace LSA flooding";
  //              }
  //              enum "lsa-analysis" {
  //                description "Trace LSA analysis";
  //              }
  //              enum "packets" {
  //                description "Trace all OSPF packets";
  //              }
  //              enum "hello" {
  //                description "Trace hello packets";
  //              }
  //              enum "database-description" {
  //                description "Trace database description packets";
  //              }
  //              enum "lsa-request" {
  //                description "Trace LSA request packets";
  //              }
  //              enum "lsa-update" {
  //                description "Trace LSA update packets";
  //              }
  //              enum "lsa-ack" {
  //                description "Trace LSA acknowledgment packets";
  //              }
  //              enum "ldp-synchronization" {
  //                description "Trace synchronization between OSPF and LDP";
  //              }
  //              enum "on-demand" {
  //                description "Trace demand circuit extensions";
  //              }
  //              enum "nsr-synchronization" {
  //                description "Trace NSR synchronization events";
  //              }
  //              enum "graceful-restart" {
  //                description "Trace graceful restart";
  //              }
  //              enum "restart-signaling" {
  //                description "Trace restart signaling";
  //              }
  //              enum "traffic-statistics" {
  //                description "Trace Segment Routing Traffic Statistics";
  //              }
  //              enum "backup-spf" {
  //                description "Trace backup SPF (LFA) specific events";
  //              }
  //              enum "source-packet-routing" {
  //                description "Trace source packet routing (SPRING) events";
  //              }
  //              enum "post-convergence-lfa" {
  //                description "Trace post-convergence-lfa related events";
  //              }
  //              enum "flex-algorithm" {
  //                description "Trace flex-algorithm related events";
  //              }
  //              enum "rmopd" {
  //                description "Trace rmopd interactions";
  //              }
  //              enum "route" {
  //                description "Trace routing information";
  //              }
  //              enum "normal" {
  //                description "Trace normal events";
  //              }
  //              enum "general" {
  //                description "Trace general events";
  //              }
  //              enum "state" {
  //                description "Trace state transitions";
  //              }
  //              enum "policy" {
  //                description "Trace policy processing";
  //              }
  //              enum "task" {
  //                description "Trace routing protocol task processing";
  //              }
  //              enum "timer" {
  //                description "Trace routing protocol timer processing";
  //              }
  //              enum "all" {
  //                description "Trace everything";
  //              }
  //            }
  //          }
  //          leaf send {
  //            description "Trace transmitted packets";
  //            type empty;
  //          }
  //          leaf receive {
  //            description "Trace received packets";
  //            type empty;
  //          }
  //          leaf detail {
  //            description "Trace detailed information";
  //            type empty;
  //          }
  //          leaf disable {
  //            description "Disable this trace flag";
  //            type empty;
  //          }
  //        }
  //      }
  //      leaf prefix-export-limit {
  //        description "Maximum number of prefixes that can be exported";
  //        type union {
  //          type string {
  //            pattern "<.*>|$.*";
  //          }
  //          type uint32 {
  //            range "0 .. 4294967295";
  //          }
  //        }
  //      }
  //      container rib-groups {
  //        description "Routing table groups for importing OSPF routes";
  //        // uses apply-advanced;
  //        leaf inet {
  //          description "Name of the IPv4/v6 routing table group";
  //          type string;
  //        }
  //        leaf inet3 {
  //          description "Name of the IPv4/v6 inet.3 routing table group";
  //          type string;
  //        }
  //      }
  //      leaf job-stats {
  //        description "Collect job statistics";
  //        type empty;
  //      }
  //      container overload {
  //        presence "enable overload";
  //        description "Set the overload mode (repel transit traffic)";
  //        // uses apply-advanced;
  //        leaf timeout {
  //          description "Time after which overload mode is reset";
  //          units "seconds";
  //          type union {
  //            type string {
  //              pattern "<.*>|$.*";
  //            }
  //            type uint32 {
  //              range "60 .. 3600";
  //            }
  //          }
  //        }
  //        leaf allow-route-leaking {
  //          description "Allow routes to be leaked when overload is configured";
  //          type empty;
  //        }
  //        leaf stub-network {
  //          description "Advertise Stub Network with maximum metric";
  //          type empty;
  //        }
  //        leaf intra-area-prefix {
  //          description "Advertise Intra Area Prefix with maximum metric";
  //          type empty;
  //        }
  //        leaf as-external {
  //          description "Advertise As External with maximum usable metric";
  //          type empty;
  //        }
  //      }
  //      container database-protection {
  //        presence "enable database-protection";
  //        description "Configure database protection attributes";
  //        // uses apply-advanced;
  //        leaf maximum-lsa {
  //          description "Maximum allowed non self-generated LSAs";
  //          type union {
  //            type string {
  //              pattern "<.*>|$.*";
  //            }
  //            type uint32 {
  //              range "1 .. 1000000";
  //            }
  //          }
  //        }
  //        leaf warning-only {
  //          description "Emit only a warning when LSA maximum limit is exceeded";
  //          type empty;
  //        }
  //        leaf warning-threshold {
  //          description "Percentage of LSA maximum above which to trigger warning";
  //          units "percent";
  //          type union {
  //            type string {
  //              pattern "<.*>|$.*";
  //            }
  //            type uint8 {
  //              range "30 .. 100";
  //            }
  //          }
  //        }
  //        leaf ignore-count {
  //          description "Maximum number of times to go into ignore state";
  //          type union {
  //            type string {
  //              pattern "<.*>|$.*";
  //            }
  //            type uint8 {
  //              range "1 .. 32";
  //            }
  //          }
  //        }
  //        leaf ignore-time {
  //          description "Time to stay in ignore state and ignore all neighbors";
  //          units "seconds";
  //          type union {
  //            type string {
  //              pattern "<.*>|$.*";
  //            }
  //            type uint16 {
  //              range "30 .. 3600";
  //            }
  //          }
  //        }
  //        leaf reset-time {
  //          description "Time after which the ignore count gets reset to zero";
  //          units "seconds";
  //          type union {
  //            type string {
  //              pattern "<.*>|$.*";
  //            }
  //            type uint32 {
  //              range "60 .. 86400";
  //            }
  //          }
  //        }
  //      }
  //      container graceful-restart {
  //        description "Configure graceful restart attributes";
  //        // uses apply-advanced;
  //        choice enable-disable {
  //          case case_1 {
  //            leaf disable {
  //              description "Disable OSPF graceful restart capability";
  //              type empty;
  //            }
  //          }
  //        }
  //        leaf restart-duration {
  //          description "Time for all neighbors to become full";
  //          units "seconds";
  //          type union {
  //            type string {
  //              pattern "<.*>|$.*";
  //            }
  //            type uint32 {
  //              range "1 .. 3600";
  //            }
  //          }
  //        }
  //        leaf notify-duration {
  //          description "Time to send all max-aged grace LSAs";
  //          units "seconds";
  //          type union {
  //            type string {
  //              pattern "<.*>|$.*";
  //            }
  //            type uint32 {
  //              range "1 .. 3600";
  //            }
  //          }
  //        }
  //        container helper-disable {
  //          presence "enable helper-disable";
  //          description "Disable graceful restart helper capability";
  //          // uses apply-advanced;
  //          choice disable-choices {
  //            case case_1 {
  //              leaf standard {
  //                description "Disable helper-mode for rfc3623 based GR";
  //                type empty;
  //              }
  //            }
  //            case case_2 {
  //              leaf restart-signaling {
  //                description "Disable helper mode for restart-signaling ";
  //                type empty;
  //              }
  //            }
  //            case case_3 {
  //              leaf both {
  //                description "Disable helper mode for both the types of GR";
  //                type empty;
  //              }
  //            }
  //          }
  //        }
  //        leaf no-strict-lsa-checking {
  //          description "Do not abort graceful helper mode upon LSA changes";
  //          type empty;
  //        }
  //      }
  //      leaf route-type-community {
  //        description "Specify BGP extended community value to encode OSPF route type";
  //        type enumeration {
  //          enum "iana" {
  //            description "BGP extended community value used is 0x0306";
  //          }
  //          enum "vendor" {
  //            description "Vendor BGP extended community value used is 0x8000";
  //          }
  //        }
  //      }
  //      container domain-id {
  //        description "Configure domain ID";
  //        choice domain_id_or_disable {
  //          case case_1 {
  //            leaf domain-id {
  //              description "Domain ID";
  //              type string;
  //            }
  //          }
  //          case case_2 {
  //            leaf disable {
  //              description "Disable domain ID";
  //              type empty;
  //            }
  //          }
  //        }
  //      }
  //      choice domain_vpn_tag_or_disable {
  //        case case_1 {
  //          leaf domain-vpn-tag {
  //            description "Domain VPN tag for external LSA";
  //            type union {
  //              type string {
  //                pattern "<.*>|$.*";
  //              }
  //              type uint32 {
  //                range "0 .. 4294967295";
  //              }
  //            }
  //          }
  //        }
  //        case case_2 {
  //          leaf no-domain-vpn-tag {
  //            description "Disable domain VPN tag";
  //            type empty;
  //          }
  //        }
  //      }
  //      leaf preference {
  //        description "Preference of internal routes";
  //        type union {
  //          type uint32;
  //          type string {
  //            pattern "<.*>|$.*";
  //          }
  //        }
  //      }
  //      leaf external-preference {
  //        description "Preference of external routes";
  //        type union {
  //          type uint32;
  //          type string {
  //            pattern "<.*>|$.*";
  //          }
  //        }
  //      }
  //      leaf labeled-preference {
  //        description "Preference of labeled routes";
  //        type union {
  //          type uint32;
  //          type string {
  //            pattern "<.*>|$.*";
  //          }
  //        }
  //      }
  //      leaf-list export {
  //        ordered-by user;
  //        description "Export policy";
  //        type jt:policy-algebra;
  //      }
  //      leaf-list import {
  //        ordered-by user;
  //        description "Import policy (for external routes or setting priority)";
  //        type jt:policy-algebra;
  //      }
  //      leaf reference-bandwidth {
  //        description "Bandwidth for calculating metric defaults";
  //        type string;
  //      }
  //      leaf lsa-refresh-interval {
  //        description "LSA refresh interval (minutes)";
  //        default "50";
  //        type union {
  //          type string {
  //            pattern "<.*>|$.*";
  //          }
  //          type uint32 {
  //            range "25 .. 50";
  //          }
  //        }
  //      }
  //      leaf spf-delay {
  //        description "Time to wait before running an SPF";
  //        status deprecated;
  //        units "milliseconds";
  //        type union {
  //          type string {
  //            pattern "<.*>|$.*";
  //          }
  //          type uint32 {
  //            range "50 .. 8000";
  //          }
  //        }
  //      }
  //      leaf no-rfc-1583 {
  //        description "Disable RFC1583 compatibility";
  //        type empty;
  //      }
  //      leaf forwarding-address-to-broadcast {
  //        description "Set forwarding address in Type 5 LSA in broadcast network";
  //        type empty;
  //      }
  //      choice nssa-abr-option {
  //        case case_1 {
  //          leaf no-nssa-abr {
  //            description "Disable full NSSA functionality at ABR";
  //            type empty;
  //          }
  //        }
  //      }
  //      container sham-link {
  //        presence "enable sham-link";
  //        description "Configure parameters for sham links";
  //        // uses apply-advanced;
  //        leaf local {
  //          description "Local sham link endpoint address";
  //          type jt:ipaddr;
  //        }
  //        leaf no-advertise-local {
  //          description "Don't advertise local sham link endpoint as stub in router LSA";
  //          status deprecated;
  //          type empty;
  //        }
  //      }
  //    }
  //    // uses apply-advanced;
  //    list topology {
  //      key name;
  //      ordered-by user;
  //      description "Topology parameters";
  //      leaf name {
  //        description "Topology name";
  //        type string;
  //      }
  //      // uses apply-advanced;
  //      leaf disable {
  //        description "Disable this topology";
  //        type empty;
  //      }
  //      leaf topology-id {
  //        description "Topology identifier";
  //        type union {
  //          type string {
  //            pattern "<.*>|$.*";
  //          }
  //          type uint8 {
  //            range "32 .. 127";
  //          }
  //        }
  //      }
  //      leaf overload {
  //        description "Set the overload mode (repel transit traffic)";
  //        type empty;
  //      }
  //      leaf rib-group {
  //        description "Routing table group for importing routes";
  //        type string;
  //      }
  //      container spf-options {
  //        description "Configure options for SPF";
  //        // uses apply-advanced;
  //        container microloop-avoidance {
  //          description "Configure microloop avoidance mechanism";
  //          // uses apply-advanced;
  //          container post-convergence-path {
  //            presence "enable post-convergence-path";
  //            description "Temporarily install post-convergence path for routes potentially affected by microloops";
  //            // uses apply-advanced;
  //            leaf delay {
  //              description "Time after which temporary post-convergence paths are removed";
  //              units "milliseconds";
  //              type union {
  //                type string {
  //                  pattern "<.*>|$.*";
  //                }
  //                type uint32 {
  //                  range "500 .. 60000";
  //                }
  //              }
  //            }
  //            leaf maximum-labels {
  //              description "Maximum number of labels installed for post-convergence paths";
  //              type union {
  //                type string {
  //                  pattern "<.*>|$.*";
  //                }
  //                type uint32 {
  //                  range "2 .. 8";
  //                }
  //              }
  //            }
  //          }
  //        }
  //        leaf delay {
  //          description "Time to wait before running an SPF";
  //          units "milliseconds";
  //          type union {
  //            type string {
  //              pattern "<.*>|$.*";
  //            }
  //            type uint32 {
  //              range "50 .. 8000";
  //            }
  //          }
  //        }
  //        leaf holddown {
  //          description "Time to hold down before running an SPF";
  //          units "milliseconds";
  //          type union {
  //            type string {
  //              pattern "<.*>|$.*";
  //            }
  //            type uint32 {
  //              range "2000 .. 20000";
  //            }
  //          }
  //        }
  //        leaf rapid-runs {
  //          description "Number of maximum rapid SPF runs before holddown";
  //          type union {
  //            type string {
  //              pattern "<.*>|$.*";
  //            }
  //            type uint32 {
  //              range "1 .. 10";
  //            }
  //          }
  //        }
  //        leaf no-ignore-our-externals {
  //          description "Do not ignore self-generated external and NSSA LSAs";
  //          type empty;
  //        }
  //      }
  //      container backup-spf-options {
  //        description "Configure options for backup SPF";
  //        // uses apply-advanced;
  //        container remote-backup-calculation {
  //          presence "enable remote-backup-calculation";
  //          description "Calculate Remote LFA backup nexthops";
  //          // uses apply-advanced;
  //          container pq-nodes-nearest-to-source {
  //            description "PQ nodes selection based upon nearest to source";
  //            // uses apply-advanced;
  //            leaf percent {
  //              description "Selection percentage for nearest to source";
  //              type union {
  //                type string {
  //                  pattern "<.*>|$.*";
  //                }
  //                type uint32 {
  //                  range "10 .. 100";
  //                }
  //              }
  //            }
  //          }
  //        }
  //        container use-post-convergence-lfa {
  //          presence "enable use-post-convergence-lfa";
  //          description "Calculate post-convergence backup paths";
  //          // uses apply-advanced;
  //          leaf maximum-labels {
  //            description "Maximum number of labels installed for post-convergence paths";
  //            type union {
  //              type string {
  //                pattern "<.*>|$.*";
  //              }
  //              type uint32 {
  //                range "2 .. 8";
  //              }
  //            }
  //          }
  //          leaf maximum-backup-paths {
  //            description "Maximum number of equal-cost post-convergence paths installed";
  //            type union {
  //              type string {
  //                pattern "<.*>|$.*";
  //              }
  //              type uint32 {
  //                range "1 .. 8";
  //              }
  //            }
  //          }
  //        }
  //        leaf use-source-packet-routing {
  //          description "Use spring backup paths for inet.0 routes";
  //          type empty;
  //        }
  //        leaf disable {
  //          description "Do not run backup SPF";
  //          type empty;
  //        }
  //        leaf no-install {
  //          description "Do not install backup nexthops into the RIB";
  //          type empty;
  //        }
  //        leaf downstream-paths-only {
  //          description "Use only downstream backup paths";
  //          type empty;
  //        }
  //        container per-prefix-calculation {
  //          description "Calculate backup nexthops for non-best prefix originators";
  //          // uses apply-advanced;
  //          leaf stubs {
  //            description "Per prefix calculation for stubs only";
  //            type empty;
  //          }
  //          leaf summary {
  //            description "Per prefix calculation for summary originators only";
  //            type empty;
  //          }
  //          leaf externals {
  //            description "Per prefix calculation for externals";
  //            type empty;
  //          }
  //          leaf all {
  //            description "Per prefix calculation for all";
  //            type empty;
  //          }
  //        }
  //        leaf node-link-degradation {
  //          description "Degrade to link protection when nodelink protection not available";
  //          type empty;
  //        }
  //      }
  //      leaf prefix-export-limit {
  //        description "Maximum number of prefixes that can be exported";
  //        type union {
  //          type string {
  //            pattern "<.*>|$.*";
  //          }
  //          type uint32 {
  //            range "0 .. 4294967295";
  //          }
  //        }
  //      }
  //    }
  //    container spf-options {
  //      description "Configure options for SPF";
  //      // uses apply-advanced;
  //      container microloop-avoidance {
  //        description "Configure microloop avoidance mechanism";
  //        // uses apply-advanced;
  //        container post-convergence-path {
  //          presence "enable post-convergence-path";
  //          description "Temporarily install post-convergence path for routes potentially affected by microloops";
  //          // uses apply-advanced;
  //          leaf delay {
  //            description "Time after which temporary post-convergence paths are removed";
  //            units "milliseconds";
  //            type union {
  //              type string {
  //                pattern "<.*>|$.*";
  //              }
  //              type uint32 {
  //                range "500 .. 60000";
  //              }
  //            }
  //          }
  //          leaf maximum-labels {
  //            description "Maximum number of labels installed for post-convergence paths";
  //            type union {
  //              type string {
  //                pattern "<.*>|$.*";
  //              }
  //              type uint32 {
  //                range "2 .. 8";
  //              }
  //            }
  //          }
  //        }
  //      }
  //      leaf delay {
  //        description "Time to wait before running an SPF";
  //        units "milliseconds";
  //        type union {
  //          type string {
  //            pattern "<.*>|$.*";
  //          }
  //          type uint32 {
  //            range "50 .. 8000";
  //          }
  //        }
  //      }
  //      leaf holddown {
  //        description "Time to hold down before running an SPF";
  //        units "milliseconds";
  //        type union {
  //          type string {
  //            pattern "<.*>|$.*";
  //          }
  //          type uint32 {
  //            range "2000 .. 20000";
  //          }
  //        }
  //      }
  //      leaf rapid-runs {
  //        description "Number of maximum rapid SPF runs before holddown";
  //        type union {
  //          type string {
  //            pattern "<.*>|$.*";
  //          }
  //          type uint32 {
  //            range "1 .. 10";
  //          }
  //        }
  //      }
  //      leaf no-ignore-our-externals {
  //        description "Do not ignore self-generated external and NSSA LSAs";
  //        type empty;
  //      }
  //    }
  //    container backup-spf-options {
  //      description "Configure options for backup SPF";
  //      // uses apply-advanced;
  //      container remote-backup-calculation {
  //        presence "enable remote-backup-calculation";
  //        description "Calculate Remote LFA backup nexthops";
  //        // uses apply-advanced;
  //        container pq-nodes-nearest-to-source {
  //          description "PQ nodes selection based upon nearest to source";
  //          // uses apply-advanced;
  //          leaf percent {
  //            description "Selection percentage for nearest to source";
  //            type union {
  //              type string {
  //                pattern "<.*>|$.*";
  //              }
  //              type uint32 {
  //                range "10 .. 100";
  //              }
  //            }
  //          }
  //        }
  //      }
  //      container use-post-convergence-lfa {
  //        presence "enable use-post-convergence-lfa";
  //        description "Calculate post-convergence backup paths";
  //        // uses apply-advanced;
  //        leaf maximum-labels {
  //          description "Maximum number of labels installed for post-convergence paths";
  //          type union {
  //            type string {
  //              pattern "<.*>|$.*";
  //            }
  //            type uint32 {
  //              range "2 .. 8";
  //            }
  //          }
  //        }
  //        leaf maximum-backup-paths {
  //          description "Maximum number of equal-cost post-convergence paths installed";
  //          type union {
  //            type string {
  //              pattern "<.*>|$.*";
  //            }
  //            type uint32 {
  //              range "1 .. 8";
  //            }
  //          }
  //        }
  //      }
  //      leaf use-source-packet-routing {
  //        description "Use spring backup paths for inet.0 routes";
  //        type empty;
  //      }
  //      leaf disable {
  //        description "Do not run backup SPF";
  //        type empty;
  //      }
  //      leaf no-install {
  //        description "Do not install backup nexthops into the RIB";
  //        type empty;
  //      }
  //      leaf downstream-paths-only {
  //        description "Use only downstream backup paths";
  //        type empty;
  //      }
  //      container per-prefix-calculation {
  //        description "Calculate backup nexthops for non-best prefix originators";
  //        // uses apply-advanced;
  //        leaf stubs {
  //          description "Per prefix calculation for stubs only";
  //          type empty;
  //        }
  //        leaf summary {
  //          description "Per prefix calculation for summary originators only";
  //          type empty;
  //        }
  //        leaf externals {
  //          description "Per prefix calculation for externals";
  //          type empty;
  //        }
  //        leaf all {
  //          description "Per prefix calculation for all";
  //          type empty;
  //        }
  //      }
  //      leaf node-link-degradation {
  //        description "Degrade to link protection when nodelink protection not available";
  //        type empty;
  //      }
  //    }
  //    container traffic-engineering {
  //      presence "enable traffic-engineering";
  //      description "Configure traffic engineering attributes";
  //      // uses apply-advanced;
  //      leaf no-topology {
  //        description "Disable dissemination of TE link-state topology information";
  //        type empty;
  //      }
  //      leaf multicast-rpf-routes {
  //        description "Install routes for multicast RPF checks into inet.2";
  //        type empty;
  //      }
  //      leaf l3-unicast-topology {
  //        description "Download IGP topology into TED";
  //        type empty;
  //      }
  //      container ignore-lsp-metrics {
  //        presence "enable ignore-lsp-metrics";
  //        description "Ignore label-switched path metrics when doing shortcuts";
  //        // uses apply-advanced;
  //        leaf unconfigured-only {
  //          description "Ignore lsp metrics for unconfigured only";
  //          type empty;
  //        }
  //      }
  //      container shortcuts {
  //        presence "enable shortcuts";
  //        description "Use label-switched paths as next hops, if possible";
  //        // uses apply-advanced;
  //        leaf ignore-lsp-metrics {
  //          description "Ignore label-switched path metrics when doing shortcuts";
  //          status deprecated;
  //          type empty;
  //        }
  //        leaf lsp-metric-into-summary {
  //          description "Advertise LSP metric into summary LSAs";
  //          type empty;
  //        }
  //        list family {
  //          key name;
  //          ordered-by user;
  //          description "Address family specific traffic-engineering attributes";
  //          leaf name {
  //            type enumeration {
  //              enum "inet" {
  //                description "IPv4 family";
  //              }
  //              enum "inet-mpls" {
  //                description "IPv4-MPLS family";
  //              }
  //            }
  //          }
  //          // uses apply-advanced;
  //        }
  //      }
  //      leaf advertise-unnumbered-interfaces {
  //        description "Advertise unnumbered interfaces";
  //        type empty;
  //      }
  //      leaf credibility-protocol-preference {
  //        description "TED protocol credibility follows protocol preference";
  //        type empty;
  //      }
  //      container advertisement {
  //        description "Advertise TE parameters even if RSVP is not turned on";
  //        // uses apply-advanced;
  //        leaf always {
  //          description "Advertise TE parameters in TE LSAs";
  //          type empty;
  //        }
  //      }
  //      container tunnel-source-protocol {
  //        description "Protocols from which to pick label-switched paths";
  //        // uses apply-advanced;
  //        container rsvp {
  //          presence "enable rsvp";
  //          description "Pick label-switched paths from rsvp";
  //          // uses apply-advanced;
  //          leaf preference {
  //            description "Preference for label-switched paths from this protocol";
  //            type union {
  //              type string {
  //                pattern "<.*>|$.*";
  //              }
  //              type uint32 {
  //                range "1 .. 255";
  //              }
  //            }
  //          }
  //        }
  //        container spring-te {
  //          presence "enable spring-te";
  //          description "Pick label-switched paths from spring-te";
  //          // uses apply-advanced;
  //          leaf preference {
  //            description "Preference for label-switched paths from this protocol";
  //            type union {
  //              type string {
  //                pattern "<.*>|$.*";
  //              }
  //              type uint32 {
  //                range "1 .. 255";
  //              }
  //            }
  //          }
  //        }
  //      }
  //    }
  //    container source-packet-routing {
  //      presence "enable source-packet-routing";
  //      description "Enable source packet routing (SPRING)";
  //      // uses apply-advanced;
  //      container adjacency-segment {
  //        description "Attributes for adjacency segments in spring";
  //        // uses apply-advanced;
  //        leaf hold-time {
  //          description "Retain time of Adjacency segment after isolating from an interface";
  //          type union {
  //            type string {
  //              pattern "<.*>|$.*";
  //            }
  //            type uint32 {
  //              range "180000 .. 900000";
  //            }
  //          }
  //        }
  //      }
  //      leaf-list prefix-segment {
  //        ordered-by user;
  //        description "Prefix Segment policy";
  //        type jt:policy-algebra;
  //      }
  //      leaf explicit-null {
  //        description "Set E and P bits in all Prefix SID advertisements";
  //        type empty;
  //      }
  //      container node-segment {
  //        presence "enable node-segment";
  //        description "Enable support for Node segments in SPRING";
  //        // uses apply-advanced;
  //        leaf ipv4-index {
  //          description "Set ipv4 node segment index";
  //          type union {
  //            type string {
  //              pattern "<.*>|$.*";
  //            }
  //            type uint32 {
  //              range "0 .. 199999";
  //            }
  //          }
  //        }
  //        leaf index-range {
  //          description "Set range of node segment indices allowed";
  //          type union {
  //            type string {
  //              pattern "<.*>|$.*";
  //            }
  //            type uint32 {
  //              range "32 .. 16385";
  //            }
  //          }
  //        }
  //      }
  //      container srgb {
  //        description "Set the SRGB global block in SPRING";
  //        leaf start-label {
  //          description "Start range for SRGB label block";
  //          type union {
  //            type string {
  //              pattern "<.*>|$.*";
  //            }
  //            type uint32;
  //          }
  //        }
  //        leaf index-range {
  //          description "Index to the SRGB start label block";
  //          type union {
  //            type string {
  //              pattern "<.*>|$.*";
  //            }
  //            type uint32;
  //          }
  //        }
  //      }
  //      leaf mapping-server {
  //        description "Mapping server name";
  //        type string;
  //      }
  //      leaf install-prefix-sid-for-best-route {
  //        description "For best route install a exact prefix sid route";
  //        type empty;
  //      }
  //      leaf ldp-stitching {
  //        description "Enable SR to LDP stitching";
  //        type empty;
  //      }
  //      leaf-list flex-algorithm {
  //        description "Flex-algorithms we would like to participate in";
  //        type union {
  //          type string {
  //            pattern "<.*>|$.*";
  //          }
  //          type uint32 {
  //            range "128 .. 255";
  //          }
  //        }
  //        max-elements 16;
  //      }
  //      leaf strict-asla-based-flex-algorithm {
  //        description "Flex-Algorithm to ignore links not having ASLA sub-TLVs";
  //        type empty;
  //      }
  //      container sensor-based-stats {
  //        description "Configure sensor based stats in SPRING";
  //        // uses apply-advanced;
  //        container per-interface-per-member-link {
  //          description "Configure sensor based stats per nexthop";
  //          leaf ingress {
  //            description "Enable sensor based stats on ingress interface";
  //            type empty;
  //          }
  //          leaf egress {
  //            description "Enable sensor based stats on egress interface";
  //            type empty;
  //          }
  //        }
  //        container per-sid {
  //          description "Configure sensor based stats per spring route";
  //          leaf ingress {
  //            description "Enable sensor based stats for per-sid ingress accounting";
  //            type empty;
  //          }
  //          leaf egress {
  //            description "Enable sensor based stats for IP-MPLS egress accounting";
  //            type empty;
  //          }
  //        }
  //      }
  //    }
  //    list area {
  //      key name;
  //      ordered-by user;
  //      description "Configure an OSPF area";
  //      leaf name {
  //        description "Area ID";
  //        type jt:areaid;
  //      }
  //      // uses apply-advanced;
  //      choice stub-option {
  //        case case_1 {
  //          container stub {
  //            presence "enable stub";
  //            description "Configure a stub area";
  //            leaf default-metric {
  //              description "Metric for the default route in this stub area";
  //              type union {
  //                type string {
  //                  pattern "<.*>|$.*";
  //                }
  //                type uint32 {
  //                  range "1 .. 16777215";
  //                }
  //              }
  //            }
  //            choice summaries-choice {
  //              leaf summaries {
  //                description "Flood summary LSAs into this stub area";
  //                type empty;
  //              }
  //              leaf no-summaries {
  //                description "Don't flood summary LSAs into this stub area";
  //                type empty;
  //              }
  //            }
  //          }
  //        }
  //        case case_2 {
  //          container nssa {
  //            presence "enable nssa";
  //            description "Configure a not-so-stubby area";
  //            // uses apply-advanced;
  //            container default-lsa {
  //              presence "enable default-lsa";
  //              description "Configure a default LSA";
  //              // uses apply-advanced;
  //              leaf default-metric {
  //                description "Metric for the default route in this area";
  //                type union {
  //                  type string {
  //                    pattern "<.*>|$.*";
  //                  }
  //                  type uint32 {
  //                    range "1 .. 16777215";
  //                  }
  //                }
  //              }
  //              leaf metric-type {
  //                description "External metric type for the default type 7 LSA";
  //                type union {
  //                  type string {
  //                    pattern "<.*>|$.*";
  //                  }
  //                  type uint32 {
  //                    range "1 .. 2";
  //                  }
  //                }
  //              }
  //              leaf type-7 {
  //                description "Flood type 7 default LSA if no-summaries is configured";
  //                type empty;
  //              }
  //            }
  //            leaf default-metric {
  //              description "Metric for the default route in this area";
  //              status deprecated;
  //              type union {
  //                type string {
  //                  pattern "<.*>|$.*";
  //                }
  //                type uint32 {
  //                  range "1 .. 16777215";
  //                }
  //              }
  //            }
  //            leaf metric-type {
  //              description "External metric type for the default type 7 LSA";
  //              status deprecated;
  //              type union {
  //                type string {
  //                  pattern "<.*>|$.*";
  //                }
  //                type uint32 {
  //                  range "1 .. 2";
  //                }
  //              }
  //            }
  //            choice summaries-choice {
  //              leaf summaries {
  //                description "Flood summary LSAs into this NSSA area";
  //                type empty;
  //              }
  //              leaf no-summaries {
  //                description "Don't flood summary LSAs into this NSSA area";
  //                type empty;
  //              }
  //            }
  //            list area-range {
  //              key name;
  //              ordered-by user;
  //              description "Configure NSSA area ranges";
  //              leaf name {
  //                description "Range to summarize NSSA routes in this area";
  //                type jt:ipprefix;
  //              }
  //              // uses apply-advanced;
  //              leaf restrict {
  //                description "Restrict advertisement of this area range";
  //                type empty;
  //              }
  //              leaf exact {
  //                description "Enforce exact match for advertisement of this area range";
  //                type empty;
  //              }
  //              container override-metric {
  //                presence "enable override-metric";
  //                description "Override the dynamic metric for this area-range";
  //                // uses apply-advanced;
  //                leaf metric {
  //                  description "Metric value";
  //                  type union {
  //                    type string {
  //                      pattern "<.*>|$.*";
  //                    }
  //                    type uint32 {
  //                      range "1 .. 16777215";
  //                    }
  //                  }
  //                }
  //                leaf metric-type {
  //                  description "Set the metric type for the override metric";
  //                  default "1";
  //                  type union {
  //                    type string {
  //                      pattern "<.*>|$.*";
  //                    }
  //                    type uint32 {
  //                      range "1 .. 2";
  //                    }
  //                  }
  //                }
  //              }
  //            }
  //          }
  //        }
  //      }
  //      list area-range {
  //        key name;
  //        ordered-by user;
  //        description "Configure area ranges";
  //        leaf name {
  //          description "Range to summarize routes in this area";
  //          type jt:ipprefix;
  //        }
  //        // uses apply-advanced;
  //        leaf restrict {
  //          description "Restrict advertisement of this area range";
  //          type empty;
  //        }
  //        leaf exact {
  //          description "Enforce exact match for advertisement of this area range";
  //          type empty;
  //        }
  //        leaf override-metric {
  //          description "Override the dynamic metric for this area-range";
  //          type union {
  //            type string {
  //              pattern "<.*>|$.*";
  //            }
  //            type uint32 {
  //              range "1 .. 16777215";
  //            }
  //          }
  //        }
  //      }
  //      leaf-list network-summary-export {
  //        ordered-by user;
  //        description "Export policy for Type 3 Summary LSAs";
  //        type jt:policy-algebra;
  //      }
  //      leaf-list network-summary-import {
  //        ordered-by user;
  //        description "Import policy for Type 3 Summary LSAs";
  //        type jt:policy-algebra;
  //      }
  //      leaf-list inter-area-prefix-export {
  //        ordered-by user;
  //        description "Export policy for Inter Area Prefix LSAs";
  //        type jt:policy-algebra;
  //      }
  //      leaf-list inter-area-prefix-import {
  //        ordered-by user;
  //        description "Import policy for Inter Area Prefix LSAs";
  //        type jt:policy-algebra;
  //      }
  //      leaf authentication-type {
  //        description "Authentication type";
  //        status deprecated;
  //        type enumeration {
  //          enum "none" {
  //            description "No authentication";
  //            status deprecated;
  //          }
  //          enum "simple" {
  //            description "Simple password authentication";
  //            status deprecated;
  //          }
  //          enum "md5" {
  //            description "MD5 authentication";
  //            status deprecated;
  //          }
  //        }
  //      }
  //      list virtual-link {
  //        key "neighbor-id transit-area";
  //        ordered-by user;
  //        description "Configure virtual links";
  //        leaf neighbor-id {
  //          description "Router ID of a virtual neighbor";
  //          type jt:ipv4addr;
  //        }
  //        leaf transit-area {
  //          description "Transit area in common with virtual neighbor";
  //          type jt:areaid;
  //        }
  //        // uses apply-advanced;
  //        choice enable-disable {
  //          case case_1 {
  //            leaf disable {
  //              description "Disable this virtual link";
  //              type empty;
  //            }
  //          }
  //        }
  //        leaf retransmit-interval {
  //          description "Retransmission interval (seconds)";
  //          type union {
  //            type string {
  //              pattern "<.*>|$.*";
  //            }
  //            type uint32 {
  //              range "1 .. 65535";
  //            }
  //          }
  //        }
  //        leaf transit-delay {
  //          description "Transit delay (seconds)";
  //          type union {
  //            type string {
  //              pattern "<.*>|$.*";
  //            }
  //            type uint32 {
  //              range "1 .. 65535";
  //            }
  //          }
  //        }
  //        leaf hello-interval {
  //          description "Hello interval (seconds)";
  //          type union {
  //            type string {
  //              pattern "<.*>|$.*";
  //            }
  //            type uint32 {
  //              range "1 .. 255";
  //            }
  //          }
  //        }
  //        leaf dead-interval {
  //          description "Dead interval (seconds)";
  //          type union {
  //            type string {
  //              pattern "<.*>|$.*";
  //            }
  //            type uint32 {
  //              range "1 .. 65535";
  //            }
  //          }
  //        }
  //        leaf mtu {
  //          description "Maximum OSPF packet size";
  //          type union {
  //            type string {
  //              pattern "<.*>|$.*";
  //            }
  //            type uint32 {
  //              range "128 .. 65535";
  //            }
  //          }
  //        }
  //        choice auth {
  //          case case_1 {
  //            container authentication {
  //              uses juniper-ospf-authentication;
  //            }
  //          }
  //          case case_2 {
  //            container authentication-key {
  //              description "Authentication key";
  //              status deprecated;
  //              leaf keyname {
  //                description "Authentication key value";
  //                type jt:unreadable;
  //              }
  //              leaf key-id {
  //                description "Key ID for MD5 authentication";
  //                type union {
  //                  type string {
  //                    pattern "<.*>|$.*";
  //                  }
  //                  type uint32 {
  //                    range "0 .. 255";
  //                  }
  //                }
  //              }
  //            }
  //          }
  //        }
  //        leaf demand-circuit {
  //          description "Interface functions as a demand circuit";
  //          type empty;
  //        }
  //        leaf flood-reduction {
  //          description "Enable flood reduction";
  //          type empty;
  //        }
  //        leaf no-neighbor-down-notification {
  //          description "Don't inform other protocols about neighbor down events";
  //          type empty;
  //        }
  //        leaf ipsec-sa {
  //          description "IPSec security association name";
  //          type string {
  //            length "1 .. 32";
  //          }
  //        }
  //        list topology {
  //          key name;
  //          ordered-by user;
  //          description "Topology specific attributes";
  //          leaf name {
  //            description "Topology name";
  //            type string;
  //          }
  //          // uses apply-advanced;
  //          leaf disable {
  //            description "Disable this topology";
  //            type empty;
  //          }
  //          leaf metric {
  //            description "Topology metric";
  //            type union {
  //              type string {
  //                pattern "<.*>|$.*";
  //              }
  //              type uint16 {
  //                range "1 .. 65535";
  //              }
  //            }
  //          }
  //          container bandwidth-based-metrics {
  //            description "Configure bandwidth based metrics";
  //            // uses apply-advanced;
  //            list bandwidth {
  //              key name;
  //              description "Bandwidth threshold";
  //              leaf name {
  //                type string;
  //              }
  //              leaf metric {
  //                description "Metric associated with specified bandwidth";
  //                type union {
  //                  type string {
  //                    pattern "<.*>|$.*";
  //                  }
  //                  type uint16 {
  //                    range "1 .. 65535";
  //                  }
  //                }
  //              }
  //            }
  //          }
  //        }
  //      }
  //      list sham-link-remote {
  //        key name;
  //        ordered-by user;
  //        description "Configure parameters for remote sham link endpoint";
  //        leaf name {
  //          description "Remote sham link endpoint address";
  //          type jt:ipaddr;
  //        }
  //        // uses apply-advanced;
  //        leaf metric {
  //          description "Sham link metric";
  //          type union {
  //            type string {
  //              pattern "<.*>|$.*";
  //            }
  //            type uint16 {
  //              range "1 .. 65535";
  //            }
  //          }
  //        }
  //        leaf ipsec-sa {
  //          description "IPSec security association name";
  //          type string {
  //            length "1 .. 32";
  //          }
  //        }
  //        leaf demand-circuit {
  //          description "Interface functions as a demand circuit";
  //          type empty;
  //        }
  //        leaf flood-reduction {
  //          description "Enable flood reduction";
  //          type empty;
  //        }
  //        list topology {
  //          key name;
  //          ordered-by user;
  //          description "Topology specific attributes";
  //          leaf name {
  //            description "Topology name";
  //            type string;
  //          }
  //          // uses apply-advanced;
  //          leaf disable {
  //            description "Disable this topology";
  //            type empty;
  //          }
  //          leaf metric {
  //            description "Topology metric";
  //            type union {
  //              type string {
  //                pattern "<.*>|$.*";
  //              }
  //              type uint16 {
  //                range "1 .. 65535";
  //              }
  //            }
  //          }
  //          container bandwidth-based-metrics {
  //            description "Configure bandwidth based metrics";
  //            // uses apply-advanced;
  //            list bandwidth {
  //              key name;
  //              description "Bandwidth threshold";
  //              leaf name {
  //                type string;
  //              }
  //              leaf metric {
  //                description "Metric associated with specified bandwidth";
  //                type union {
  //                  type string {
  //                    pattern "<.*>|$.*";
  //                  }
  //                  type uint16 {
  //                    range "1 .. 65535";
  //                  }
  //                }
  //              }
  //            }
  //          }
  //        }
  //      }
  //      list interface {
  //        key name;
  //        ordered-by user;
  //        description "Include an interface in this area";
  //        leaf name {
  //          description "Interface name";
  //          type union {
  //            type jt:ipv4addr-or-interface;
  //            type string {
  //              pattern "<.*>|$.*";
  //            }
  //          }
  //        }
  //        // uses apply-advanced;
  //        choice enable-disable {
  //          case case_1 {
  //            leaf disable {
  //              description "Disable OSPF on this interface";
  //              type empty;
  //            }
  //          }
  //        }
  //        leaf interface-type {
  //          description "Type of interface";
  //          type enumeration {
  //            enum "nbma" {
  //              description "Nonbroadcast multiaccess";
  //            }
  //            enum "p2mp" {
  //              description "Point-to-multipoint NBMA";
  //            }
  //            enum "p2p" {
  //              description "Point-to-point";
  //            }
  //            enum "p2mp-over-lan" {
  //              description "Point-to-multipoint over LAN mode";
  //            }
  //          }
  //        }
  //        choice protection-type {
  //          case case_1 {
  //            leaf link-protection {
  //              description "Protect interface from link faults only";
  //              type empty;
  //            }
  //          }
  //          case case_2 {
  //            leaf node-link-protection {
  //              description "Protect interface from both link and node faults";
  //              type empty;
  //            }
  //          }
  //        }
  //        leaf no-eligible-backup {
  //          description "Not eligible to backup traffic from protected interfaces";
  //          type empty;
  //        }
  //        leaf no-eligible-remote-backup {
  //          description "Not eligible for Remote-LFA backup traffic from protected interfaces";
  //          type empty;
  //        }
  //        container passive {
  //          presence "enable passive";
  //          description "Do not run OSPF, but advertise it";
  //          // uses apply-advanced;
  //          container traffic-engineering {
  //            description "Advertise TE link information";
  //            // uses apply-advanced;
  //            leaf remote-node-id {
  //              description "Remote address of the link";
  //              type jt:ipaddr;
  //            }
  //            leaf remote-node-router-id {
  //              description "TE Router-ID of the remote node";
  //              type jt:ipv4addr;
  //            }
  //          }
  //        }
  //        leaf secondary {
  //          description "Treat interface as secondary";
  //          type empty;
  //        }
  //        leaf own-router-lsa {
  //          description "Generate a separate router LSA for this interface";
  //          type empty;
  //        }
  //        container bandwidth-based-metrics {
  //          description "Configure bandwidth based metrics";
  //          // uses apply-advanced;
  //          list bandwidth {
  //            key name;
  //            description "Bandwidth threshold";
  //            leaf name {
  //              type string;
  //            }
  //            leaf metric {
  //              description "Metric associated with specified bandwidth";
  //              type union {
  //                type string {
  //                  pattern "<.*>|$.*";
  //                }
  //                type uint16 {
  //                  range "1 .. 65535";
  //                }
  //              }
  //            }
  //          }
  //        }
  //        leaf metric {
  //          description "Interface metric";
  //          type union {
  //            type string {
  //              pattern "<.*>|$.*";
  //            }
  //            type uint16 {
  //              range "1 .. 65535";
  //            }
  //          }
  //        }
  //        leaf priority {
  //          description "Designated router priority";
  //          type union {
  //            type string {
  //              pattern "<.*>|$.*";
  //            }
  //            type uint32 {
  //              range "0 .. 255";
  //            }
  //          }
  //        }
  //        leaf retransmit-interval {
  //          description "Retransmission interval (seconds)";
  //          type union {
  //            type string {
  //              pattern "<.*>|$.*";
  //            }
  //            type uint32 {
  //              range "1 .. 65535";
  //            }
  //          }
  //        }
  //        leaf transit-delay {
  //          description "Transit delay (seconds)";
  //          type union {
  //            type string {
  //              pattern "<.*>|$.*";
  //            }
  //            type uint32 {
  //              range "1 .. 65535";
  //            }
  //          }
  //        }
  //        leaf hello-interval {
  //          description "Hello interval (seconds)";
  //          type union {
  //            type string {
  //              pattern "<.*>|$.*";
  //            }
  //            type uint32 {
  //              range "1 .. 255";
  //            }
  //          }
  //        }
  //        leaf dead-interval {
  //          description "Dead interval (seconds)";
  //          type union {
  //            type string {
  //              pattern "<.*>|$.*";
  //            }
  //            type uint32 {
  //              range "1 .. 65535";
  //            }
  //          }
  //        }
  //        leaf mtu {
  //          description "Maximum OSPF packet size";
  //          type union {
  //            type string {
  //              pattern "<.*>|$.*";
  //            }
  //            type uint32 {
  //              range "128 .. 65535";
  //            }
  //          }
  //        }
  //        choice auth {
  //          case case_1 {
  //            container authentication {
  //              uses juniper-ospf-authentication;
  //            }
  //          }
  //          case case_2 {
  //            container authentication-key {
  //              description "Authentication key";
  //              status deprecated;
  //              leaf keyname {
  //                description "Authentication key value";
  //                type jt:unreadable;
  //              }
  //              leaf key-id {
  //                description "Key ID for MD5 authentication";
  //                type union {
  //                  type string {
  //                    pattern "<.*>|$.*";
  //                  }
  //                  type uint32 {
  //                    range "0 .. 255";
  //                  }
  //                }
  //              }
  //            }
  //          }
  //        }
  //        leaf demand-circuit {
  //          description "Interface functions as a demand circuit";
  //          type empty;
  //        }
  //        leaf flood-reduction {
  //          description "Enable flood reduction";
  //          type empty;
  //        }
  //        leaf no-neighbor-down-notification {
  //          description "Don't inform other protocols about neighbor down events";
  //          type empty;
  //        }
  //        leaf ipsec-sa {
  //          description "IPSec security association name";
  //          type string {
  //            length "1 .. 32";
  //          }
  //        }
  //        list topology {
  //          key name;
  //          ordered-by user;
  //          description "Topology specific attributes";
  //          leaf name {
  //            description "Topology name";
  //            type string;
  //          }
  //          // uses apply-advanced;
  //          leaf disable {
  //            description "Disable this topology";
  //            type empty;
  //          }
  //          leaf metric {
  //            description "Topology metric";
  //            type union {
  //              type string {
  //                pattern "<.*>|$.*";
  //              }
  //              type uint16 {
  //                range "1 .. 65535";
  //              }
  //            }
  //          }
  //          container bandwidth-based-metrics {
  //            description "Configure bandwidth based metrics";
  //            // uses apply-advanced;
  //            list bandwidth {
  //              key name;
  //              description "Bandwidth threshold";
  //              leaf name {
  //                type string;
  //              }
  //              leaf metric {
  //                description "Metric associated with specified bandwidth";
  //                type union {
  //                  type string {
  //                    pattern "<.*>|$.*";
  //                  }
  //                  type uint16 {
  //                    range "1 .. 65535";
  //                  }
  //                }
  //              }
  //            }
  //          }
  //        }
  //        leaf transmit-interval {
  //          description "OSPF packet transmit interval (milliseconds)";
  //          status deprecated;
  //          type union {
  //            type string {
  //              pattern "<.*>|$.*";
  //            }
  //            type uint32 {
  //              range "1 .. 4294967295";
  //            }
  //          }
  //        }
  //        container bfd-liveness-detection {
  //          description "Bidirectional Forwarding Detection options";
  //          // uses apply-advanced;
  //          leaf version {
  //            description "BFD protocol version number";
  //            default "automatic";
  //            type enumeration {
  //              enum "0" {
  //                description "BFD version 0 (deprecated)";
  //              }
  //              enum "1" {
  //                description "BFD version 1";
  //              }
  //              enum "automatic" {
  //                description "Choose BFD version automatically";
  //              }
  //            }
  //          }
  //          leaf minimum-interval {
  //            description "Minimum transmit and receive interval";
  //            units "milliseconds";
  //            type union {
  //              type string {
  //                pattern "<.*>|$.*";
  //              }
  //              type uint32 {
  //                range "1 .. 255000";
  //              }
  //            }
  //          }
  //          leaf minimum-transmit-interval {
  //            description "Minimum transmit interval";
  //            status deprecated;
  //            units "milliseconds";
  //            type union {
  //              type string {
  //                pattern "<.*>|$.*";
  //              }
  //              type uint32 {
  //                range "1 .. 255000";
  //              }
  //            }
  //          }
  //          leaf minimum-receive-interval {
  //            description "Minimum receive interval";
  //            units "milliseconds";
  //            type union {
  //              type string {
  //                pattern "<.*>|$.*";
  //              }
  //              type uint32 {
  //                range "1 .. 255000";
  //              }
  //            }
  //          }
  //          leaf multiplier {
  //            description "Detection time multiplier";
  //            default "3";
  //            type union {
  //              type string {
  //                pattern "<.*>|$.*";
  //              }
  //              type uint32 {
  //                range "1 .. 255";
  //              }
  //            }
  //          }
  //          leaf inline-disable {
  //            description "Disable inline mode for this BFD session";
  //            type empty;
  //          }
  //          leaf pdu-size {
  //            description "BFD transport protocol payload size";
  //            default "24";
  //            type union {
  //              type string {
  //                pattern "<.*>|$.*";
  //              }
  //              type uint32 {
  //                range "24 .. 9000";
  //              }
  //            }
  //          }
  //          choice adaptation-choice {
  //            case case_1 {
  //              leaf no-adaptation {
  //                description "Disable adaptation";
  //                type empty;
  //              }
  //            }
  //          }
  //          container transmit-interval {
  //            description "Transmit-interval options";
  //            // uses apply-advanced;
  //            leaf minimum-interval {
  //              description "Minimum transmit interval";
  //              units "milliseconds";
  //              type union {
  //                type string {
  //                  pattern "<.*>|$.*";
  //                }
  //                type uint32 {
  //                  range "1 .. 255000";
  //                }
  //              }
  //            }
  //            leaf threshold {
  //              description "High transmit interval triggering a trap";
  //              units "milliseconds";
  //              type union {
  //                type uint32;
  //                type string {
  //                  pattern "<.*>|$.*";
  //                }
  //              }
  //            }
  //          }
  //          container detection-time {
  //            description "Detection-time options";
  //            // uses apply-advanced;
  //            leaf threshold {
  //              description "High detection-time triggering a trap";
  //              units "milliseconds";
  //              type union {
  //                type uint32;
  //                type string {
  //                  pattern "<.*>|$.*";
  //                }
  //              }
  //            }
  //          }
  //          container authentication {
  //            description "Authentication options";
  //            // uses apply-advanced;
  //            leaf key-chain {
  //              description "Key chain name";
  //              type string;
  //            }
  //            leaf algorithm {
  //              description "Algorithm name";
  //              type enumeration {
  //                enum "simple-password" {
  //                  description "Simple password";
  //                }
  //                enum "keyed-md5" {
  //                  description "Keyed message Digest 5";
  //                }
  //                enum "meticulous-keyed-md5" {
  //                  description "Meticulous keyed message Digest 5";
  //                }
  //                enum "keyed-sha-1" {
  //                  description "Keyed secure hash algorithm (SHA1) ";
  //                }
  //                enum "meticulous-keyed-sha-1" {
  //                  description "Meticulous keyed secure hash algorithm (SHA1) ";
  //                }
  //              }
  //            }
  //            leaf loose-check {
  //              description "Verify authentication only if authentication is negotiated";
  //              type empty;
  //            }
  //          }
  //          container echo {
  //            description "Echo mode parameters";
  //            // uses apply-advanced;
  //            leaf minimum-interval {
  //              description "Minimum transmit and receive interval";
  //              units "milliseconds";
  //              type union {
  //                type string {
  //                  pattern "<.*>|$.*";
  //                }
  //                type uint32 {
  //                  range "100 .. 255000";
  //                }
  //              }
  //            }
  //          }
  //          container echo-lite {
  //            description "Echo-lite more parameters";
  //            // uses apply-advanced;
  //            leaf minimum-interval {
  //              description "Minimum transmit and receive interval";
  //              units "milliseconds";
  //              type union {
  //                type string {
  //                  pattern "<.*>|$.*";
  //                }
  //                type uint32 {
  //                  range "100 .. 255000";
  //                }
  //              }
  //            }
  //          }
  //          leaf full-neighbors-only {
  //            description "Setup BFD sessions only to Full neighbors";
  //            type empty;
  //          }
  //          leaf holddown-interval {
  //            description "Time to hold the session-UP notification to the client";
  //            units "milliseconds";
  //            type union {
  //              type string {
  //                pattern "<.*>|$.*";
  //              }
  //              type uint32 {
  //                range "0 .. 255000";
  //              }
  //            }
  //          }
  //        }
  //        leaf dynamic-neighbors {
  //          description "Learn neighbors dynamically on a p2mp interface";
  //          type empty;
  //        }
  //        leaf no-advertise-adjacency-segment {
  //          description "Do not advertise an adjacency segment for this interface";
  //          type empty;
  //        }
  //        list neighbor {
  //          key name;
  //          ordered-by user;
  //          description "NBMA neighbor";
  //          leaf name {
  //            description "Address of neighbor";
  //            type jt:ipaddr;
  //          }
  //          leaf eligible {
  //            description "Eligible to be DR on an NBMA network";
  //            type empty;
  //          }
  //        }
  //        leaf poll-interval {
  //          description "Poll interval for NBMA interfaces";
  //          type union {
  //            type string {
  //              pattern "<.*>|$.*";
  //            }
  //            type uint32 {
  //              range "1 .. 65535";
  //            }
  //          }
  //        }
  //        leaf no-interface-state-traps {
  //          description "Do not send interface state change traps";
  //          type empty;
  //        }
  //        leaf strict-bfd {
  //          description "Enable strict bfd over this interface";
  //          type empty;
  //        }
  //        container post-convergence-lfa {
  //          presence "enable post-convergence-lfa";
  //          description "Protect interface using post-convergence backup path";
  //          // uses apply-advanced;
  //          container node-protection {
  //            presence "enable node-protection";
  //            description "Compute backup path assuming node failure";
  //            // uses apply-advanced;
  //            leaf cost {
  //              description "Cost for node protection";
  //              type union {
  //                type string {
  //                  pattern "<.*>|$.*";
  //                }
  //                type uint16 {
  //                  range "1 .. 65535";
  //                }
  //              }
  //            }
  //          }
  //          leaf srlg-protection {
  //            description "Compute backup path assuming SRLG failure";
  //            type empty;
  //          }
  //          leaf fate-sharing-protection {
  //            description "Compute backup path assuming fate-sharing group failure";
  //            type empty;
  //          }
  //        }
  //        leaf te-metric {
  //          description "Traffic engineering metric";
  //          type union {
  //            type string {
  //              pattern "<.*>|$.*";
  //            }
  //            type uint32 {
  //              range "1 .. 4294967295";
  //            }
  //          }
  //        }
  //        container ldp-synchronization {
  //          description "Advertise maximum metric until LDP is operational";
  //          presence "enable ldp-synchronization";
  //          uses ldp-sync-obj;
  //        }
  //        container ipv4-adjacency-segment {
  //          description "Configure ipv4 adjacency segment";
  //          // uses apply-advanced;
  //          container protected {
  //            description "Adjacency SID is eligible for protection";
  //            choice adjsid-type {
  //              case case_1 {
  //                container index {
  //                  description "Adjacency SID indexed from SRGB";
  //                  leaf index-number {
  //                    type union {
  //                      type string {
  //                        pattern "<.*>|$.*";
  //                      }
  //                      type uint32 {
  //                        range "0 .. 199999";
  //                      }
  //                    }
  //                  }
  //                }
  //              }
  //              case case_2 {
  //                leaf label {
  //                  description "Adjacency SID from static label pool";
  //                  type union {
  //                    type string {
  //                      pattern "<.*>|$.*";
  //                    }
  //                    type uint32 {
  //                      range "16 .. 1048575";
  //                    }
  //                  }
  //                }
  //              }
  //              case case_3 {
  //                leaf dynamic {
  //                  description "Dynamically allocate an adjacency segment";
  //                  type empty;
  //                }
  //              }
  //            }
  //          }
  //          container unprotected {
  //            description "Adjacency SID uneligible for protection";
  //            choice adjsid-type {
  //              case case_1 {
  //                container index {
  //                  description "Adjacency SID indexed from SRGB";
  //                  leaf index-number {
  //                    type union {
  //                      type string {
  //                        pattern "<.*>|$.*";
  //                      }
  //                      type uint32 {
  //                        range "0 .. 199999";
  //                      }
  //                    }
  //                  }
  //                }
  //              }
  //              case case_2 {
  //                leaf label {
  //                  description "Adjacency SID from static label pool";
  //                  type union {
  //                    type string {
  //                      pattern "<.*>|$.*";
  //                    }
  //                    type uint32 {
  //                      range "16 .. 1048575";
  //                    }
  //                  }
  //                }
  //              }
  //              case case_3 {
  //                leaf dynamic {
  //                  description "Dynamically allocate an adjacency segment";
  //                  type empty;
  //                }
  //              }
  //            }
  //          }
  //        }
  //        list lan-neighbor {
  //          key name;
  //          ordered-by user;
  //          description "Configuration specific to a LAN neighbor";
  //          leaf name {
  //            description "Address of neighbor";
  //            type jt:ipaddr;
  //          }
  //          // uses apply-advanced;
  //          container ipv4-adjacency-segment {
  //            description "Configure ipv4 adjacency segment";
  //            // uses apply-advanced;
  //            container protected {
  //              description "Adjacency SID is eligible for protection";
  //              choice adjsid-type {
  //                case case_1 {
  //                  container index {
  //                    description "Adjacency SID indexed from SRGB";
  //                    leaf index-number {
  //                      type union {
  //                        type string {
  //                          pattern "<.*>|$.*";
  //                        }
  //                        type uint32 {
  //                          range "0 .. 199999";
  //                        }
  //                      }
  //                    }
  //                  }
  //                }
  //                case case_2 {
  //                  leaf label {
  //                    description "Adjacency SID from static label pool";
  //                    type union {
  //                      type string {
  //                        pattern "<.*>|$.*";
  //                      }
  //                      type uint32 {
  //                        range "16 .. 1048575";
  //                      }
  //                    }
  //                  }
  //                }
  //                case case_3 {
  //                  leaf dynamic {
  //                    description "Dynamically allocate an adjacency segment";
  //                    type empty;
  //                  }
  //                }
  //              }
  //            }
  //            container unprotected {
  //              description "Adjacency SID uneligible for protection";
  //              choice adjsid-type {
  //                case case_1 {
  //                  container index {
  //                    description "Adjacency SID indexed from SRGB";
  //                    leaf index-number {
  //                      type union {
  //                        type string {
  //                          pattern "<.*>|$.*";
  //                        }
  //                        type uint32 {
  //                          range "0 .. 199999";
  //                        }
  //                      }
  //                    }
  //                  }
  //                }
  //                case case_2 {
  //                  leaf label {
  //                    description "Adjacency SID from static label pool";
  //                    type union {
  //                      type string {
  //                        pattern "<.*>|$.*";
  //                      }
  //                      type uint32 {
  //                        range "16 .. 1048575";
  //                      }
  //                    }
  //                  }
  //                }
  //                case case_3 {
  //                  leaf dynamic {
  //                    description "Dynamically allocate an adjacency segment";
  //                    type empty;
  //                  }
  //                }
  //              }
  //            }
  //          }
  //        }
  //        leaf delay-metric {
  //          description "Delay metric";
  //          units "microseconds";
  //          type union {
  //            type string {
  //              pattern "<.*>|$.*";
  //            }
  //            type uint32 {
  //              range "0 .. 16777215";
  //            }
  //          }
  //        }
  //        container delay-measurement {
  //          presence "enable delay-measurement";
  //          description "Enable delay measurement";
  //          // uses apply-advanced;
  //          leaf probe-interval {
  //            description "Probe interval";
  //            units "seconds";
  //            type union {
  //              type string {
  //                pattern "<.*>|$.*";
  //              }
  //              type uint32 {
  //                range "1 .. 255";
  //              }
  //            }
  //          }
  //          leaf probe-count {
  //            description "Probe count";
  //            type union {
  //              type string {
  //                pattern "<.*>|$.*";
  //              }
  //              type uint32 {
  //                range "1 .. 15";
  //              }
  //            }
  //          }
  //          container advertisement {
  //            description "Delay advertisement";
  //            // uses apply-advanced;
  //            container periodic {
  //              description "Periodic advertisement parameters";
  //              // uses apply-advanced;
  //              leaf threshold {
  //                description "Threshold";
  //                units "percentage";
  //                type union {
  //                  type string {
  //                    pattern "<.*>|$.*";
  //                  }
  //                  type uint32 {
  //                    range "0 .. 100";
  //                  }
  //                }
  //              }
  //              leaf interval {
  //                description "Interval";
  //                units "seconds";
  //                type union {
  //                  type string {
  //                    pattern "<.*>|$.*";
  //                  }
  //                  type uint32 {
  //                    range "30 .. 3600";
  //                  }
  //                }
  //              }
  //            }
  //            container accelerated {
  //              presence "enable accelerated";
  //              description "Accelerated advertisement parameters";
  //              // uses apply-advanced;
  //              leaf threshold {
  //                description "Threshold";
  //                units "percentage";
  //                type union {
  //                  type string {
  //                    pattern "<.*>|$.*";
  //                  }
  //                  type uint32 {
  //                    range "0 .. 100";
  //                  }
  //                }
  //              }
  //            }
  //          }
  //        }
  //        container application-specific {
  //          description "Advertise application-specific TE attributes";
  //          // uses apply-advanced;
  //          list attribute-group {
  //            key name;
  //            ordered-by user;
  //            description "Link attribute group name";
  //            max-elements 1;
  //            leaf name {
  //              description "Link attribute group name";
  //              type string;
  //            }
  //            // uses apply-advanced;
  //            leaf te-metric {
  //              description "Traffic engineering metric for this attribute group";
  //              type union {
  //                type string {
  //                  pattern "<.*>|$.*";
  //                }
  //                type uint32 {
  //                  range "1 .. 4294967295";
  //                }
  //              }
  //            }
  //            leaf-list admin-group {
  //              ordered-by user;
  //              description "Administrative groups for this attribute-group";
  //              type string;
  //              max-elements 16;
  //            }
  //            leaf delay-metric {
  //              description "Delay metric for this attribute-group";
  //              units "microseconds";
  //              type union {
  //                type string {
  //                  pattern "<.*>|$.*";
  //                }
  //                type uint32 {
  //                  range "0 .. 16777215";
  //                }
  //              }
  //            }
  //            leaf advertise-interface-delay {
  //              description "Use interface specific static/dynamic delay values as applicable in ASLA Sub-TLVs";
  //              type empty;
  //            }
  //            container application {
  //              description "Standard Applications part of this attribute-group";
  //              // uses apply-advanced;
  //              leaf flex-algorithm {
  //                description "Set X flag in standard application bit mask";
  //                type empty;
  //              }
  //            }
  //          }
  //        }
  //      }
  //      leaf no-context-identifier-advertisement {
  //        description "Disable context identifier advertisments in this area";
  //        type empty;
  //      }
  //      list peer-interface {
  //        key name;
  //        ordered-by user;
  //        description "Configuration for peer interface";
  //        leaf name {
  //          description "Name of peer interface";
  //          type string;
  //        }
  //        // uses apply-advanced;
  //        choice enable-disable {
  //          case case_1 {
  //            leaf disable {
  //              description "Disable OSPF on this control peer";
  //              type empty;
  //            }
  //          }
  //        }
  //        leaf retransmit-interval {
  //          description "Retransmission interval (seconds)";
  //          type union {
  //            type string {
  //              pattern "<.*>|$.*";
  //            }
  //            type uint32 {
  //              range "1 .. 65535";
  //            }
  //          }
  //        }
  //        leaf transit-delay {
  //          description "Transit delay (seconds)";
  //          type union {
  //            type string {
  //              pattern "<.*>|$.*";
  //            }
  //            type uint32 {
  //              range "1 .. 65535";
  //            }
  //          }
  //        }
  //        leaf hello-interval {
  //          description "Hello interval (seconds)";
  //          type union {
  //            type string {
  //              pattern "<.*>|$.*";
  //            }
  //            type uint32 {
  //              range "1 .. 255";
  //            }
  //          }
  //        }
  //        leaf dead-interval {
  //          description "Dead interval (seconds)";
  //          type union {
  //            type string {
  //              pattern "<.*>|$.*";
  //            }
  //            type uint32 {
  //              range "1 .. 65535";
  //            }
  //          }
  //        }
  //        leaf mtu {
  //          description "Maximum OSPF packet size";
  //          type union {
  //            type string {
  //              pattern "<.*>|$.*";
  //            }
  //            type uint32 {
  //              range "128 .. 65535";
  //            }
  //          }
  //        }
  //        choice auth {
  //          case case_1 {
  //            container authentication {
  //              uses juniper-ospf-authentication;
  //            }
  //          }
  //          case case_2 {
  //            container authentication-key {
  //              description "Authentication key";
  //              status deprecated;
  //              leaf keyname {
  //                description "Authentication key value";
  //                type jt:unreadable;
  //              }
  //              leaf key-id {
  //                description "Key ID for MD5 authentication";
  //                type union {
  //                  type string {
  //                    pattern "<.*>|$.*";
  //                  }
  //                  type uint32 {
  //                    range "0 .. 255";
  //                  }
  //                }
  //              }
  //            }
  //          }
  //        }
  //        leaf demand-circuit {
  //          description "Interface functions as a demand circuit";
  //          type empty;
  //        }
  //        leaf flood-reduction {
  //          description "Enable flood reduction";
  //          type empty;
  //        }
  //        leaf no-neighbor-down-notification {
  //          description "Don't inform other protocols about neighbor down events";
  //          type empty;
  //        }
  //      }
  //      leaf no-source-packet-routing {
  //        description "Disable SPRING in this area";
  //        type empty;
  //      }
  //      list context-identifier {
  //        key name;
  //        ordered-by user;
  //        description "Configure context identifier in support of edge protection";
  //        leaf name {
  //          description "Context identifier";
  //          type jt:ipv4addr;
  //        }
  //        // uses apply-advanced;
  //      }
  //      list label-switched-path {
  //        key name;
  //        ordered-by user;
  //        description "Configuration for advertisement of a label-switched path";
  //        leaf name {
  //          description "Name of label-switched path to be advertised";
  //          type string {
  //            length "1 .. 64";
  //          }
  //        }
  //        // uses apply-advanced;
  //        choice enable-disable {
  //          case case_1 {
  //            leaf disable {
  //              description "Disable OSPF on this label-switched path";
  //              type empty;
  //            }
  //          }
  //        }
  //        leaf metric {
  //          description "Interface metric";
  //          type union {
  //            type string {
  //              pattern "<.*>|$.*";
  //            }
  //            type uint16 {
  //              range "1 .. 65535";
  //            }
  //          }
  //        }
  //        list topology {
  //          key name;
  //          ordered-by user;
  //          description "Topology specific attributes";
  //          leaf name {
  //            description "Topology name";
  //            type string;
  //          }
  //          // uses apply-advanced;
  //          leaf disable {
  //            description "Disable this topology";
  //            type empty;
  //          }
  //          leaf metric {
  //            description "Topology metric";
  //            type union {
  //              type string {
  //                pattern "<.*>|$.*";
  //              }
  //              type uint16 {
  //                range "1 .. 65535";
  //              }
  //            }
  //          }
  //          container bandwidth-based-metrics {
  //            description "Configure bandwidth based metrics";
  //            // uses apply-advanced;
  //            list bandwidth {
  //              key name;
  //              description "Bandwidth threshold";
  //              leaf name {
  //                type string;
  //              }
  //              leaf metric {
  //                description "Metric associated with specified bandwidth";
  //                type union {
  //                  type string {
  //                    pattern "<.*>|$.*";
  //                  }
  //                  type uint16 {
  //                    range "1 .. 65535";
  //                  }
  //                }
  //              }
  //            }
  //          }
  //        }
  //      }
  //    }
  //    choice enable-disable {
  //      case case_1 {
  //        leaf disable {
  //          description "Disable OSPF";
  //          type empty;
  //        }
  //      }
  //    }
  //    container traceoptions {
  //      description "Trace options for OSPF";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "spf" {
  //              description "Trace SPF calculations";
  //            }
  //            enum "error" {
  //              description "Trace errored packets";
  //            }
  //            enum "event" {
  //              description "Trace OSPF state machine events";
  //            }
  //            enum "packet-dump" {
  //              description "Dump the contents of selected packet types";
  //            }
  //            enum "flooding" {
  //              description "Trace LSA flooding";
  //            }
  //            enum "lsa-analysis" {
  //              description "Trace LSA analysis";
  //            }
  //            enum "packets" {
  //              description "Trace all OSPF packets";
  //            }
  //            enum "hello" {
  //              description "Trace hello packets";
  //            }
  //            enum "database-description" {
  //              description "Trace database description packets";
  //            }
  //            enum "lsa-request" {
  //              description "Trace LSA request packets";
  //            }
  //            enum "lsa-update" {
  //              description "Trace LSA update packets";
  //            }
  //            enum "lsa-ack" {
  //              description "Trace LSA acknowledgment packets";
  //            }
  //            enum "ldp-synchronization" {
  //              description "Trace synchronization between OSPF and LDP";
  //            }
  //            enum "on-demand" {
  //              description "Trace demand circuit extensions";
  //            }
  //            enum "nsr-synchronization" {
  //              description "Trace NSR synchronization events";
  //            }
  //            enum "graceful-restart" {
  //              description "Trace graceful restart";
  //            }
  //            enum "restart-signaling" {
  //              description "Trace restart signaling";
  //            }
  //            enum "traffic-statistics" {
  //              description "Trace Segment Routing Traffic Statistics";
  //            }
  //            enum "backup-spf" {
  //              description "Trace backup SPF (LFA) specific events";
  //            }
  //            enum "source-packet-routing" {
  //              description "Trace source packet routing (SPRING) events";
  //            }
  //            enum "post-convergence-lfa" {
  //              description "Trace post-convergence-lfa related events";
  //            }
  //            enum "flex-algorithm" {
  //              description "Trace flex-algorithm related events";
  //            }
  //            enum "rmopd" {
  //              description "Trace rmopd interactions";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    leaf prefix-export-limit {
  //      description "Maximum number of prefixes that can be exported";
  //      type union {
  //        type string {
  //          pattern "<.*>|$.*";
  //        }
  //        type uint32 {
  //          range "0 .. 4294967295";
  //        }
  //      }
  //    }
  //    container rib-groups {
  //      description "Routing table groups for importing OSPF routes";
  //      // uses apply-advanced;
  //      leaf inet {
  //        description "Name of the IPv4/v6 routing table group";
  //        type string;
  //      }
  //      leaf inet3 {
  //        description "Name of the IPv4/v6 inet.3 routing table group";
  //        type string;
  //      }
  //    }
  //    leaf job-stats {
  //      description "Collect job statistics";
  //      type empty;
  //    }
  //    container overload {
  //      presence "enable overload";
  //      description "Set the overload mode (repel transit traffic)";
  //      // uses apply-advanced;
  //      leaf timeout {
  //        description "Time after which overload mode is reset";
  //        units "seconds";
  //        type union {
  //          type string {
  //            pattern "<.*>|$.*";
  //          }
  //          type uint32 {
  //            range "60 .. 3600";
  //          }
  //        }
  //      }
  //      leaf allow-route-leaking {
  //        description "Allow routes to be leaked when overload is configured";
  //        type empty;
  //      }
  //      leaf stub-network {
  //        description "Advertise Stub Network with maximum metric";
  //        type empty;
  //      }
  //      leaf intra-area-prefix {
  //        description "Advertise Intra Area Prefix with maximum metric";
  //        type empty;
  //      }
  //      leaf as-external {
  //        description "Advertise As External with maximum usable metric";
  //        type empty;
  //      }
  //    }
  //    container database-protection {
  //      presence "enable database-protection";
  //      description "Configure database protection attributes";
  //      // uses apply-advanced;
  //      leaf maximum-lsa {
  //        description "Maximum allowed non self-generated LSAs";
  //        type union {
  //          type string {
  //            pattern "<.*>|$.*";
  //          }
  //          type uint32 {
  //            range "1 .. 1000000";
  //          }
  //        }
  //      }
  //      leaf warning-only {
  //        description "Emit only a warning when LSA maximum limit is exceeded";
  //        type empty;
  //      }
  //      leaf warning-threshold {
  //        description "Percentage of LSA maximum above which to trigger warning";
  //        units "percent";
  //        type union {
  //          type string {
  //            pattern "<.*>|$.*";
  //          }
  //          type uint8 {
  //            range "30 .. 100";
  //          }
  //        }
  //      }
  //      leaf ignore-count {
  //        description "Maximum number of times to go into ignore state";
  //        type union {
  //          type string {
  //            pattern "<.*>|$.*";
  //          }
  //          type uint8 {
  //            range "1 .. 32";
  //          }
  //        }
  //      }
  //      leaf ignore-time {
  //        description "Time to stay in ignore state and ignore all neighbors";
  //        units "seconds";
  //        type union {
  //          type string {
  //            pattern "<.*>|$.*";
  //          }
  //          type uint16 {
  //            range "30 .. 3600";
  //          }
  //        }
  //      }
  //      leaf reset-time {
  //        description "Time after which the ignore count gets reset to zero";
  //        units "seconds";
  //        type union {
  //          type string {
  //            pattern "<.*>|$.*";
  //          }
  //          type uint32 {
  //            range "60 .. 86400";
  //          }
  //        }
  //      }
  //    }
  //    container graceful-restart {
  //      description "Configure graceful restart attributes";
  //      // uses apply-advanced;
  //      choice enable-disable {
  //        case case_1 {
  //          leaf disable {
  //            description "Disable OSPF graceful restart capability";
  //            type empty;
  //          }
  //        }
  //      }
  //      leaf restart-duration {
  //        description "Time for all neighbors to become full";
  //        units "seconds";
  //        type union {
  //          type string {
  //            pattern "<.*>|$.*";
  //          }
  //          type uint32 {
  //            range "1 .. 3600";
  //          }
  //        }
  //      }
  //      leaf notify-duration {
  //        description "Time to send all max-aged grace LSAs";
  //        units "seconds";
  //        type union {
  //          type string {
  //            pattern "<.*>|$.*";
  //          }
  //          type uint32 {
  //            range "1 .. 3600";
  //          }
  //        }
  //      }
  //      container helper-disable {
  //        presence "enable helper-disable";
  //        description "Disable graceful restart helper capability";
  //        // uses apply-advanced;
  //        choice disable-choices {
  //          case case_1 {
  //            leaf standard {
  //              description "Disable helper-mode for rfc3623 based GR";
  //              type empty;
  //            }
  //          }
  //          case case_2 {
  //            leaf restart-signaling {
  //              description "Disable helper mode for restart-signaling ";
  //              type empty;
  //            }
  //          }
  //          case case_3 {
  //            leaf both {
  //              description "Disable helper mode for both the types of GR";
  //              type empty;
  //            }
  //          }
  //        }
  //      }
  //      leaf no-strict-lsa-checking {
  //        description "Do not abort graceful helper mode upon LSA changes";
  //        type empty;
  //      }
  //    }
  //    leaf route-type-community {
  //      description "Specify BGP extended community value to encode OSPF route type";
  //      type enumeration {
  //        enum "iana" {
  //          description "BGP extended community value used is 0x0306";
  //        }
  //        enum "vendor" {
  //          description "Vendor BGP extended community value used is 0x8000";
  //        }
  //      }
  //    }
  //    container domain-id {
  //      description "Configure domain ID";
  //      choice domain_id_or_disable {
  //        case case_1 {
  //          leaf domain-id {
  //            description "Domain ID";
  //            type string;
  //          }
  //        }
  //        case case_2 {
  //          leaf disable {
  //            description "Disable domain ID";
  //            type empty;
  //          }
  //        }
  //      }
  //    }
  //    choice domain_vpn_tag_or_disable {
  //      case case_1 {
  //        leaf domain-vpn-tag {
  //          description "Domain VPN tag for external LSA";
  //          type union {
  //            type string {
  //              pattern "<.*>|$.*";
  //            }
  //            type uint32 {
  //              range "0 .. 4294967295";
  //            }
  //          }
  //        }
  //      }
  //      case case_2 {
  //        leaf no-domain-vpn-tag {
  //          description "Disable domain VPN tag";
  //          type empty;
  //        }
  //      }
  //    }
  //    leaf preference {
  //      description "Preference of internal routes";
  //      type union {
  //        type uint32;
  //        type string {
  //          pattern "<.*>|$.*";
  //        }
  //      }
  //    }
  //    leaf external-preference {
  //      description "Preference of external routes";
  //      type union {
  //        type uint32;
  //        type string {
  //          pattern "<.*>|$.*";
  //        }
  //      }
  //    }
  //    leaf labeled-preference {
  //      description "Preference of labeled routes";
  //      type union {
  //        type uint32;
  //        type string {
  //          pattern "<.*>|$.*";
  //        }
  //      }
  //    }
  //    leaf-list export {
  //      ordered-by user;
  //      description "Export policy";
  //      type jt:policy-algebra;
  //    }
  //    leaf-list import {
  //      ordered-by user;
  //      description "Import policy (for external routes or setting priority)";
  //      type jt:policy-algebra;
  //    }
  //    leaf reference-bandwidth {
  //      description "Bandwidth for calculating metric defaults";
  //      type string;
  //    }
  //    leaf lsa-refresh-interval {
  //      description "LSA refresh interval (minutes)";
  //      default "50";
  //      type union {
  //        type string {
  //          pattern "<.*>|$.*";
  //        }
  //        type uint32 {
  //          range "25 .. 50";
  //        }
  //      }
  //    }
  //    leaf spf-delay {
  //      description "Time to wait before running an SPF";
  //      status deprecated;
  //      units "milliseconds";
  //      type union {
  //        type string {
  //          pattern "<.*>|$.*";
  //        }
  //        type uint32 {
  //          range "50 .. 8000";
  //        }
  //      }
  //    }
  //    leaf no-rfc-1583 {
  //      description "Disable RFC1583 compatibility";
  //      type empty;
  //    }
  //    leaf forwarding-address-to-broadcast {
  //      description "Set forwarding address in Type 5 LSA in broadcast network";
  //      type empty;
  //    }
  //    choice nssa-abr-option {
  //      case case_1 {
  //        leaf no-nssa-abr {
  //          description "Disable full NSSA functionality at ABR";
  //          type empty;
  //        }
  //      }
  //    }
  //    container sham-link {
  //      presence "enable sham-link";
  //      description "Configure parameters for sham links";
  //      // uses apply-advanced;
  //      leaf local {
  //        description "Local sham link endpoint address";
  //        type jt:ipaddr;
  //      }
  //      leaf no-advertise-local {
  //        description "Don't advertise local sham link endpoint as stub in router LSA";
  //        status deprecated;
  //        type empty;
  //      }
  //    }
  //  }
  //  grouping juniper-protocols-pim {
  //    // uses apply-advanced;
  //    leaf protocol-instance-name {
  //      description "Name of protocol instance under routing instance";
  //      type string;
  //    }
  //    container family {
  //      description "Local address family";
  //      container any {
  //        presence "enable any";
  //        description "Default properties for all address families";
  //        // uses apply-advanced;
  //        leaf disable {
  //          description "Disable all families";
  //          type empty;
  //        }
  //      }
  //      container inet {
  //        presence "enable inet";
  //        description "IPv4 specific properties";
  //        // uses apply-advanced;
  //        choice enable-disable {
  //          case case_1 {
  //            leaf disable {
  //              description "Disable PIMv4 on all interfaces";
  //              type empty;
  //            }
  //          }
  //        }
  //      }
  //      container inet6 {
  //        presence "enable inet6";
  //        description "IPv6 specific properties";
  //        // uses apply-advanced;
  //        choice enable-disable {
  //          case case_1 {
  //            leaf disable {
  //              description "Disable PIMv6 on all interfaces";
  //              type empty;
  //            }
  //          }
  //        }
  //      }
  //    }
  //    choice enable-disable {
  //      case case_1 {
  //        leaf disable {
  //          description "Disable PIM";
  //          type empty;
  //        }
  //      }
  //    }
  //    container nonstop-routing {
  //      description "Configure PIM nonstop-routing attributes";
  //      // uses apply-advanced;
  //      choice enable-disable {
  //        case case_1 {
  //          leaf disable {
  //            description "Disable non-stop routing for PIM";
  //            type empty;
  //          }
  //        }
  //      }
  //    }
  //    container traceoptions {
  //      description "Trace options for PIM";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "route" {
  //              description "Trace routing information";
  //            }
  //            enum "packets" {
  //              description "Trace all PIM packets";
  //            }
  //            enum "hello" {
  //              description "Trace hello packets";
  //            }
  //            enum "register" {
  //              description "Trace register/register-stop messages";
  //            }
  //            enum "join" {
  //              description "Trace join/prune/graft/graft-ack messages";
  //            }
  //            enum "prune" {
  //              description "Trace join/prune/graft/graft-ack messages";
  //            }
  //            enum "graft" {
  //              description "Trace join/prune/graft/graft-ack messages";
  //            }
  //            enum "bootstrap" {
  //              description "Trace bootstrap/RP/auto-RP messages";
  //            }
  //            enum "rp" {
  //              description "Trace bootstrap/RP/auto-RP messages";
  //            }
  //            enum "autorp" {
  //              description "Trace bootstrap/RP/auto-RP messages";
  //            }
  //            enum "assert" {
  //              description "Trace assert messages";
  //            }
  //            enum "mdt" {
  //              description "Trace messages related to multicast data tunnels";
  //            }
  //            enum "nsr-synchronization" {
  //              description "Trace NSR synchronization events";
  //            }
  //            enum "bidirectional-df-election" {
  //              description "Trace bidirectional PIM DF election events";
  //            }
  //            enum "mofrr" {
  //              description "Trace Multicast only Fast Re-Route messages";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //        container filter {
  //          description "Filter to apply to this flag";
  //          presence "enable filter";
  //          uses pim_filter_obj;
  //        }
  //      }
  //    }
  //    container dense-groups {
  //      description "Dense mode groups for sparse-dense mode";
  //      // uses apply-advanced;
  //      leaf dynamic-reject {
  //        description "Reject dynamic autorp negative dense-mode prefixes learnt from network";
  //        type empty;
  //      }
  //      list pim-dense-group-type {
  //        key name;
  //        ordered-by user;
  //        leaf name {
  //          description "Group address or range to forward in dense mode";
  //          type jt:ipprefix;
  //        }
  //        choice dense-group-flags {
  //          case case_1 {
  //            leaf reject {
  //              description "Do not include prefix as dense mode; force sparse mode";
  //              type empty;
  //            }
  //          }
  //          case case_2 {
  //            leaf announce {
  //              description "Advertise as negative prefix in auto-RP announce messages";
  //              type empty;
  //            }
  //          }
  //        }
  //      }
  //    }
  //    leaf vpn-tunnel-source {
  //      description "Source address for the provider space mGRE tunnel";
  //      status deprecated;
  //      type jt:ipv4addr;
  //    }
  //    leaf vpn-group-address {
  //      description "Group address for the VPN in provider space";
  //      status deprecated;
  //      type jt:ipv4addr;
  //    }
  //    leaf-list tunnel-devices {
  //      ordered-by user;
  //      description "Tunnel devices to be used for creating mt interfaces";
  //      type union {
  //        type jt:interface-device;
  //        type string {
  //          pattern "<.*>|$.*";
  //        }
  //      }
  //    }
  //    container rpf-selection {
  //      description "Select RPF neighbor";
  //      // uses apply-advanced;
  //      list group {
  //        key name;
  //        ordered-by user;
  //        description "IP prefix of multicast group";
  //        leaf name {
  //          description "IP prefix of group";
  //          type jt:ipprefix;
  //        }
  //        // uses apply-advanced;
  //        container wildcard-source {
  //          presence "enable wildcard-source";
  //          description "Select RPF for (*,g) and unspecified (s,g) joins";
  //          // uses apply-advanced;
  //          leaf next-hop {
  //            description "Next-hop address";
  //            type jt:ipaddr;
  //          }
  //        }
  //        list source {
  //          key name;
  //          ordered-by user;
  //          description "IP prefix of one or more multicast sources";
  //          leaf name {
  //            description "IP prefix of source";
  //            type jt:ipprefix;
  //          }
  //          // uses apply-advanced;
  //          leaf next-hop {
  //            description "Next-hop address";
  //            type jt:ipaddr;
  //          }
  //        }
  //      }
  //      list prefix-list {
  //        key name;
  //        ordered-by user;
  //        description "Multicast group prefix list";
  //        leaf name {
  //          description "Name of prefix list to match against";
  //          type string;
  //        }
  //        // uses apply-advanced;
  //        container wildcard-source {
  //          presence "enable wildcard-source";
  //          description "Select RPF for (*,g) and unspecified (s,g) joins";
  //          // uses apply-advanced;
  //          leaf next-hop {
  //            description "Next-hop address";
  //            type jt:ipaddr;
  //          }
  //        }
  //        list source {
  //          key name;
  //          ordered-by user;
  //          description "IP prefix of one or more multicast sources";
  //          leaf name {
  //            description "IP prefix of source";
  //            type jt:ipprefix;
  //          }
  //          // uses apply-advanced;
  //          leaf next-hop {
  //            description "Next-hop address";
  //            type jt:ipaddr;
  //          }
  //        }
  //      }
  //    }
  //    container mvpn {
  //      presence "enable mvpn";
  //      description "PIM MVPN control-plane options";
  //      // uses apply-advanced;
  //      container autodiscovery {
  //        description "PE router autodiscovery options for SSM MDTs";
  //        status deprecated;
  //        // uses apply-advanced;
  //        leaf inet-mdt {
  //          description "MDT-SAFI PE autodiscovery for SSM MDTs";
  //          type empty;
  //        }
  //      }
  //      container family {
  //        description "PIM MVPN address family";
  //        // uses apply-advanced;
  //        container inet {
  //          description "IPv4 PIM MVPN specific properties";
  //          // uses apply-advanced;
  //          leaf rosen-mvpn {
  //            status deprecated;
  //            type empty;
  //          }
  //          leaf ngen-mvpn {
  //            status deprecated;
  //            type empty;
  //          }
  //          container autodiscovery {
  //            description "PE router autodiscovery options for SSM MDTs";
  //            // uses apply-advanced;
  //            leaf inet-mdt {
  //              description "MDT-SAFI PE autodiscovery for SSM MDTs";
  //              type empty;
  //            }
  //          }
  //          leaf disable {
  //            description "Disable family IPv4";
  //            type empty;
  //          }
  //        }
  //        container inet6 {
  //          description "IPv6 PIM MVPN specific properties";
  //          // uses apply-advanced;
  //          leaf rosen-mvpn {
  //            status deprecated;
  //            type empty;
  //          }
  //          leaf ngen-mvpn {
  //            status deprecated;
  //            type empty;
  //          }
  //          container autodiscovery {
  //            description "PE router autodiscovery options for SSM MDTs";
  //            // uses apply-advanced;
  //            leaf inet-mdt {
  //              description "MDT-SAFI PE autodiscovery for SSM MDTs";
  //              type empty;
  //            }
  //          }
  //          leaf disable {
  //            description "Disable family IPv6";
  //            type empty;
  //          }
  //        }
  //      }
  //    }
  //    container rib-group {
  //      description "Routing table group";
  //      uses rib_group_type;
  //    }
  //    leaf-list import {
  //      ordered-by user;
  //      description "PIM sparse import join policy";
  //      type jt:policy-algebra;
  //    }
  //    leaf-list export {
  //      ordered-by user;
  //      description "PIM sparse export join policy";
  //      type jt:policy-algebra;
  //    }
  //    container mldp-inband-signalling {
  //      presence "enable mldp-inband-signalling";
  //      // uses apply-advanced;
  //      leaf-list policy {
  //        ordered-by user;
  //        description "PIM MLDP join translation filter policy";
  //        type jt:policy-algebra;
  //      }
  //    }
  //    container rpf-vector {
  //      description "RPF vector TLV";
  //      // uses apply-advanced;
  //      leaf-list policy {
  //        ordered-by user;
  //        description "RPF vector TLV include policy";
  //        type jt:policy-algebra;
  //      }
  //    }
  //    leaf assert-timeout {
  //      description "Set assert timeout";
  //      default "180";
  //      type union {
  //        type string {
  //          pattern "<.*>|$.*";
  //        }
  //        type uint32 {
  //          range "5 .. 210";
  //        }
  //      }
  //    }
  //    leaf assert-robust-count {
  //      description "Number of assert messages an assert winner sends in one cycle";
  //      default "2";
  //      type union {
  //        type string {
  //          pattern "<.*>|$.*";
  //        }
  //        type uint32 {
  //          range "1 .. 5";
  //        }
  //      }
  //    }
  //    leaf join-prune-timeout {
  //      description "Set join/prune timeout";
  //      default "210";
  //      type union {
  //        type string {
  //          pattern "<.*>|$.*";
  //        }
  //        type uint32 {
  //          range "210 .. 420";
  //        }
  //      }
  //    }
  //    container spt-threshold {
  //      description "Set shortest-path-tree threshold policy";
  //      // uses apply-advanced;
  //      leaf-list infinity {
  //        ordered-by user;
  //        description "Apply policy to always remain on shared tree";
  //        type jt:policy-algebra;
  //      }
  //    }
  //    container sglimit {
  //      description "Set limit on number of (S,G) states ";
  //      // uses apply-advanced;
  //      list family {
  //        key name;
  //        ordered-by user;
  //        description "Protocol family";
  //        leaf name {
  //          type enumeration {
  //            enum "inet" {
  //              description "IPv4 family";
  //            }
  //            enum "inet6" {
  //              description "IPv6 family";
  //            }
  //          }
  //        }
  //        // uses apply-advanced;
  //        leaf maximum {
  //          description "Maximum limit above which additional entries are not accepted";
  //          type union {
  //            type string {
  //              pattern "<.*>|$.*";
  //            }
  //            type uint32 {
  //              range "1 .. 65535";
  //            }
  //          }
  //        }
  //        leaf threshold {
  //          description "Percentage of maximum at which to start generating warnings";
  //          type union {
  //            type string {
  //              pattern "<.*>|$.*";
  //            }
  //            type uint32 {
  //              range "1 .. 100";
  //            }
  //          }
  //        }
  //        leaf log-interval {
  //          description "Time between successive log messages";
  //          type union {
  //            type string {
  //              pattern "<.*>|$.*";
  //            }
  //            type uint32 {
  //              range "1 .. 65535";
  //            }
  //          }
  //        }
  //      }
  //      leaf maximum {
  //        description "Maximum limit above which additional entries are not accepted";
  //        type union {
  //          type string {
  //            pattern "<.*>|$.*";
  //          }
  //          type uint32 {
  //            range "1 .. 65535";
  //          }
  //        }
  //      }
  //      leaf threshold {
  //        description "Percentage of maximum at which to start generating warnings";
  //        type union {
  //          type string {
  //            pattern "<.*>|$.*";
  //          }
  //          type uint32 {
  //            range "1 .. 100";
  //          }
  //        }
  //      }
  //      leaf log-interval {
  //        description "Time between successive log messages";
  //        type union {
  //          type string {
  //            pattern "<.*>|$.*";
  //          }
  //          type uint32 {
  //            range "1 .. 65535";
  //          }
  //        }
  //      }
  //    }
  //    container rp {
  //      description "Router's rendezvous point properties";
  //      // uses apply-advanced;
  //      leaf bootstrap-priority {
  //        description "Eligibility to be the bootstrap router (IPv4 only)";
  //        type union {
  //          type string {
  //            pattern "<.*>|$.*";
  //          }
  //          type uint32 {
  //            range "0 .. 255";
  //          }
  //        }
  //      }
  //      leaf-list bootstrap-import {
  //        ordered-by user;
  //        description "Bootstrap import policy (IPv4 only)";
  //        type jt:policy-algebra;
  //      }
  //      leaf-list bootstrap-export {
  //        ordered-by user;
  //        description "Bootstrap export policy (IPv4 only)";
  //        type jt:policy-algebra;
  //      }
  //      container bootstrap {
  //        description "Bootstrap properties";
  //        // uses apply-advanced;
  //        container family {
  //          description "Bootstrap address family";
  //          container inet {
  //            description "IPv4 bootstrap properties";
  //            uses pim_bootstrap_options_type;
  //          }
  //          container inet6 {
  //            description "IPv6 bootstrap properties";
  //            uses pim_bootstrap_options_type;
  //          }
  //        }
  //      }
  //      container register-limit {
  //        description "Set limit on incoming registers that create (S,G) state";
  //        // uses apply-advanced;
  //        list family {
  //          key name;
  //          ordered-by user;
  //          description "Protocol family";
  //          leaf name {
  //            type enumeration {
  //              enum "inet" {
  //                description "IPv4 family";
  //              }
  //              enum "inet6" {
  //                description "IPv6 family";
  //              }
  //            }
  //          }
  //          // uses apply-advanced;
  //          leaf maximum {
  //            description "Maximum limit above which additional entries are not accepted";
  //            type union {
  //              type string {
  //                pattern "<.*>|$.*";
  //              }
  //              type uint32 {
  //                range "1 .. 65535";
  //              }
  //            }
  //          }
  //          leaf threshold {
  //            description "Percentage of maximum at which to start generating warnings";
  //            type union {
  //              type string {
  //                pattern "<.*>|$.*";
  //              }
  //              type uint32 {
  //                range "1 .. 100";
  //              }
  //            }
  //          }
  //          leaf log-interval {
  //            description "Time between successive log messages";
  //            type union {
  //              type string {
  //                pattern "<.*>|$.*";
  //              }
  //              type uint32 {
  //                range "1 .. 65535";
  //              }
  //            }
  //          }
  //        }
  //        leaf maximum {
  //          description "Maximum limit above which additional entries are not accepted";
  //          type union {
  //            type string {
  //              pattern "<.*>|$.*";
  //            }
  //            type uint32 {
  //              range "1 .. 65535";
  //            }
  //          }
  //        }
  //        leaf threshold {
  //          description "Percentage of maximum at which to start generating warnings";
  //          type union {
  //            type string {
  //              pattern "<.*>|$.*";
  //            }
  //            type uint32 {
  //              range "1 .. 100";
  //            }
  //          }
  //        }
  //        leaf log-interval {
  //          description "Time between successive log messages";
  //          type union {
  //            type string {
  //              pattern "<.*>|$.*";
  //            }
  //            type uint32 {
  //              range "1 .. 65535";
  //            }
  //          }
  //        }
  //      }
  //      container group-rp-mapping {
  //        description "Group-rp-mapping";
  //        // uses apply-advanced;
  //        list family {
  //          key name;
  //          ordered-by user;
  //          description "Protocol family";
  //          leaf name {
  //            type enumeration {
  //              enum "inet" {
  //                description "IPv4 family";
  //              }
  //              enum "inet6" {
  //                description "IPv6 family";
  //              }
  //            }
  //          }
  //          // uses apply-advanced;
  //          leaf maximum {
  //            description "Maximum limit above which additional entries are not accepted";
  //            type union {
  //              type string {
  //                pattern "<.*>|$.*";
  //              }
  //              type uint32 {
  //                range "1 .. 65535";
  //              }
  //            }
  //          }
  //          leaf threshold {
  //            description "Percentage of maximum at which to start generating warnings";
  //            type union {
  //              type string {
  //                pattern "<.*>|$.*";
  //              }
  //              type uint32 {
  //                range "1 .. 100";
  //              }
  //            }
  //          }
  //          leaf log-interval {
  //            description "Time between successive log messages";
  //            type union {
  //              type string {
  //                pattern "<.*>|$.*";
  //              }
  //              type uint32 {
  //                range "1 .. 65535";
  //              }
  //            }
  //          }
  //        }
  //        leaf maximum {
  //          description "Maximum limit above which additional entries are not accepted";
  //          type union {
  //            type string {
  //              pattern "<.*>|$.*";
  //            }
  //            type uint32 {
  //              range "1 .. 65535";
  //            }
  //          }
  //        }
  //        leaf threshold {
  //          description "Percentage of maximum at which to start generating warnings";
  //          type union {
  //            type string {
  //              pattern "<.*>|$.*";
  //            }
  //            type uint32 {
  //              range "1 .. 100";
  //            }
  //          }
  //        }
  //        leaf log-interval {
  //          description "Time between successive log messages";
  //          type union {
  //            type string {
  //              pattern "<.*>|$.*";
  //            }
  //            type uint32 {
  //              range "1 .. 65535";
  //            }
  //          }
  //        }
  //      }
  //      leaf-list rp-register-policy {
  //        ordered-by user;
  //        description "RP policy applied to incoming register messages";
  //        type jt:policy-algebra;
  //      }
  //      leaf-list dr-register-policy {
  //        ordered-by user;
  //        description "DR policy applied to outgoing register messages";
  //        type jt:policy-algebra;
  //      }
  //      container local {
  //        description "Router's local RP properties";
  //        // uses apply-advanced;
  //        leaf address {
  //          description "Local RP address (IPv4 only)";
  //          type jt:ipv4addr;
  //        }
  //        choice enable-disable {
  //          case case_1 {
  //            leaf disable {
  //              description "Disable this RP (IPv4 only)";
  //              type empty;
  //            }
  //          }
  //        }
  //        leaf priority {
  //          description "Router's priority for becoming an RP (IPv4 only)";
  //          type union {
  //            type string {
  //              pattern "<.*>|$.*";
  //            }
  //            type uint32 {
  //              range "0 .. 255";
  //            }
  //          }
  //        }
  //        leaf hold-time {
  //          description "How long neighbor considers this router to be up, in seconds (IPv4 only)";
  //          type union {
  //            type string {
  //              pattern "<.*>|$.*";
  //            }
  //            type uint32 {
  //              range "1 .. 65535";
  //            }
  //          }
  //        }
  //        list group-ranges {
  //          key name;
  //          ordered-by user;
  //          description "Group address range for which this router can be an RP (IPv4 only)";
  //          leaf name {
  //            type jt:ipv4prefix;
  //          }
  //          // uses apply-advanced;
  //        }
  //        leaf override {
  //          description "Static RP mapping will take precedence over dynamic";
  //          type empty;
  //        }
  //        container family {
  //          description "Local RP address family";
  //          container inet {
  //            description "IPv4 local RP properties";
  //            // uses apply-advanced;
  //            leaf address {
  //              description "Local RP address";
  //              type jt:ipv4addr;
  //            }
  //            choice enable-disable {
  //              case case_1 {
  //                leaf disable {
  //                  description "Disable this RP";
  //                  type empty;
  //                }
  //              }
  //            }
  //            leaf priority {
  //              description "Router's priority for becoming an RP";
  //              type union {
  //                type string {
  //                  pattern "<.*>|$.*";
  //                }
  //                type uint32 {
  //                  range "0 .. 255";
  //                }
  //              }
  //            }
  //            leaf hold-time {
  //              description "How long neighbor considers this router to be up, in seconds";
  //              type union {
  //                type string {
  //                  pattern "<.*>|$.*";
  //                }
  //                type uint32 {
  //                  range "1 .. 65535";
  //                }
  //              }
  //            }
  //            list group-ranges {
  //              key name;
  //              ordered-by user;
  //              description "Group address range for which this router can be an RP";
  //              leaf name {
  //                type jt:ipv4prefix;
  //              }
  //              // uses apply-advanced;
  //            }
  //            leaf override {
  //              description "Static RP mapping will take precedence over dynamic";
  //              type empty;
  //            }
  //            container anycast-pim {
  //              description "Attributes for IPv4 anycast PIM";
  //              // uses apply-advanced;
  //              container rp-set {
  //                description "Rendezvous points belonging to anycast RP set";
  //                // uses apply-advanced;
  //                list address {
  //                  key name;
  //                  ordered-by user;
  //                  description "IPv4 address of one or more remote anycast RPs";
  //                  leaf name {
  //                    description "IPv4 address of remote anycast RP";
  //                    type jt:ipaddr;
  //                  }
  //                  // uses apply-advanced;
  //                  leaf forward-msdp-sa {
  //                    description "Forward SAs learned from MSDP to this RP";
  //                    type empty;
  //                  }
  //                }
  //              }
  //              leaf local-address {
  //                description "Local address for replicating register messages to other RPs";
  //                type jt:ipaddr;
  //              }
  //            }
  //          }
  //          container inet6 {
  //            description "IPv6 local RP properties";
  //            // uses apply-advanced;
  //            leaf address {
  //              description "Local RP address";
  //              type jt:ipv6addr;
  //            }
  //            choice enable-disable {
  //              case case_1 {
  //                leaf disable {
  //                  description "Disable this RP";
  //                  type empty;
  //                }
  //              }
  //            }
  //            leaf priority {
  //              description "Router's priority for becoming an RP";
  //              type union {
  //                type string {
  //                  pattern "<.*>|$.*";
  //                }
  //                type uint32 {
  //                  range "0 .. 255";
  //                }
  //              }
  //            }
  //            leaf hold-time {
  //              description "How long neighbor considers this router to be up, in seconds";
  //              type union {
  //                type string {
  //                  pattern "<.*>|$.*";
  //                }
  //                type uint32 {
  //                  range "1 .. 65535";
  //                }
  //              }
  //            }
  //            list group-ranges {
  //              key name;
  //              ordered-by user;
  //              description "Group address range for which this router can be an RP";
  //              leaf name {
  //                type jt:ipv6prefix;
  //              }
  //              // uses apply-advanced;
  //            }
  //            leaf override {
  //              description "Static RP mapping will take precedence over dynamic";
  //              type empty;
  //            }
  //            container anycast-pim {
  //              description "Attributes for IPv6 anycast PIM";
  //              // uses apply-advanced;
  //              container rp-set {
  //                description "Rendezvous points belonging to anycast RP set";
  //                // uses apply-advanced;
  //                list address {
  //                  key name;
  //                  ordered-by user;
  //                  description "IPv6 address of one or more remote anycast RPs";
  //                  leaf name {
  //                    description "IPv6 address of remote anycast RP";
  //                    type jt:ipv6addr;
  //                  }
  //                  // uses apply-advanced;
  //                }
  //              }
  //              leaf local-address {
  //                description "Local address for replicating register messages to other RPs";
  //                type jt:ipv6addr;
  //              }
  //            }
  //          }
  //        }
  //      }
  //      container embedded-rp {
  //        presence "enable embedded-rp";
  //        description "Set embedded-RP mode (IPv6 only)";
  //        // uses apply-advanced;
  //        list group-ranges {
  //          key name;
  //          ordered-by user;
  //          description "Group address range of RP";
  //          uses pim_rp_group_range_type;
  //        }
  //        leaf maximum-rps {
  //          description "Maximum number of embedded RPs";
  //          default "100";
  //          type union {
  //            type string {
  //              pattern "<.*>|$.*";
  //            }
  //            type uint32 {
  //              range "1 .. 500";
  //            }
  //          }
  //        }
  //      }
  //      container auto-rp {
  //        description "Set auto-RP mode (IPv4 only)";
  //        // uses apply-advanced;
  //        choice autorp-mode {
  //          case case_1 {
  //            leaf discovery {
  //              description "Listen for auto-RP discovery messages";
  //              type empty;
  //            }
  //          }
  //          case case_2 {
  //            leaf announce {
  //              description "Transmit auto-RP announcement messages";
  //              type empty;
  //            }
  //          }
  //          case case_3 {
  //            leaf mapping {
  //              description "Transmit auto-RP mapping messages";
  //              type empty;
  //            }
  //          }
  //        }
  //        choice mapping-agent-election-choice {
  //          leaf mapping-agent-election {
  //            description "Consider higher-addressed mapping agents as authoritative";
  //            type empty;
  //          }
  //          leaf no-mapping-agent-election {
  //            description "Don't consider higher-addressed mapping agents as authoritative";
  //            type empty;
  //          }
  //        }
  //      }
  //      container static {
  //        description "Configure static PIM RPs";
  //        // uses apply-advanced;
  //        list address {
  //          key name;
  //          ordered-by user;
  //          description "RP address";
  //          leaf name {
  //            description "IP address of RP";
  //            type jt:ipaddr;
  //          }
  //          // uses apply-advanced;
  //          leaf version {
  //            description "PIM version of RP";
  //            status deprecated;
  //            type union {
  //              type string {
  //                pattern "<.*>|$.*";
  //              }
  //              type uint32 {
  //                range "1 .. 2";
  //              }
  //            }
  //          }
  //          list group-ranges {
  //            key name;
  //            ordered-by user;
  //            description "Group address range of RP";
  //            uses pim_rp_group_range_type;
  //          }
  //          leaf override {
  //            description "Static RP mapping will take precedence over dynamic";
  //            type empty;
  //          }
  //        }
  //      }
  //      container bidirectional {
  //        description "Configure PIM bidirectional-mode RPs";
  //        // uses apply-advanced;
  //        list address {
  //          key name;
  //          ordered-by user;
  //          description "RP address";
  //          leaf name {
  //            description "IP address of RP";
  //            type jt:ipaddr;
  //          }
  //          // uses apply-advanced;
  //          leaf priority {
  //            description "Router's priority for becoming an RP";
  //            type union {
  //              type string {
  //                pattern "<.*>|$.*";
  //              }
  //              type uint32 {
  //                range "0 .. 255";
  //              }
  //            }
  //          }
  //          leaf hold-time {
  //            description "How long neighbor considers this router to be up";
  //            units "seconds";
  //            type union {
  //              type string {
  //                pattern "<.*>|$.*";
  //              }
  //              type uint32 {
  //                range "1 .. 65535";
  //              }
  //            }
  //          }
  //          list group-ranges {
  //            key name;
  //            ordered-by user;
  //            description "Group address range of RP";
  //            uses pim_rp_group_range_type;
  //          }
  //        }
  //      }
  //    }
  //    leaf passive {
  //      description "Configure PIM protocol in passive mode";
  //      type empty;
  //    }
  //    list interface {
  //      key name;
  //      ordered-by user;
  //      description "PIM interface options";
  //      leaf name {
  //        description "Interface name";
  //        type string;
  //      }
  //      // uses apply-advanced;
  //      container family {
  //        description "Local address family";
  //        container any {
  //          presence "enable any";
  //          description "Default properties for all families";
  //          // uses apply-advanced;
  //          leaf disable {
  //            description "Disable all families";
  //            type empty;
  //          }
  //        }
  //        container inet {
  //          presence "enable inet";
  //          description "IPv4 specific properties";
  //          // uses apply-advanced;
  //          container bfd-liveness-detection {
  //            description "Bidirectional Forwarding Detection options";
  //            // uses apply-advanced;
  //            leaf version {
  //              description "BFD protocol version number";
  //              default "automatic";
  //              type enumeration {
  //                enum "0" {
  //                  description "BFD version 0 (deprecated)";
  //                }
  //                enum "1" {
  //                  description "BFD version 1";
  //                }
  //                enum "automatic" {
  //                  description "Choose BFD version automatically";
  //                }
  //              }
  //            }
  //            leaf minimum-interval {
  //              description "Minimum transmit and receive interval";
  //              units "milliseconds";
  //              type union {
  //                type string {
  //                  pattern "<.*>|$.*";
  //                }
  //                type uint32 {
  //                  range "1 .. 255000";
  //                }
  //              }
  //            }
  //            leaf minimum-transmit-interval {
  //              description "Minimum transmit interval";
  //              status deprecated;
  //              units "milliseconds";
  //              type union {
  //                type string {
  //                  pattern "<.*>|$.*";
  //                }
  //                type uint32 {
  //                  range "1 .. 255000";
  //                }
  //              }
  //            }
  //            leaf minimum-receive-interval {
  //              description "Minimum receive interval";
  //              units "milliseconds";
  //              type union {
  //                type string {
  //                  pattern "<.*>|$.*";
  //                }
  //                type uint32 {
  //                  range "1 .. 255000";
  //                }
  //              }
  //            }
  //            leaf multiplier {
  //              description "Detection time multiplier";
  //              default "3";
  //              type union {
  //                type string {
  //                  pattern "<.*>|$.*";
  //                }
  //                type uint32 {
  //                  range "1 .. 255";
  //                }
  //              }
  //            }
  //            leaf inline-disable {
  //              description "Disable inline mode for this BFD session";
  //              type empty;
  //            }
  //            leaf pdu-size {
  //              description "BFD transport protocol payload size";
  //              default "24";
  //              type union {
  //                type string {
  //                  pattern "<.*>|$.*";
  //                }
  //                type uint32 {
  //                  range "24 .. 9000";
  //                }
  //              }
  //            }
  //            choice adaptation-choice {
  //              case case_1 {
  //                leaf no-adaptation {
  //                  description "Disable adaptation";
  //                  type empty;
  //                }
  //              }
  //            }
  //            container transmit-interval {
  //              description "Transmit-interval options";
  //              // uses apply-advanced;
  //              leaf minimum-interval {
  //                description "Minimum transmit interval";
  //                units "milliseconds";
  //                type union {
  //                  type string {
  //                    pattern "<.*>|$.*";
  //                  }
  //                  type uint32 {
  //                    range "1 .. 255000";
  //                  }
  //                }
  //              }
  //              leaf threshold {
  //                description "High transmit interval triggering a trap";
  //                units "milliseconds";
  //                type union {
  //                  type uint32;
  //                  type string {
  //                    pattern "<.*>|$.*";
  //                  }
  //                }
  //              }
  //            }
  //            container detection-time {
  //              description "Detection-time options";
  //              // uses apply-advanced;
  //              leaf threshold {
  //                description "High detection-time triggering a trap";
  //                units "milliseconds";
  //                type union {
  //                  type uint32;
  //                  type string {
  //                    pattern "<.*>|$.*";
  //                  }
  //                }
  //              }
  //            }
  //            container authentication {
  //              description "Authentication options";
  //              // uses apply-advanced;
  //              leaf key-chain {
  //                description "Key chain name";
  //                type string;
  //              }
  //              leaf algorithm {
  //                description "Algorithm name";
  //                type enumeration {
  //                  enum "simple-password" {
  //                    description "Simple password";
  //                  }
  //                  enum "keyed-md5" {
  //                    description "Keyed message Digest 5";
  //                  }
  //                  enum "meticulous-keyed-md5" {
  //                    description "Meticulous keyed message Digest 5";
  //                  }
  //                  enum "keyed-sha-1" {
  //                    description "Keyed secure hash algorithm (SHA1) ";
  //                  }
  //                  enum "meticulous-keyed-sha-1" {
  //                    description "Meticulous keyed secure hash algorithm (SHA1) ";
  //                  }
  //                }
  //              }
  //              leaf loose-check {
  //                description "Verify authentication only if authentication is negotiated";
  //                type empty;
  //              }
  //            }
  //          }
  //          leaf mcae-mac-synchronize {
  //            description "Mclag mac synchronization";
  //            type empty;
  //          }
  //          choice enable-disable {
  //            case case_1 {
  //              leaf disable {
  //                description "Disable PIMv4 on this interface";
  //                type empty;
  //              }
  //            }
  //          }
  //        }
  //        container inet6 {
  //          presence "enable inet6";
  //          description "IPv6 specific properties";
  //          // uses apply-advanced;
  //          container bfd-liveness-detection {
  //            description "Bidirectional Forwarding Detection options";
  //            // uses apply-advanced;
  //            leaf version {
  //              description "BFD protocol version number";
  //              default "automatic";
  //              type enumeration {
  //                enum "0" {
  //                  description "BFD version 0 (deprecated)";
  //                }
  //                enum "1" {
  //                  description "BFD version 1";
  //                }
  //                enum "automatic" {
  //                  description "Choose BFD version automatically";
  //                }
  //              }
  //            }
  //            leaf minimum-interval {
  //              description "Minimum transmit and receive interval";
  //              units "milliseconds";
  //              type union {
  //                type string {
  //                  pattern "<.*>|$.*";
  //                }
  //                type uint32 {
  //                  range "1 .. 255000";
  //                }
  //              }
  //            }
  //            leaf minimum-transmit-interval {
  //              description "Minimum transmit interval";
  //              status deprecated;
  //              units "milliseconds";
  //              type union {
  //                type string {
  //                  pattern "<.*>|$.*";
  //                }
  //                type uint32 {
  //                  range "1 .. 255000";
  //                }
  //              }
  //            }
  //            leaf minimum-receive-interval {
  //              description "Minimum receive interval";
  //              units "milliseconds";
  //              type union {
  //                type string {
  //                  pattern "<.*>|$.*";
  //                }
  //                type uint32 {
  //                  range "1 .. 255000";
  //                }
  //              }
  //            }
  //            leaf multiplier {
  //              description "Detection time multiplier";
  //              default "3";
  //              type union {
  //                type string {
  //                  pattern "<.*>|$.*";
  //                }
  //                type uint32 {
  //                  range "1 .. 255";
  //                }
  //              }
  //            }
  //            leaf inline-disable {
  //              description "Disable inline mode for this BFD session";
  //              type empty;
  //            }
  //            leaf pdu-size {
  //              description "BFD transport protocol payload size";
  //              default "24";
  //              type union {
  //                type string {
  //                  pattern "<.*>|$.*";
  //                }
  //                type uint32 {
  //                  range "24 .. 9000";
  //                }
  //              }
  //            }
  //            choice adaptation-choice {
  //              case case_1 {
  //                leaf no-adaptation {
  //                  description "Disable adaptation";
  //                  type empty;
  //                }
  //              }
  //            }
  //            container transmit-interval {
  //              description "Transmit-interval options";
  //              // uses apply-advanced;
  //              leaf minimum-interval {
  //                description "Minimum transmit interval";
  //                units "milliseconds";
  //                type union {
  //                  type string {
  //                    pattern "<.*>|$.*";
  //                  }
  //                  type uint32 {
  //                    range "1 .. 255000";
  //                  }
  //                }
  //              }
  //              leaf threshold {
  //                description "High transmit interval triggering a trap";
  //                units "milliseconds";
  //                type union {
  //                  type uint32;
  //                  type string {
  //                    pattern "<.*>|$.*";
  //                  }
  //                }
  //              }
  //            }
  //            container detection-time {
  //              description "Detection-time options";
  //              // uses apply-advanced;
  //              leaf threshold {
  //                description "High detection-time triggering a trap";
  //                units "milliseconds";
  //                type union {
  //                  type uint32;
  //                  type string {
  //                    pattern "<.*>|$.*";
  //                  }
  //                }
  //              }
  //            }
  //            container authentication {
  //              description "Authentication options";
  //              // uses apply-advanced;
  //              leaf key-chain {
  //                description "Key chain name";
  //                type string;
  //              }
  //              leaf algorithm {
  //                description "Algorithm name";
  //                type enumeration {
  //                  enum "simple-password" {
  //                    description "Simple password";
  //                  }
  //                  enum "keyed-md5" {
  //                    description "Keyed message Digest 5";
  //                  }
  //                  enum "meticulous-keyed-md5" {
  //                    description "Meticulous keyed message Digest 5";
  //                  }
  //                  enum "keyed-sha-1" {
  //                    description "Keyed secure hash algorithm (SHA1) ";
  //                  }
  //                  enum "meticulous-keyed-sha-1" {
  //                    description "Meticulous keyed secure hash algorithm (SHA1) ";
  //                  }
  //                }
  //              }
  //              leaf loose-check {
  //                description "Verify authentication only if authentication is negotiated";
  //                type empty;
  //              }
  //            }
  //          }
  //          choice enable-disable {
  //            case case_1 {
  //              leaf disable {
  //                description "Disable PIMv6 on this interface";
  //                type empty;
  //              }
  //            }
  //          }
  //        }
  //      }
  //      choice enable-disable {
  //        case case_1 {
  //          leaf disable {
  //            description "Disable PIM on this interface";
  //            type empty;
  //          }
  //        }
  //      }
  //      container bidirectional {
  //        description "PIM bidirectional mode properties";
  //        // uses apply-advanced;
  //        container df-election {
  //          description "Bidir designated forwarder properties";
  //          // uses apply-advanced;
  //          leaf robustness-count {
  //            description "Election robustness count";
  //            type union {
  //              type string {
  //                pattern "<.*>|$.*";
  //              }
  //              type uint32 {
  //                range "1 .. 10";
  //              }
  //            }
  //          }
  //          leaf offer-period {
  //            description "Election offer message period";
  //            units "milliseconds";
  //            type union {
  //              type string {
  //                pattern "<.*>|$.*";
  //              }
  //              type uint32 {
  //                range "100 .. 10000";
  //              }
  //            }
  //          }
  //          leaf backoff-period {
  //            description "Election backoff period";
  //            units "milliseconds";
  //            type union {
  //              type string {
  //                pattern "<.*>|$.*";
  //              }
  //              type uint32 {
  //                range "100 .. 65535";
  //              }
  //            }
  //          }
  //        }
  //      }
  //      leaf mode {
  //        description "Mode of interface";
  //        type enumeration {
  //          enum "dense" {
  //            description "Dense mode";
  //          }
  //          enum "sparse" {
  //            description "Sparse mode";
  //          }
  //          enum "sparse-dense" {
  //            description "Sparse-dense mode";
  //          }
  //          enum "bidirectional-sparse" {
  //            description "Bidirectional-sparse mode";
  //          }
  //          enum "bidirectional-sparse-dense" {
  //            description "Bidirectional-sparse-dense mode";
  //          }
  //        }
  //      }
  //      leaf priority {
  //        description "Hello option DR priority";
  //        type union {
  //          type string {
  //            pattern "<.*>|$.*";
  //          }
  //          type uint32 {
  //            range "0 .. 4294967295";
  //          }
  //        }
  //      }
  //      container stickydr {
  //        presence "enable stickydr";
  //        description "Make DR sticky";
  //        // uses apply-advanced;
  //      }
  //      container multiple-triggered-joins {
  //        presence "enable multiple-triggered-joins";
  //        description "Send multiple pim triggered joins in quick intervals";
  //        // uses apply-advanced;
  //        leaf count {
  //          description "Set number of triggered joins to be sent";
  //          default "2";
  //          type union {
  //            type string {
  //              pattern "<.*>|$.*";
  //            }
  //            type uint16 {
  //              range "2 .. 15";
  //            }
  //          }
  //        }
  //        leaf interval {
  //          description "Set interval between multiple triggered joins to be sent in milliseconds";
  //          default "100";
  //          type union {
  //            type string {
  //              pattern "<.*>|$.*";
  //            }
  //            type uint16 {
  //              range "100 .. 1000";
  //            }
  //          }
  //        }
  //      }
  //      leaf version {
  //        description "Force PIM version";
  //        status deprecated;
  //        type union {
  //          type string {
  //            pattern "<.*>|$.*";
  //          }
  //          type uint32 {
  //            range "1 .. 2";
  //          }
  //        }
  //      }
  //      leaf hello-interval {
  //        description "Hello interval";
  //        units "seconds";
  //        type union {
  //          type string {
  //            pattern "<.*>|$.*";
  //          }
  //          type uint32 {
  //            range "0 .. 255";
  //          }
  //        }
  //      }
  //      leaf-list neighbor-policy {
  //        ordered-by user;
  //        description "PIM neighbor policy applied to incoming hello messages";
  //        type jt:policy-algebra;
  //      }
  //      leaf-list accept-join-always-from {
  //        ordered-by user;
  //        description "Accept pim join/prune messages based on the policy configured";
  //        type jt:policy-algebra;
  //      }
  //      leaf accept-remote-source {
  //        description "Accept traffic from remote source";
  //        type empty;
  //      }
  //      container dual-dr {
  //        presence "enable dual-dr";
  //        description "Configure PIM Dual DR";
  //        // uses apply-advanced;
  //        leaf enhanced {
  //          description "Enable enhanced PIM Dual DR";
  //          type empty;
  //        }
  //      }
  //      leaf distributed-dr {
  //        description "PIM Distributed DR";
  //        type empty;
  //      }
  //      leaf reset-tracking-bit {
  //        description "Clear tracking-bit in PIM Hello LAN Prune Delay Option";
  //        type empty;
  //      }
  //      leaf propagation-delay {
  //        description "Propagation delay value";
  //        default "500";
  //        units "milliseconds";
  //        type union {
  //          type string {
  //            pattern "<.*>|$.*";
  //          }
  //          type uint32 {
  //            range "250 .. 2000";
  //          }
  //        }
  //      }
  //      leaf override-interval {
  //        description "Override interval value";
  //        default "2000";
  //        units "milliseconds";
  //        type union {
  //          type string {
  //            pattern "<.*>|$.*";
  //          }
  //          type uint32 {
  //            range "500 .. 6000";
  //          }
  //        }
  //      }
  //      leaf disable-packet-register {
  //        description "Disable PIM packet registers on first hop router";
  //        type empty;
  //      }
  //      container bfd-liveness-detection {
  //        description "Bidirectional Forwarding Detection options (ipv4 only)";
  //        status deprecated;
  //        // uses apply-advanced;
  //        leaf version {
  //          description "BFD protocol version number";
  //          default "automatic";
  //          type enumeration {
  //            enum "0" {
  //              description "BFD version 0 (deprecated)";
  //            }
  //            enum "1" {
  //              description "BFD version 1";
  //            }
  //            enum "automatic" {
  //              description "Choose BFD version automatically";
  //            }
  //          }
  //        }
  //        leaf minimum-interval {
  //          description "Minimum transmit and receive interval";
  //          units "milliseconds";
  //          type union {
  //            type string {
  //              pattern "<.*>|$.*";
  //            }
  //            type uint32 {
  //              range "1 .. 255000";
  //            }
  //          }
  //        }
  //        leaf minimum-transmit-interval {
  //          description "Minimum transmit interval";
  //          status deprecated;
  //          units "milliseconds";
  //          type union {
  //            type string {
  //              pattern "<.*>|$.*";
  //            }
  //            type uint32 {
  //              range "1 .. 255000";
  //            }
  //          }
  //        }
  //        leaf minimum-receive-interval {
  //          description "Minimum receive interval";
  //          units "milliseconds";
  //          type union {
  //            type string {
  //              pattern "<.*>|$.*";
  //            }
  //            type uint32 {
  //              range "1 .. 255000";
  //            }
  //          }
  //        }
  //        leaf multiplier {
  //          description "Detection time multiplier";
  //          default "3";
  //          type union {
  //            type string {
  //              pattern "<.*>|$.*";
  //            }
  //            type uint32 {
  //              range "1 .. 255";
  //            }
  //          }
  //        }
  //        leaf inline-disable {
  //          description "Disable inline mode for this BFD session";
  //          type empty;
  //        }
  //        leaf pdu-size {
  //          description "BFD transport protocol payload size";
  //          default "24";
  //          type union {
  //            type string {
  //              pattern "<.*>|$.*";
  //            }
  //            type uint32 {
  //              range "24 .. 9000";
  //            }
  //          }
  //        }
  //        choice adaptation-choice {
  //          case case_1 {
  //            leaf no-adaptation {
  //              description "Disable adaptation";
  //              type empty;
  //            }
  //          }
  //        }
  //        container transmit-interval {
  //          description "Transmit-interval options";
  //          // uses apply-advanced;
  //          leaf minimum-interval {
  //            description "Minimum transmit interval";
  //            units "milliseconds";
  //            type union {
  //              type string {
  //                pattern "<.*>|$.*";
  //              }
  //              type uint32 {
  //                range "1 .. 255000";
  //              }
  //            }
  //          }
  //          leaf threshold {
  //            description "High transmit interval triggering a trap";
  //            units "milliseconds";
  //            type union {
  //              type uint32;
  //              type string {
  //                pattern "<.*>|$.*";
  //              }
  //            }
  //          }
  //        }
  //        container detection-time {
  //          description "Detection-time options";
  //          // uses apply-advanced;
  //          leaf threshold {
  //            description "High detection-time triggering a trap";
  //            units "milliseconds";
  //            type union {
  //              type uint32;
  //              type string {
  //                pattern "<.*>|$.*";
  //              }
  //            }
  //          }
  //        }
  //        container authentication {
  //          description "Authentication options";
  //          // uses apply-advanced;
  //          leaf key-chain {
  //            description "Key chain name";
  //            type string;
  //          }
  //          leaf algorithm {
  //            description "Algorithm name";
  //            type enumeration {
  //              enum "simple-password" {
  //                description "Simple password";
  //              }
  //              enum "keyed-md5" {
  //                description "Keyed message Digest 5";
  //              }
  //              enum "meticulous-keyed-md5" {
  //                description "Meticulous keyed message Digest 5";
  //              }
  //              enum "keyed-sha-1" {
  //                description "Keyed secure hash algorithm (SHA1) ";
  //              }
  //              enum "meticulous-keyed-sha-1" {
  //                description "Meticulous keyed secure hash algorithm (SHA1) ";
  //              }
  //            }
  //          }
  //          leaf loose-check {
  //            description "Verify authentication only if authentication is negotiated";
  //            type empty;
  //          }
  //        }
  //      }
  //    }
  //    container mdt {
  //      description "Configure multicast data tunnel parameters";
  //      status deprecated;
  //      // uses apply-advanced;
  //      container threshold {
  //        description "Threshold for creation of multicast tunnels";
  //        // uses apply-advanced;
  //        list group {
  //          key name;
  //          ordered-by user;
  //          description "IP prefix of multicast group";
  //          leaf name {
  //            description "IP prefix of group";
  //            type jt:ipprefix;
  //          }
  //          // uses apply-advanced;
  //          list source {
  //            key name;
  //            ordered-by user;
  //            description "IP prefix of one or more multicast sources ";
  //            leaf name {
  //              description "IP prefix of source";
  //              type jt:ipprefix;
  //            }
  //            // uses apply-advanced;
  //            leaf rate {
  //              description "Data threshold to create new tunnel";
  //              units "kilobits";
  //              type union {
  //                type string {
  //                  pattern "<.*>|$.*";
  //                }
  //                type uint32 {
  //                  range "10 .. 1000000";
  //                }
  //              }
  //            }
  //          }
  //        }
  //      }
  //      leaf data-mdt-reuse {
  //        description "Allow multiple customer streams to be transmitted over one data tunnel ";
  //        type empty;
  //      }
  //      leaf tunnel-limit {
  //        description "Maximum multicast data tunnels";
  //        type union {
  //          type string {
  //            pattern "<.*>|$.*";
  //          }
  //          type uint32 {
  //            range "0 .. 8192";
  //          }
  //        }
  //      }
  //      leaf group-range {
  //        description "Group address range for multicast data tunnels";
  //        type jt:ipprefix;
  //      }
  //    }
  //    container graceful-restart {
  //      description "Configure graceful restart attributes";
  //      // uses apply-advanced;
  //      choice enable-disable {
  //        case case_1 {
  //          leaf disable {
  //            description "Disable PIM graceful restart capability";
  //            type empty;
  //          }
  //        }
  //      }
  //      leaf restart-duration {
  //        description "Maximum time for graceful restart to finish (seconds)";
  //        units "seconds";
  //        type union {
  //          type string {
  //            pattern "<.*>|$.*";
  //          }
  //          type uint32 {
  //            range "30 .. 300";
  //          }
  //        }
  //      }
  //      leaf no-bidirectional-mode {
  //        description "Disable PIM graceful restart for bidirectional mode";
  //        type empty;
  //      }
  //      leaf restart-complete-duration {
  //        description "Maximum time for graceful restart to complete (seconds)";
  //        units "seconds";
  //        type union {
  //          type string {
  //            pattern "<.*>|$.*";
  //          }
  //          type uint32 {
  //            range "5 .. 300";
  //          }
  //        }
  //      }
  //    }
  //    container join-load-balance {
  //      presence "enable join-load-balance";
  //      description "Configure PIM join load balancing";
  //      // uses apply-advanced;
  //      leaf automatic {
  //        description "Enable automatic PIM join load balancing";
  //        type empty;
  //      }
  //    }
  //    leaf standby-path-creation-delay {
  //      description "Amount of time to wait before creating standby path";
  //      units "seconds";
  //      type union {
  //        type string {
  //          pattern "<.*>|$.*";
  //        }
  //        type uint32 {
  //          range "1 .. 300";
  //        }
  //      }
  //    }
  //    leaf idle-standby-path-switchover-delay {
  //      description "Amount of time to wait before switching over to idle standby path";
  //      units "seconds";
  //      type union {
  //        type string {
  //          pattern "<.*>|$.*";
  //        }
  //        type uint32 {
  //          range "1 .. 300";
  //        }
  //      }
  //    }
  //    leaf dr-election-on-p2p {
  //      description "Enable DR election on Point-to-Point Interfaces";
  //      type empty;
  //    }
  //    leaf no-wildcard-register-stop {
  //      description "Disable sending of wildcard register stop message";
  //      type empty;
  //    }
  //    leaf nexthop-hold-time {
  //      description "Nexthop hold time in milliseconds";
  //      units "milliseconds";
  //      type union {
  //        type string {
  //          pattern "<.*>|$.*";
  //        }
  //        type uint32 {
  //          range "1 .. 1000";
  //        }
  //      }
  //    }
  //    leaf mpls-internet-multicast {
  //      description "Enable support for Internet Multicast over MPLS";
  //      type empty;
  //    }
  //    container join-make-before-break {
  //      description "Enable PIM Join Make-Before-Break during RPF neighbor change";
  //      // uses apply-advanced;
  //      choice enable-disable {
  //        case case_1 {
  //          leaf disable {
  //            description "Disable Make-Before-Break for PIM RPF neighbor change";
  //            type empty;
  //          }
  //        }
  //      }
  //    }
  //    leaf reset-tracking-bit {
  //      description "Clear tracking-bit in PIM Hello LAN Prune Delay Option";
  //      type empty;
  //    }
  //    leaf propagation-delay {
  //      description "Propagation delay value";
  //      default "500";
  //      units "milliseconds";
  //      type union {
  //        type string {
  //          pattern "<.*>|$.*";
  //        }
  //        type uint32 {
  //          range "250 .. 2000";
  //        }
  //      }
  //    }
  //    leaf override-interval {
  //      description "Override interval value";
  //      default "2000";
  //      units "milliseconds";
  //      type union {
  //        type string {
  //          pattern "<.*>|$.*";
  //        }
  //        type uint32 {
  //          range "500 .. 6000";
  //        }
  //      }
  //    }
  //    leaf disable-packet-register {
  //      description "Disable PIM packet registers on first hop router";
  //      type empty;
  //    }
  //    container default-vpn-source {
  //      presence "enable default-vpn-source";
  //      description "Let all VRFs use master loopback address for mt interfaces";
  //      // uses apply-advanced;
  //      leaf interface-name {
  //        description "Master loopback interface name";
  //        type union {
  //          type jt:interface-unit;
  //          type string {
  //            pattern "<.*>|$.*";
  //          }
  //        }
  //      }
  //    }
  //  }
  //  grouping juniper-protocols-pim-snooping {
  //    description "PIM snooping options";
  //    // uses apply-advanced;
  //    container traceoptions {
  //      description "Trace options for PIM Snooping";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "packets" {
  //              description "Trace all PIM packets";
  //            }
  //            enum "hello" {
  //              description "Trace hello packets";
  //            }
  //            enum "join" {
  //              description "Trace join messages";
  //            }
  //            enum "prune" {
  //              description "Trace prune messages";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    leaf no-dr-flood {
  //      description "Disable default flooding of multicast data on the PIM designated router port";
  //      type empty;
  //    }
  //    list vlan {
  //      key name;
  //      ordered-by user;
  //      description "Vlan options";
  //      leaf name {
  //        description "Vlan_id of the learning-domain";
  //        type union {
  //          type string {
  //            pattern "<.*>|$.*";
  //          }
  //          type uint32 {
  //            range "0 .. 1023";
  //          }
  //        }
  //      }
  //      // uses apply-advanced;
  //      leaf no-dr-flood {
  //        description "Disable default flooding of multicast data on the PIM DR port";
  //        type empty;
  //      }
  //    }
  //  }
  //  grouping juniper-protocols-rip {
  //    // uses apply-advanced;
  //    container traceoptions {
  //      description "Trace options for RIP";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "auth" {
  //              description "Trace RIP authentication";
  //            }
  //            enum "error" {
  //              description "Trace RIP errors";
  //            }
  //            enum "expiration" {
  //              description "Trace RIP route expiration processing";
  //            }
  //            enum "holddown" {
  //              description "Trace RIP hold-down processing";
  //            }
  //            enum "packets" {
  //              description "Trace all RIP packets";
  //            }
  //            enum "request" {
  //              description "Trace RIP information packets";
  //            }
  //            enum "trigger" {
  //              description "Trace RIP triggered updates";
  //            }
  //            enum "update" {
  //              description "Trace RIP update packets";
  //            }
  //            enum "nsr-synchronization" {
  //              description "Trace NSR synchronization events";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //        container filter {
  //          description "Filter to apply to this flag";
  //          presence "enable filter";
  //          uses rip_filter_obj;
  //        }
  //      }
  //    }
  //    container rib-group {
  //      description "Routing table group for importing RIP routes";
  //      uses rib_group_inet_type;
  //    }
  //    leaf metric-in {
  //      description "Metric value to add to incoming routes";
  //      type union {
  //        type string {
  //          pattern "<.*>|$.*";
  //        }
  //        type uint32 {
  //          range "1 .. 15";
  //        }
  //      }
  //    }
  //    container send {
  //      description "Configure RIP send options";
  //      choice send-opts {
  //        case case_1 {
  //          leaf broadcast {
  //            description "Broadcast RIPv2 packets (RIPv1 compatible)";
  //            type empty;
  //          }
  //        }
  //        case case_2 {
  //          leaf multicast {
  //            description "Multicast RIPv2 packets";
  //            type empty;
  //          }
  //        }
  //        case case_3 {
  //          leaf none {
  //            description "Do not send RIP updates";
  //            type empty;
  //          }
  //        }
  //        case case_4 {
  //          leaf version-1 {
  //            description "Broadcast RIPv1 packets";
  //            type empty;
  //          }
  //        }
  //      }
  //    }
  //    container receive {
  //      description "Configure RIP receive options";
  //      choice receive-opts {
  //        case case_1 {
  //          leaf both {
  //            description "Accept both RIPv1 and RIPv2 packets";
  //            type empty;
  //          }
  //        }
  //        case case_2 {
  //          leaf none {
  //            description "Do not receive RIP packets";
  //            type empty;
  //          }
  //        }
  //        case case_3 {
  //          leaf version-1 {
  //            description "Accept RIPv1 packets only";
  //            type empty;
  //          }
  //        }
  //        case case_4 {
  //          leaf version-2 {
  //            description "Accept only RIPv2 packets";
  //            type empty;
  //          }
  //        }
  //      }
  //    }
  //    choice check-zero-choice {
  //      leaf check-zero {
  //        description "Check reserved fields on incoming RIPv2 packets";
  //        type empty;
  //      }
  //      leaf no-check-zero {
  //        description "Don't check reserved fields on incoming RIPv2 packets";
  //        type empty;
  //      }
  //    }
  //    leaf message-size {
  //      description "Number of route entries per update message";
  //      type union {
  //        type string {
  //          pattern "<.*>|$.*";
  //        }
  //        type uint32 {
  //          range "25 .. 255";
  //        }
  //      }
  //    }
  //    leaf-list import {
  //      ordered-by user;
  //      description "Import policy";
  //      type jt:policy-algebra;
  //    }
  //    leaf holddown {
  //      description "Hold-down time";
  //      units "seconds";
  //      type union {
  //        type string {
  //          pattern "<.*>|$.*";
  //        }
  //        type uint32 {
  //          range "10 .. 180";
  //        }
  //      }
  //    }
  //    leaf route-timeout {
  //      description "Delay before routes time out";
  //      units "seconds";
  //      type union {
  //        type string {
  //          pattern "<.*>|$.*";
  //        }
  //        type uint32 {
  //          range "30 .. 360";
  //        }
  //      }
  //    }
  //    leaf update-interval {
  //      description "Interval between regular route updates";
  //      units "seconds";
  //      type union {
  //        type string {
  //          pattern "<.*>|$.*";
  //        }
  //        type uint32 {
  //          range "10 .. 60";
  //        }
  //      }
  //    }
  //    choice authentication {
  //      case case_1 {
  //        leaf authentication-type {
  //          type enumeration {
  //            enum "none" {
  //              description "No authentication";
  //            }
  //            enum "simple" {
  //              description "Simple password authentication";
  //            }
  //            enum "md5" {
  //              description "MD5 authentication";
  //            }
  //          }
  //        }
  //      }
  //      case case_2 {
  //        list authentication-selective-md5 {
  //          key name;
  //          ordered-by user;
  //          description "MD5 authentication with one or more keys";
  //          leaf name {
  //            description "Key ID for MD5 authentication";
  //            type union {
  //              type string {
  //                pattern "<.*>|$.*";
  //              }
  //              type uint32 {
  //                range "0 .. 255";
  //              }
  //            }
  //          }
  //          leaf key {
  //            description "MD5 authentication key value";
  //            type jt:unreadable;
  //          }
  //          leaf start-time {
  //            description "Start time for key transmission (YYYY-MM-DD.HH:MM)";
  //            type jt:time;
  //          }
  //        }
  //      }
  //    }
  //    leaf authentication-key {
  //      description "Authentication key (password)";
  //      type jt:unreadable;
  //    }
  //    list group {
  //      key name;
  //      ordered-by user;
  //      description "Instance configuration";
  //      leaf name {
  //        description "Group name";
  //        type string {
  //        }
  //      }
  //      // uses apply-advanced;
  //      leaf route-timeout {
  //        description "Delay before routes time out";
  //        units "seconds";
  //        type union {
  //          type string {
  //            pattern "<.*>|$.*";
  //          }
  //          type uint32 {
  //            range "30 .. 360";
  //          }
  //        }
  //      }
  //      leaf update-interval {
  //        description "Interval between regular route updates";
  //        units "seconds";
  //        type union {
  //          type string {
  //            pattern "<.*>|$.*";
  //          }
  //          type uint32 {
  //            range "10 .. 60";
  //          }
  //        }
  //      }
  //      leaf preference {
  //        description "Preference of routes learned by this group";
  //        type union {
  //          type uint32;
  //          type string {
  //            pattern "<.*>|$.*";
  //          }
  //        }
  //      }
  //      leaf metric-out {
  //        description "Default metric of exported routes";
  //        type union {
  //          type string {
  //            pattern "<.*>|$.*";
  //          }
  //          type uint32 {
  //            range "1 .. 15";
  //          }
  //        }
  //      }
  //      leaf-list export {
  //        ordered-by user;
  //        description "Export policy";
  //        type jt:policy-algebra;
  //      }
  //      leaf-list import {
  //        ordered-by user;
  //        description "Import policy";
  //        type jt:policy-algebra;
  //      }
  //      leaf demand-circuit {
  //        description "Enable demand circuit on this interface";
  //        type empty;
  //      }
  //      leaf max-retrans-time {
  //        description "Maximum time to re-transmit a message in demand-circuit";
  //        type union {
  //          type string {
  //            pattern "<.*>|$.*";
  //          }
  //          type uint32 {
  //            range "5 .. 180";
  //          }
  //        }
  //      }
  //      container bfd-liveness-detection {
  //        description "Bidirectional Forwarding Detection options";
  //        // uses apply-advanced;
  //        leaf version {
  //          description "BFD protocol version number";
  //          default "automatic";
  //          type enumeration {
  //            enum "0" {
  //              description "BFD version 0 (deprecated)";
  //            }
  //            enum "1" {
  //              description "BFD version 1";
  //            }
  //            enum "automatic" {
  //              description "Choose BFD version automatically";
  //            }
  //          }
  //        }
  //        leaf minimum-interval {
  //          description "Minimum transmit and receive interval";
  //          units "milliseconds";
  //          type union {
  //            type string {
  //              pattern "<.*>|$.*";
  //            }
  //            type uint32 {
  //              range "1 .. 255000";
  //            }
  //          }
  //        }
  //        leaf minimum-transmit-interval {
  //          description "Minimum transmit interval";
  //          status deprecated;
  //          units "milliseconds";
  //          type union {
  //            type string {
  //              pattern "<.*>|$.*";
  //            }
  //            type uint32 {
  //              range "1 .. 255000";
  //            }
  //          }
  //        }
  //        leaf minimum-receive-interval {
  //          description "Minimum receive interval";
  //          units "milliseconds";
  //          type union {
  //            type string {
  //              pattern "<.*>|$.*";
  //            }
  //            type uint32 {
  //              range "1 .. 255000";
  //            }
  //          }
  //        }
  //        leaf multiplier {
  //          description "Detection time multiplier";
  //          default "3";
  //          type union {
  //            type string {
  //              pattern "<.*>|$.*";
  //            }
  //            type uint32 {
  //              range "1 .. 255";
  //            }
  //          }
  //        }
  //        leaf inline-disable {
  //          description "Disable inline mode for this BFD session";
  //          type empty;
  //        }
  //        leaf pdu-size {
  //          description "BFD transport protocol payload size";
  //          default "24";
  //          type union {
  //            type string {
  //              pattern "<.*>|$.*";
  //            }
  //            type uint32 {
  //              range "24 .. 9000";
  //            }
  //          }
  //        }
  //        choice adaptation-choice {
  //          case case_1 {
  //            leaf no-adaptation {
  //              description "Disable adaptation";
  //              type empty;
  //            }
  //          }
  //        }
  //        container transmit-interval {
  //          description "Transmit-interval options";
  //          // uses apply-advanced;
  //          leaf minimum-interval {
  //            description "Minimum transmit interval";
  //            units "milliseconds";
  //            type union {
  //              type string {
  //                pattern "<.*>|$.*";
  //              }
  //              type uint32 {
  //                range "1 .. 255000";
  //              }
  //            }
  //          }
  //          leaf threshold {
  //            description "High transmit interval triggering a trap";
  //            units "milliseconds";
  //            type union {
  //              type uint32;
  //              type string {
  //                pattern "<.*>|$.*";
  //              }
  //            }
  //          }
  //        }
  //        container detection-time {
  //          description "Detection-time options";
  //          // uses apply-advanced;
  //          leaf threshold {
  //            description "High detection-time triggering a trap";
  //            units "milliseconds";
  //            type union {
  //              type uint32;
  //              type string {
  //                pattern "<.*>|$.*";
  //              }
  //            }
  //          }
  //        }
  //        container authentication {
  //          description "Authentication options";
  //          // uses apply-advanced;
  //          leaf key-chain {
  //            description "Key chain name";
  //            type string;
  //          }
  //          leaf algorithm {
  //            description "Algorithm name";
  //            type enumeration {
  //              enum "simple-password" {
  //                description "Simple password";
  //              }
  //              enum "keyed-md5" {
  //                description "Keyed message Digest 5";
  //              }
  //              enum "meticulous-keyed-md5" {
  //                description "Meticulous keyed message Digest 5";
  //              }
  //              enum "keyed-sha-1" {
  //                description "Keyed secure hash algorithm (SHA1) ";
  //              }
  //              enum "meticulous-keyed-sha-1" {
  //                description "Meticulous keyed secure hash algorithm (SHA1) ";
  //              }
  //            }
  //          }
  //          leaf loose-check {
  //            description "Verify authentication only if authentication is negotiated";
  //            type empty;
  //          }
  //        }
  //      }
  //      list neighbor {
  //        key name;
  //        ordered-by user;
  //        description "Neighbor configuration";
  //        leaf name {
  //          description "Interface name";
  //          type union {
  //            type jt:interface-name;
  //            type string {
  //              pattern "<.*>|$.*";
  //            }
  //          }
  //        }
  //        // uses apply-advanced;
  //        leaf route-timeout {
  //          description "Delay before routes time out";
  //          units "seconds";
  //          type union {
  //            type string {
  //              pattern "<.*>|$.*";
  //            }
  //            type uint32 {
  //              range "30 .. 360";
  //            }
  //          }
  //        }
  //        leaf update-interval {
  //          description "Interval between regular route updates";
  //          units "seconds";
  //          type union {
  //            type string {
  //              pattern "<.*>|$.*";
  //            }
  //            type uint32 {
  //              range "10 .. 60";
  //            }
  //          }
  //        }
  //        leaf interface-type {
  //          description "Interface type for the neighbor";
  //          type enumeration {
  //            enum "p2mp" {
  //              description "Point-to-multipoint link";
  //            }
  //          }
  //        }
  //        leaf dynamic-peers {
  //          description "Learn peers dynamically on a p2mp interface";
  //          type empty;
  //        }
  //        list peer {
  //          key name;
  //          ordered-by user;
  //          description "P2MP peer";
  //          leaf name {
  //            description "Address of peer";
  //            type jt:ipaddr;
  //          }
  //        }
  //        leaf metric-in {
  //          description "Metric value to add to incoming routes";
  //          type union {
  //            type string {
  //              pattern "<.*>|$.*";
  //            }
  //            type uint32 {
  //              range "1 .. 15";
  //            }
  //          }
  //        }
  //        container send {
  //          description "Configure RIP send options";
  //          choice send-opts {
  //            case case_1 {
  //              leaf broadcast {
  //                description "Broadcast RIPv2 packets (RIPv1 compatible)";
  //                type empty;
  //              }
  //            }
  //            case case_2 {
  //              leaf multicast {
  //                description "Multicast RIPv2 packets";
  //                type empty;
  //              }
  //            }
  //            case case_3 {
  //              leaf none {
  //                description "Do not send RIP updates";
  //                type empty;
  //              }
  //            }
  //            case case_4 {
  //              leaf version-1 {
  //                description "Broadcast RIPv1 packets";
  //                type empty;
  //              }
  //            }
  //          }
  //        }
  //        container receive {
  //          description "Configure RIP receive options";
  //          choice receive-opts {
  //            case case_1 {
  //              leaf both {
  //                description "Accept both RIPv1 and RIPv2 packets";
  //                type empty;
  //              }
  //            }
  //            case case_2 {
  //              leaf none {
  //                description "Do not receive RIP packets";
  //                type empty;
  //              }
  //            }
  //            case case_3 {
  //              leaf version-1 {
  //                description "Accept RIPv1 packets only";
  //                type empty;
  //              }
  //            }
  //            case case_4 {
  //              leaf version-2 {
  //                description "Accept only RIPv2 packets";
  //                type empty;
  //              }
  //            }
  //          }
  //        }
  //        leaf demand-circuit {
  //          description "Enable demand circuit on this interface";
  //          type empty;
  //        }
  //        leaf max-retrans-time {
  //          description "Maximum time to re-transmit a msg in demand-circuit";
  //          type union {
  //            type string {
  //              pattern "<.*>|$.*";
  //            }
  //            type uint32 {
  //              range "5 .. 180";
  //            }
  //          }
  //        }
  //        choice check-zero-choice {
  //          leaf check-zero {
  //            description "Check reserved fields on incoming RIPv1 packets";
  //            type empty;
  //          }
  //          leaf no-check-zero {
  //            description "Don't check reserved fields on incoming RIPv1 packets";
  //            type empty;
  //          }
  //        }
  //        leaf any-sender {
  //          description "Disable strict checks on sender address";
  //          type empty;
  //        }
  //        leaf message-size {
  //          description "Number of route entries per update message";
  //          type union {
  //            type string {
  //              pattern "<.*>|$.*";
  //            }
  //            type uint32 {
  //              range "25 .. 255";
  //            }
  //          }
  //        }
  //        leaf-list import {
  //          ordered-by user;
  //          description "Import policy";
  //          type jt:policy-algebra;
  //        }
  //        choice authentication {
  //          case case_1 {
  //            leaf authentication-type {
  //              type enumeration {
  //                enum "none" {
  //                  description "No authentication";
  //                }
  //                enum "simple" {
  //                  description "Simple password authentication";
  //                }
  //                enum "md5" {
  //                  description "MD5 authentication";
  //                }
  //              }
  //            }
  //          }
  //          case case_2 {
  //            list authentication-selective-md5 {
  //              key name;
  //              ordered-by user;
  //              description "MD5 authentication with one or more keys";
  //              leaf name {
  //                description "Key ID for MD5 authentication";
  //                type union {
  //                  type string {
  //                    pattern "<.*>|$.*";
  //                  }
  //                  type uint32 {
  //                    range "0 .. 255";
  //                  }
  //                }
  //              }
  //              leaf key {
  //                description "MD5 authentication key value";
  //                type jt:unreadable;
  //              }
  //              leaf start-time {
  //                description "Start time for key transmission (YYYY-MM-DD.HH:MM)";
  //                type jt:time;
  //              }
  //            }
  //          }
  //        }
  //        leaf authentication-key {
  //          description "Authentication key (password)";
  //          type jt:unreadable;
  //        }
  //        container bfd-liveness-detection {
  //          description "Bidirectional Forwarding Detection options";
  //          // uses apply-advanced;
  //          leaf version {
  //            description "BFD protocol version number";
  //            default "automatic";
  //            type enumeration {
  //              enum "0" {
  //                description "BFD version 0 (deprecated)";
  //              }
  //              enum "1" {
  //                description "BFD version 1";
  //              }
  //              enum "automatic" {
  //                description "Choose BFD version automatically";
  //              }
  //            }
  //          }
  //          leaf minimum-interval {
  //            description "Minimum transmit and receive interval";
  //            units "milliseconds";
  //            type union {
  //              type string {
  //                pattern "<.*>|$.*";
  //              }
  //              type uint32 {
  //                range "1 .. 255000";
  //              }
  //            }
  //          }
  //          leaf minimum-transmit-interval {
  //            description "Minimum transmit interval";
  //            status deprecated;
  //            units "milliseconds";
  //            type union {
  //              type string {
  //                pattern "<.*>|$.*";
  //              }
  //              type uint32 {
  //                range "1 .. 255000";
  //              }
  //            }
  //          }
  //          leaf minimum-receive-interval {
  //            description "Minimum receive interval";
  //            units "milliseconds";
  //            type union {
  //              type string {
  //                pattern "<.*>|$.*";
  //              }
  //              type uint32 {
  //                range "1 .. 255000";
  //              }
  //            }
  //          }
  //          leaf multiplier {
  //            description "Detection time multiplier";
  //            default "3";
  //            type union {
  //              type string {
  //                pattern "<.*>|$.*";
  //              }
  //              type uint32 {
  //                range "1 .. 255";
  //              }
  //            }
  //          }
  //          leaf inline-disable {
  //            description "Disable inline mode for this BFD session";
  //            type empty;
  //          }
  //          leaf pdu-size {
  //            description "BFD transport protocol payload size";
  //            default "24";
  //            type union {
  //              type string {
  //                pattern "<.*>|$.*";
  //              }
  //              type uint32 {
  //                range "24 .. 9000";
  //              }
  //            }
  //          }
  //          choice adaptation-choice {
  //            case case_1 {
  //              leaf no-adaptation {
  //                description "Disable adaptation";
  //                type empty;
  //              }
  //            }
  //          }
  //          container transmit-interval {
  //            description "Transmit-interval options";
  //            // uses apply-advanced;
  //            leaf minimum-interval {
  //              description "Minimum transmit interval";
  //              units "milliseconds";
  //              type union {
  //                type string {
  //                  pattern "<.*>|$.*";
  //                }
  //                type uint32 {
  //                  range "1 .. 255000";
  //                }
  //              }
  //            }
  //            leaf threshold {
  //              description "High transmit interval triggering a trap";
  //              units "milliseconds";
  //              type union {
  //                type uint32;
  //                type string {
  //                  pattern "<.*>|$.*";
  //                }
  //              }
  //            }
  //          }
  //          container detection-time {
  //            description "Detection-time options";
  //            // uses apply-advanced;
  //            leaf threshold {
  //              description "High detection-time triggering a trap";
  //              units "milliseconds";
  //              type union {
  //                type uint32;
  //                type string {
  //                  pattern "<.*>|$.*";
  //                }
  //              }
  //            }
  //          }
  //          container authentication {
  //            description "Authentication options";
  //            // uses apply-advanced;
  //            leaf key-chain {
  //              description "Key chain name";
  //              type string;
  //            }
  //            leaf algorithm {
  //              description "Algorithm name";
  //              type enumeration {
  //                enum "simple-password" {
  //                  description "Simple password";
  //                }
  //                enum "keyed-md5" {
  //                  description "Keyed message Digest 5";
  //                }
  //                enum "meticulous-keyed-md5" {
  //                  description "Meticulous keyed message Digest 5";
  //                }
  //                enum "keyed-sha-1" {
  //                  description "Keyed secure hash algorithm (SHA1) ";
  //                }
  //                enum "meticulous-keyed-sha-1" {
  //                  description "Meticulous keyed secure hash algorithm (SHA1) ";
  //                }
  //              }
  //            }
  //            leaf loose-check {
  //              description "Verify authentication only if authentication is negotiated";
  //              type empty;
  //            }
  //          }
  //        }
  //      }
  //    }
  //    container graceful-restart {
  //      presence "enable graceful-restart";
  //      description "RIP graceful restart options";
  //      // uses apply-advanced;
  //      choice enable-disable {
  //        case case_1 {
  //          leaf disable {
  //            description "Disable graceful restart";
  //            type empty;
  //          }
  //        }
  //      }
  //      leaf restart-time {
  //        description "Time after which RIP is declared out of restart";
  //        type union {
  //          type string {
  //            pattern "<.*>|$.*";
  //          }
  //          type uint32 {
  //            range "1 .. 600";
  //          }
  //        }
  //      }
  //    }
  //  }
  //  grouping juniper-protocols-ripng {
  //    // uses apply-advanced;
  //    container traceoptions {
  //      description "Trace options for RIPng";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "error" {
  //              description "Trace RIPng errors";
  //            }
  //            enum "expiration" {
  //              description "Trace RIPng route expiration processing";
  //            }
  //            enum "holddown" {
  //              description "Trace RIPng hold-down processing";
  //            }
  //            enum "packets" {
  //              description "Trace all RIPng packets";
  //            }
  //            enum "request" {
  //              description "Trace RIPng information packets";
  //            }
  //            enum "trigger" {
  //              description "Trace RIPng triggered updates";
  //            }
  //            enum "update" {
  //              description "Trace RIPng update packets";
  //            }
  //            enum "nsr-synchronization" {
  //              description "Trace NSR synchronization events";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    leaf metric-in {
  //      description "Metric value to add to incoming routes";
  //      type union {
  //        type string {
  //          pattern "<.*>|$.*";
  //        }
  //        type uint32 {
  //          range "1 .. 15";
  //        }
  //      }
  //    }
  //    container send {
  //      description "Configure RIPng send options";
  //      choice send-opts {
  //        case case_1 {
  //          leaf none {
  //            description "Do not send RIPng updates";
  //            type empty;
  //          }
  //        }
  //      }
  //    }
  //    container receive {
  //      description "Configure RIPng receive options";
  //      choice receive-opts {
  //        case case_1 {
  //          leaf none {
  //            description "Do not receive RIPng packets";
  //            type empty;
  //          }
  //        }
  //      }
  //    }
  //    leaf-list import {
  //      ordered-by user;
  //      description "Import policy";
  //      type jt:policy-algebra;
  //    }
  //    leaf holddown {
  //      description "Hold-down time";
  //      units "seconds";
  //      type union {
  //        type string {
  //          pattern "<.*>|$.*";
  //        }
  //        type uint32 {
  //          range "10 .. 180";
  //        }
  //      }
  //    }
  //    leaf route-timeout {
  //      description "Delay before routes time out";
  //      units "seconds";
  //      type union {
  //        type string {
  //          pattern "<.*>|$.*";
  //        }
  //        type uint32 {
  //          range "30 .. 360";
  //        }
  //      }
  //    }
  //    leaf update-interval {
  //      description "Interval between regular route updates";
  //      units "seconds";
  //      type union {
  //        type string {
  //          pattern "<.*>|$.*";
  //        }
  //        type uint32 {
  //          range "10 .. 60";
  //        }
  //      }
  //    }
  //    list group {
  //      key name;
  //      ordered-by user;
  //      description "Instance configuration";
  //      leaf name {
  //        description "Group name";
  //        type string {
  //        }
  //      }
  //      // uses apply-advanced;
  //      leaf route-timeout {
  //        description "Delay before routes time out";
  //        units "seconds";
  //        type union {
  //          type string {
  //            pattern "<.*>|$.*";
  //          }
  //          type uint32 {
  //            range "30 .. 360";
  //          }
  //        }
  //      }
  //      leaf update-interval {
  //        description "Interval between regular route updates";
  //        units "seconds";
  //        type union {
  //          type string {
  //            pattern "<.*>|$.*";
  //          }
  //          type uint32 {
  //            range "10 .. 60";
  //          }
  //        }
  //      }
  //      leaf preference {
  //        description "Preference of routes learned by this group";
  //        type union {
  //          type uint32;
  //          type string {
  //            pattern "<.*>|$.*";
  //          }
  //        }
  //      }
  //      leaf metric-out {
  //        description "Default metric of exported routes";
  //        type union {
  //          type string {
  //            pattern "<.*>|$.*";
  //          }
  //          type uint32 {
  //            range "1 .. 15";
  //          }
  //        }
  //      }
  //      leaf-list export {
  //        ordered-by user;
  //        description "Export policy";
  //        type jt:policy-algebra;
  //      }
  //      leaf-list import {
  //        ordered-by user;
  //        description "Import policy";
  //        type jt:policy-algebra;
  //      }
  //      list neighbor {
  //        key name;
  //        ordered-by user;
  //        description "Neighbor configuration";
  //        leaf name {
  //          description "Interface name";
  //          type union {
  //            type jt:interface-name;
  //            type string {
  //              pattern "<.*>|$.*";
  //            }
  //          }
  //        }
  //        // uses apply-advanced;
  //        leaf route-timeout {
  //          description "Delay before routes time out";
  //          units "seconds";
  //          type union {
  //            type string {
  //              pattern "<.*>|$.*";
  //            }
  //            type uint32 {
  //              range "30 .. 360";
  //            }
  //          }
  //        }
  //        leaf update-interval {
  //          description "Interval between regular route updates";
  //          units "seconds";
  //          type union {
  //            type string {
  //              pattern "<.*>|$.*";
  //            }
  //            type uint32 {
  //              range "10 .. 60";
  //            }
  //          }
  //        }
  //        leaf metric-in {
  //          description "Metric value to add to incoming routes";
  //          type union {
  //            type string {
  //              pattern "<.*>|$.*";
  //            }
  //            type uint32 {
  //              range "1 .. 15";
  //            }
  //          }
  //        }
  //        container send {
  //          description "Configure RIPng send options";
  //          choice send-opts {
  //            case case_1 {
  //              leaf none {
  //                description "Do not send RIPng updates";
  //                type empty;
  //              }
  //            }
  //          }
  //        }
  //        container receive {
  //          description "Configure RIPng receive options";
  //          choice receive-opts {
  //            case case_1 {
  //              leaf none {
  //                description "Do not receive RIPng packets";
  //                type empty;
  //              }
  //            }
  //          }
  //        }
  //        leaf-list import {
  //          ordered-by user;
  //          description "Import policy";
  //          type jt:policy-algebra;
  //        }
  //      }
  //    }
  //    container graceful-restart {
  //      presence "enable graceful-restart";
  //      description "RIPng graceful restart options";
  //      // uses apply-advanced;
  //      choice enable-disable {
  //        case case_1 {
  //          leaf disable {
  //            description "Disable graceful restart";
  //            type empty;
  //          }
  //        }
  //      }
  //      leaf restart-time {
  //        description "Time after which RIPng is declared out of restart";
  //        type union {
  //          type string {
  //            pattern "<.*>|$.*";
  //          }
  //          type uint32 {
  //            range "1 .. 600";
  //          }
  //        }
  //      }
  //    }
  //  }
  //  grouping juniper-protocols-router-discovery {
  //    // uses apply-advanced;
  //    choice enable-disable {
  //      case case_1 {
  //        leaf disable {
  //          description "Disable router discovery";
  //          type empty;
  //        }
  //      }
  //    }
  //    container traceoptions {
  //      description "Trace options for router discovery";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //      }
  //    }
  //    list interface {
  //      key name;
  //      ordered-by user;
  //      description "Interfaces on which to configure router discovery";
  //      leaf name {
  //        description "Interface name";
  //        type union {
  //          type jt:interface-name;
  //          type string {
  //            pattern "<.*>|$.*";
  //          }
  //        }
  //      }
  //      // uses apply-advanced;
  //      leaf max-advertisement-interval {
  //        description "Maximum time before sending advertisements";
  //        units "seconds";
  //        type union {
  //          type string {
  //            pattern "<.*>|$.*";
  //          }
  //          type uint32 {
  //            range "4 .. 1800";
  //          }
  //        }
  //      }
  //      leaf min-advertisement-interval {
  //        description "Minimum time before sending advertisements";
  //        units "seconds";
  //        type union {
  //          type string {
  //            pattern "<.*>|$.*";
  //          }
  //          type uint32 {
  //            range "3 .. 1800";
  //          }
  //        }
  //      }
  //      leaf lifetime {
  //        description "How long addresses in advertisements are valid";
  //        units "seconds";
  //        type union {
  //          type string {
  //            pattern "<.*>|$.*";
  //          }
  //          type uint32 {
  //            range "3 .. 9000";
  //          }
  //        }
  //      }
  //    }
  //    list address {
  //      key name;
  //      ordered-by user;
  //      description "IP addresses to include in advertisements";
  //      leaf name {
  //        description "IP addresses to include in router advertisements";
  //        type jt:ipv4addr;
  //      }
  //      // uses apply-advanced;
  //      leaf advertise {
  //        description "Advertise the IP address in advertisements";
  //        type empty;
  //      }
  //      leaf ignore {
  //        description "Do not advertise the IP address in advertisements";
  //        type empty;
  //      }
  //      leaf broadcast {
  //        description "Include IP address only in broadcast advertisements";
  //        type empty;
  //      }
  //      leaf multicast {
  //        description "Include IP address only in multicast advertisements";
  //        type empty;
  //      }
  //      leaf ineligible {
  //        description "IP address can never become a default router";
  //        type empty;
  //      }
  //      leaf priority {
  //        description "Preference of the address to become a default router";
  //        type union {
  //          type int32;
  //          type string {
  //            pattern "<.*>|$.*";
  //          }
  //        }
  //      }
  //    }
  //  }
  //  grouping juniper-protocols-rsvp {
  //    description "RSVP options";
  //    // uses apply-advanced;
  //    choice enable-disable {
  //      case case_1 {
  //        leaf disable {
  //          description "Disable RSVP";
  //          type empty;
  //        }
  //      }
  //    }
  //    container graceful-restart {
  //      description "Configure graceful restart attributes";
  //      // uses apply-advanced;
  //      choice enable-disable {
  //        case case_1 {
  //          leaf disable {
  //            description "Disable RSVP graceful restart capability";
  //            type empty;
  //          }
  //        }
  //      }
  //      leaf helper-disable {
  //        description "Disable graceful restart helper capability";
  //        type empty;
  //      }
  //      leaf maximum-helper-restart-time {
  //        description "Maximum wait time from down event to neighbor dead";
  //        default "20";
  //        units "seconds";
  //        type union {
  //          type string {
  //            pattern "<.*>|$.*";
  //          }
  //          type uint32 {
  //            range "1 .. 1800";
  //          }
  //        }
  //      }
  //      leaf maximum-helper-recovery-time {
  //        description "Maximum time restarting neighbor states are kept";
  //        default "180";
  //        units "seconds";
  //        type union {
  //          type string {
  //            pattern "<.*>|$.*";
  //          }
  //          type uint32 {
  //            range "1 .. 3600";
  //          }
  //        }
  //      }
  //    }
  //    container tunnel-services {
  //      presence "enable tunnel-services";
  //      description "Use tunnel services for P2MP LSP ultimate-hop popping";
  //      // uses apply-advanced;
  //      leaf-list devices {
  //        ordered-by user;
  //        description "Tunnel services devices to use for P2MP LSPs";
  //        type union {
  //          type jt:interface-device;
  //          type string {
  //            pattern "<.*>|$.*";
  //          }
  //        }
  //      }
  //    }
  //    leaf no-p2mp-sublsp {
  //      description "Disable P2MP sub-LSP object generation";
  //      type empty;
  //    }
  //    leaf no-node-id-subobject {
  //      description "Do not include the node-id sub-object in the RRO";
  //      type empty;
  //    }
  //    leaf no-interface-hello {
  //      description "Disble interface Hellos on all RSVP interfaces";
  //      type empty;
  //    }
  //    container pop-and-forward {
  //      description "RSVP pop-and-forward specific global parameters";
  //      // uses apply-advanced;
  //      container application-label {
  //        description "Number of application labels under the RSVP transport";
  //        // uses apply-advanced;
  //        leaf depth {
  //          description "Application label depth";
  //          default "1";
  //          type union {
  //            type string {
  //              pattern "<.*>|$.*";
  //            }
  //            type uint32 {
  //              range "0 .. 3";
  //            }
  //          }
  //        }
  //      }
  //    }
  //    leaf hello-acknowledgements {
  //      description "Acknowledge Hellos on RSVP interfaces not having sessions";
  //      type empty;
  //    }
  //    leaf no-hello-acknowledgements {
  //      description "Do not ack Hellos on RSVP interfaces not having sessions";
  //      type empty;
  //    }
  //    container node-hello {
  //      presence "enable node-hello";
  //      description "Enable node-ID based Hellos on all RSVP interfaces";
  //      leaf hello-interval {
  //        description "Hello interval";
  //        default "9";
  //        units "seconds";
  //        type union {
  //          type string {
  //            pattern "<.*>|$.*";
  //          }
  //          type uint32 {
  //            range "0 .. 60";
  //          }
  //        }
  //      }
  //    }
  //    leaf no-node-hello {
  //      description "Disable node-ID based Hellos on the router";
  //      type empty;
  //    }
  //    leaf allow-bidirectional {
  //      description "Enable bidirectional support in RSVP";
  //      status deprecated;
  //      type empty;
  //    }
  //    leaf local-reversion {
  //      description "Enable local reversion at this Point of Local Repair";
  //      type empty;
  //    }
  //    leaf no-local-reversion {
  //      description "Disable local reversion at this Point of Local Repair";
  //      type empty;
  //    }
  //    leaf rfc6510-lsp-attributes {
  //      description "Use RFC6510 compliant LSP_ATTRIBUTES";
  //      type empty;
  //    }
  //    container fast-reroute {
  //      description "One-to-one fast-reroute protection mechanism";
  //      // uses apply-advanced;
  //      leaf optimize-timer {
  //        description "Frequency of reoptimization for fast-reroute detour";
  //        units "seconds";
  //        type union {
  //          type string {
  //            pattern "<.*>|$.*";
  //          }
  //          type int32 {
  //            range "0 .. 65535";
  //          }
  //        }
  //      }
  //    }
  //    container load-balance {
  //      description "Per-packet load-balancing algorithm";
  //      // uses apply-advanced;
  //      leaf bandwidth {
  //        description "Per-packet load balancing proportional to LSP bandwidth";
  //        type empty;
  //      }
  //    }
  //    container traceoptions {
  //      description "Trace options for RSVP";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "io-event" {
  //              description "Trace RSVP IO task related events";
  //            }
  //            enum "io-packets" {
  //              description "Trace all RSVP periodic refresh activity";
  //            }
  //            enum "packets" {
  //              description "Trace all RSVP trigger packets";
  //            }
  //            enum "path" {
  //              description "Trace RSVP trigger path messages";
  //            }
  //            enum "resv" {
  //              description "Trace RSVP trigger Resv messages";
  //            }
  //            enum "pathtear" {
  //              description "Trace RSVP PathTear messages";
  //            }
  //            enum "resvtear" {
  //              description "Trace RSVP ResvTear messages";
  //            }
  //            enum "state" {
  //              description "Trace state transitions";
  //            }
  //            enum "error" {
  //              description "Trace error conditions";
  //            }
  //            enum "route" {
  //              description "Trace routing information";
  //            }
  //            enum "lmp" {
  //              description "Trace RSVP-LMP related interactions";
  //            }
  //            enum "event" {
  //              description "Trace RSVP related events";
  //            }
  //            enum "nsr-synchronization" {
  //              description "Trace NSR synchronization events";
  //            }
  //            enum "lsp-prefix" {
  //              description "Prefix the trace messages with LSP information";
  //            }
  //            enum "enhanced-frr" {
  //              description "Enhanced FRR related information";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    leaf refresh-time {
  //      description "Refresh time in seconds";
  //      default "1200";
  //      type union {
  //        type string {
  //          pattern "<.*>|$.*";
  //        }
  //        type uint32 {
  //          range "1 .. 65535";
  //        }
  //      }
  //    }
  //    leaf keep-multiplier {
  //      description "Keep multiplier";
  //      default "3";
  //      type union {
  //        type string {
  //          pattern "<.*>|$.*";
  //        }
  //        type uint32 {
  //          range "1 .. 255";
  //        }
  //      }
  //    }
  //    leaf graceful-deletion-timeout {
  //      description "Time to complete graceful deletion signaling";
  //      default "30";
  //      units "seconds";
  //      type union {
  //        type string {
  //          pattern "<.*>|$.*";
  //        }
  //        type uint32 {
  //          range "1 .. 300";
  //        }
  //      }
  //    }
  //    leaf setup-protection {
  //      description "Enable setup protection";
  //      type empty;
  //    }
  //    leaf no-p2mp-re-merge {
  //      description "Enable p2mp remerge";
  //      type empty;
  //    }
  //    leaf cross-credibility-cspf {
  //      description "Compute CSPF paths spanning protocols for bypass LSP, detour LSP and loose hop expansion";
  //      type empty;
  //    }
  //    container preemption {
  //      description "Set RSVP session preemption attributes";
  //      // uses apply-advanced;
  //      choice preemption-type {
  //        case case_1 {
  //          leaf disabled {
  //            description "No RSVP session preemption";
  //            type empty;
  //          }
  //        }
  //        case case_2 {
  //          leaf normal {
  //            description "Run RSVP session preemption to accommodate new sessions";
  //            type empty;
  //          }
  //        }
  //        case case_3 {
  //          leaf aggressive {
  //            description "Run RSVP session preemption whenever necessary";
  //            type empty;
  //          }
  //        }
  //      }
  //      container soft-preemption {
  //        description "Options for establishing new path before tearing down a preempted LSP";
  //        // uses apply-advanced;
  //        leaf cleanup-timer {
  //          description "Time a soft-preempted LSP will be maintained";
  //          units "seconds";
  //          type union {
  //            type string {
  //              pattern "<.*>|$.*";
  //            }
  //            type int32 {
  //              range "0 .. 10800";
  //            }
  //          }
  //        }
  //      }
  //    }
  //    leaf authentication-key {
  //      description "Authentication password";
  //      type jt:unreadable;
  //    }
  //    leaf no-authentication-check {
  //      description "Skip authentication check for received messages";
  //      type empty;
  //    }
  //    container associated-bidirectional-lsp {
  //      description "Set associated bidirectional LSP attributes";
  //      // uses apply-advanced;
  //      leaf single-sided-provisioning {
  //        description "Enable unidirectional reverse LSP setup for single sided provisioned forward LSP";
  //        type empty;
  //      }
  //    }
  //    leaf no-enhanced-frr-bypass {
  //      description "Disable enhanced facility backup FRR";
  //      type empty;
  //    }
  //    leaf no-node-hello-on-bypass {
  //      description "Do not send NodeID hello over bypass LSP";
  //      type empty;
  //    }
  //    container expand-flood-reflector-hop {
  //      presence "enable expand-flood-reflector-hop";
  //      description "Control expansion of flood reflector ERO strict hops";
  //    }
  //    list interface {
  //      key name;
  //      ordered-by user;
  //      description "RSVP interface options";
  //      leaf name {
  //        description "Interface name";
  //        type union {
  //          type jt:interface-name;
  //          type string {
  //            pattern "<.*>|$.*";
  //          }
  //        }
  //      }
  //      // uses apply-advanced;
  //      choice enable-disable {
  //        case case_1 {
  //          leaf disable {
  //            description "Disable RSVP on this interface";
  //            type empty;
  //          }
  //        }
  //      }
  //      leaf authentication-key {
  //        description "Authentication password";
  //        type jt:unreadable;
  //      }
  //      choice aggregate-choice {
  //        leaf aggregate {
  //          description "Permit refresh reduction extensions on the interface";
  //          status deprecated;
  //          type empty;
  //        }
  //        leaf no-aggregate {
  //          description "Don't permit refresh reduction extensions on the interface";
  //          status deprecated;
  //          type empty;
  //        }
  //      }
  //      choice reliable-choice {
  //        leaf reliable {
  //          description "Permit reliable message delivery on the interface";
  //          type empty;
  //        }
  //        leaf no-reliable {
  //          description "Don't permit reliable message delivery on the interface";
  //          type empty;
  //        }
  //      }
  //      leaf hello-interval {
  //        description "Hello interval";
  //        default "9";
  //        units "seconds";
  //        type union {
  //          type string {
  //            pattern "<.*>|$.*";
  //          }
  //          type uint32 {
  //            range "0 .. 60";
  //          }
  //        }
  //      }
  //     //  container subscription {
  //     //    description "Link bandwidth percentage for RSVP reservation";
  //     //    uses subscription-type;
  //     //  }
  //      leaf bandwidth {
  //        description "Available bandwidth for the interface units bps";
  //        type string;
  //      }
  //     //  container update-threshold {
  //     //    description "Change in reserved bandwidth to trigger IGP update";
  //     //    // uses apply-advanced;
  //     //    container adaptive {
  //     //      description "Tune update-threshold dynamically";
  //     //      // uses apply-advanced;
  //     //      list limit {
  //     //        key name;
  //     //        description "Available Bandwidth threshold limit";
  //     //        leaf name {
  //     //          description "Upper limit of Available bandwidth for this range";
  //     //          type string;
  //     //        }
  //     //        leaf threshold-percent {
  //     //          description "Percentage change in reserved bandwidth to trigger IGP update";
  //     //          default "10.0";
  //     //          units "percent";
  //     //          type decimal64 {
  //     //            fraction-digits 9;
  //     //            range "0.001 .. 20";
  //     //          }
  //     //        }
  //     //        leaf threshold-value {
  //     //          description "Change in reserved bandwidth to trigger IGP update (will be capped at 20% of link BW)";
  //     //          type string;
  //     //        }
  //     //      }
  //     //    }
  //     //    leaf threshold-percent {
  //     //      description "Percentage change in reserved bandwidth to trigger IGP update";
  //     //      default "10.0";
  //     //      units "percent";
  //     //      type decimal64 {
  //     //        fraction-digits 9;
  //     //        range "0.001 .. 20";
  //     //      }
  //     //    }
  //     //    leaf threshold-value {
  //     //      description "Change in reserved bandwidth to trigger IGP update (will be capped at 20% of link BW)";
  //     //      type string;
  //     //    }
  //     //  }
  //     //  container update-threshold-max-reservable {
  //     //    description "Change in non-rsvp bandwidth to trigger IGP update ";
  //     //    // uses apply-advanced;
  //     //    leaf bandwidth {
  //     //      description "Change in non-rsvp bandwidth to trigger IGP update units bps";
  //     //      type string;
  //     //    }
  //     //    leaf percent {
  //     //      description "Percentage change in max-reservable bandwidth to trigger IGP update";
  //     //      units "percent";
  //     //      type union {
  //     //        type string {
  //     //          pattern "<.*>|$.*";
  //     //        }
  //     //        type uint32 {
  //     //          range "1 .. 100";
  //     //        }
  //     //      }
  //     //    }
  //     //  }
  //      container non-rsvp-bandwdith {
  //        description "Config knobs relating to non-rsvp bandwidth";
  //        // uses apply-advanced;
  //        leaf local-bw-override-threshold {
  //          description "Overide threshold and update local bandwidth with non-rsvp bandwidth usage";
  //          type empty;
  //        }
  //      }
  //      container link-protection {
  //        presence "enable link-protection";
  //        description "Protect traffic with a label-stacked LSP";
  //        // uses apply-advanced;
  //        choice enable-disable {
  //          case case_1 {
  //            leaf disable {
  //              description "Disable link protection on this interface";
  //              type empty;
  //            }
  //          }
  //        }
  //        container bandwidth {
  //          description "Bandwidth for each bypass";
  //          uses bandwidth-type;
  //        }
  //        leaf max-bypasses {
  //          description "Max number of bypasses permitted for protecting this interface";
  //          default "1";
  //          type union {
  //            type string {
  //              pattern "<.*>|$.*";
  //            }
  //            type uint32 {
  //              range "0 .. 99";
  //            }
  //          }
  //        }
  //        leaf subscription {
  //          description "Percent of bandwidth guaranteed when admitting protected LSPs into bypasses";
  //          default "100";
  //          type union {
  //            type string {
  //              pattern "<.*>|$.*";
  //            }
  //            type uint32 {
  //              range "1 .. 65535";
  //            }
  //          }
  //        }
  //        leaf no-node-protection {
  //          description "Disallow node protection on this interface";
  //          type empty;
  //        }
  //        leaf optimize-timer {
  //          description "Interval between bypass reoptimizations";
  //          default "0";
  //          units "seconds";
  //          type union {
  //            type string {
  //              pattern "<.*>|$.*";
  //            }
  //            type uint32 {
  //              range "0 .. 65535";
  //            }
  //          }
  //        }
  //        leaf class-of-service {
  //          description "Class of service for the bypass LSP";
  //          type union {
  //            type string {
  //              pattern "<.*>|$.*";
  //            }
  //            type int32 {
  //              range "0 .. 7";
  //            }
  //          }
  //        }
  //        leaf hop-limit {
  //          description "Maximum allowed router hops for bypass";
  //          type union {
  //            type string {
  //              pattern "<.*>|$.*";
  //            }
  //            type uint32 {
  //              range "2 .. 255";
  //            }
  //          }
  //        }
  //        leaf no-cspf {
  //          description "Disable automatic path computation";
  //          type empty;
  //        }
  //        leaf exclude-srlg {
  //          description "Exclude SRLG links";
  //          type empty;
  //        }
  //        container priority {
  //          presence "enable priority";
  //          description "Preemption priorities for the bypass LSP";
  //        }
  //        leaf setup-priority {
  //          description "Set-up priority";
  //          type union {
  //            type string {
  //              pattern "<.*>|$.*";
  //            }
  //            type uint32 {
  //              range "0 .. 7";
  //            }
  //          }
  //        }
  //        leaf reservation-priority {
  //          description "Reservation priority";
  //          type union {
  //            type string {
  //              pattern "<.*>|$.*";
  //            }
  //            type uint32 {
  //              range "0 .. 7";
  //            }
  //          }
  //        }
  //        list path {
  //          key name;
  //          ordered-by user;
  //          description "Explicit route of bypass path";
  //          leaf name {
  //            description "Address of next system in path";
  //            type jt:ipv4addr;
  //          }
  //          choice loose_strict_none {
  //            case case_1 {
  //              leaf loose {
  //                description "Next hop might not be adjacent";
  //                type empty;
  //              }
  //            }
  //            case case_2 {
  //              leaf strict {
  //                description "Next hop must be adjacent";
  //                type empty;
  //              }
  //            }
  //          }
  //        }
  //        container admin-group {
  //          description "Administrative group policy";
  //          uses admin_group_include_exclude;
  //        }
  //       //  list bypass {
  //       //    key name;
  //       //    ordered-by user;
  //       //    description "Bypass with specific constraints";
  //       //    leaf name {
  //       //      description "Name of bypass";
  //       //      type string {
  //       //        length "1 .. 64";
  //       //      }
  //       //    }
  //       //    // uses apply-advanced;
  //       //    leaf to {
  //       //      description "Address of egress router";
  //       //      type jt:ipv4addr;
  //       //    }
  //       //    container bandwidth {
  //       //      description "Bandwidth for each bypass";
  //       //      uses bandwidth-type;
  //       //    }
  //       //    container subscription {
  //       //      description "Bandwidth percent available on bypass for protected LSPs";
  //       //      presence "enable subscription";
  //       //      uses bypass-subscription-type;
  //       //    }
  //       //    leaf description {
  //       //      description "Text description of bypass";
  //       //      type string {
  //       //        length "1 .. 80";
  //       //      }
  //       //    }
  //       //    container priority {
  //       //      presence "enable priority";
  //       //      description "Preemption priorities for bypass";
  //       //    }
  //       //    leaf setup-priority {
  //       //      description "Set-up priority";
  //       //      type union {
  //       //        type string {
  //       //          pattern "<.*>|$.*";
  //       //        }
  //       //        type uint32 {
  //       //          range "0 .. 7";
  //       //        }
  //       //      }
  //       //    }
  //       //    leaf reservation-priority {
  //       //      description "Reservation priority";
  //       //      type union {
  //       //        type string {
  //       //          pattern "<.*>|$.*";
  //       //        }
  //       //        type uint32 {
  //       //          range "0 .. 7";
  //       //        }
  //       //      }
  //       //    }
  //       //    leaf class-of-service {
  //       //      description "Class of service for the bypass LSP";
  //       //      type union {
  //       //        type string {
  //       //          pattern "<.*>|$.*";
  //       //        }
  //       //        type int32 {
  //       //          range "0 .. 7";
  //       //        }
  //       //      }
  //       //    }
  //       //    leaf hop-limit {
  //       //      description "Maximum allowed router hops for bypass";
  //       //      type union {
  //       //        type string {
  //       //          pattern "<.*>|$.*";
  //       //        }
  //       //        type uint32 {
  //       //          range "2 .. 255";
  //       //        }
  //       //      }
  //       //    }
  //       //    leaf no-cspf {
  //       //      description "Disable automatic path computation";
  //       //      type empty;
  //       //    }
  //       //    leaf exclude-srlg {
  //       //      description "Exclude SRLG links";
  //       //      type empty;
  //       //    }
  //       //    list path {
  //       //      key name;
  //       //      ordered-by user;
  //       //      description "Explicit route of bypass path";
  //       //      leaf name {
  //       //        description "Address of next system in path";
  //       //        type jt:ipv4addr;
  //       //      }
  //       //      choice loose_strict_none {
  //       //        case case_1 {
  //       //          leaf loose {
  //       //            description "Next hop might not be adjacent";
  //       //            type empty;
  //       //          }
  //       //        }
  //       //        case case_2 {
  //       //          leaf strict {
  //       //            description "Next hop must be adjacent";
  //       //            type empty;
  //       //          }
  //       //        }
  //       //      }
  //       //    }
  //       //    container admin-group {
  //       //      description "Administrative group policy";
  //       //      uses admin_group_include_exclude;
  //       //    }
  //       //  }
  //       //  container optimize {
  //       //    description "Configure compute optimization algorithm";
  //       //    // uses apply-advanced;
  //       //    choice compute-algo {
  //       //      case case_1 {
  //       //        leaf bandwidth {
  //       //          description "Compute path optimized for available bandwidth";
  //       //          type empty;
  //       //        }
  //       //      }
  //       //    }
  //       //  }
  //      }
  //    }
  //    list peer-interface {
  //      key name;
  //      ordered-by user;
  //      description "Configuration for peer interface";
  //      leaf name {
  //        description "Name of peer interface";
  //        type string;
  //      }
  //      // uses apply-advanced;
  //      choice enable-disable {
  //        case case_1 {
  //          leaf disable {
  //            description "Disable RSVP on this control peer";
  //            type empty;
  //          }
  //        }
  //      }
  //      leaf authentication-key {
  //        description "Authentication password";
  //        type jt:unreadable;
  //      }
  //      choice aggregate-choice {
  //        leaf aggregate {
  //          description "Permit refresh reduction extensions on the interface";
  //          status deprecated;
  //          type empty;
  //        }
  //        leaf no-aggregate {
  //          description "Don't permit refresh reduction extensions on the interface";
  //          status deprecated;
  //          type empty;
  //        }
  //      }
  //      choice reliable-choice {
  //        leaf reliable {
  //          description "Permit reliable message delivery on the interface";
  //          type empty;
  //        }
  //        leaf no-reliable {
  //          description "Don't permit reliable message delivery on the interface";
  //          type empty;
  //        }
  //      }
  //      leaf hello-interval {
  //        description "Hello interval";
  //        default "9";
  //        units "seconds";
  //        type union {
  //          type string {
  //            pattern "<.*>|$.*";
  //          }
  //          type uint32 {
  //            range "0 .. 60";
  //          }
  //        }
  //      }
  //      container dynamic-bidirectional-transport {
  //        presence "enable dynamic-bidirectional-transport";
  //        description "Enable dynamic setup of bidirectional packet LSP for transporting non-packet GMPLS LSP";
  //        // uses apply-advanced;
  //        leaf template {
  //          description "Template for the dynamic bidirectional packet LSP";
  //          type string {
  //          }
  //        }
  //      }
  //    }
  //    list lsp-set {
  //      key name;
  //      ordered-by user;
  //      description "Configuration for lsp set";
  //      leaf name {
  //        description "Name of lsp set";
  //        type string;
  //      }
  //      // uses apply-advanced;
  //      choice enable-disable {
  //        case case_1 {
  //          leaf disable {
  //            description "Disable this lsp set";
  //            type empty;
  //          }
  //        }
  //      }
  //      container match-criteria {
  //        description "Match criteria for this lsp set";
  //        uses lsp-set-match-type;
  //      }
  //      container traceoptions {
  //        description "Trace options for this lsp set";
  //        // uses apply-advanced;
  //        container file {
  //          description "Trace file options";
  //          leaf filename {
  //            description "Name of file in which to write trace information";
  //            type string {
  //              length "1 .. 1024";
  //            }
  //          }
  //          leaf replace {
  //            description "Replace trace file rather than appending to it";
  //            status deprecated;
  //            type empty;
  //          }
  //          leaf size {
  //            description "Maximum trace file size";
  //            type string;
  //          }
  //          leaf files {
  //            description "Maximum number of trace files";
  //            default "10";
  //            type union {
  //              type string {
  //                pattern "<.*>|$.*";
  //              }
  //              type uint32 {
  //                range "2 .. 1000";
  //              }
  //            }
  //          }
  //          leaf no-stamp {
  //            description "Do not timestamp trace file";
  //            status deprecated;
  //            type empty;
  //          }
  //          choice world-readable-choice {
  //            leaf world-readable {
  //              description "Allow any user to read the log file";
  //              type empty;
  //            }
  //            leaf no-world-readable {
  //              description "Don't allow any user to read the log file";
  //              type empty;
  //            }
  //          }
  //        }
  //        list flag {
  //          key name;
  //          ordered-by user;
  //          description "Tracing parameters";
  //          leaf name {
  //            type enumeration {
  //              enum "io-event" {
  //                description "Trace RSVP IO task related events";
  //              }
  //              enum "io-packets" {
  //                description "Trace all RSVP periodic refresh activity";
  //              }
  //              enum "packets" {
  //                description "Trace all RSVP packets";
  //              }
  //              enum "path" {
  //                description "Trace RSVP path messages";
  //              }
  //              enum "resv" {
  //                description "Trace RSVP Resv messages";
  //              }
  //              enum "pathtear" {
  //                description "Trace RSVP PathTear messages";
  //              }
  //              enum "resvtear" {
  //                description "Trace RSVP ResvTear messages";
  //              }
  //              enum "state" {
  //                description "Trace state transitions";
  //              }
  //              enum "error" {
  //                description "Trace error conditions";
  //              }
  //              enum "route" {
  //                description "Trace routing information";
  //              }
  //              enum "lmp" {
  //                description "Trace RSVP-LMP related interactions";
  //              }
  //              enum "event" {
  //                description "Trace RSVP related events";
  //              }
  //              enum "nsr-synchronization" {
  //                description "Trace NSR synchronization events";
  //              }
  //              enum "lsp-prefix" {
  //                description "Prefix the trace messages with LSP information";
  //              }
  //              enum "enhanced-frr" {
  //                description "Enhanced FRR related information";
  //              }
  //              enum "all" {
  //                description "Trace everything";
  //              }
  //            }
  //          }
  //          leaf send {
  //            description "Trace transmitted packets";
  //            type empty;
  //          }
  //          leaf receive {
  //            description "Trace received packets";
  //            type empty;
  //          }
  //          leaf detail {
  //            description "Trace detailed information";
  //            type empty;
  //          }
  //          leaf disable {
  //            description "Disable this trace flag";
  //            type empty;
  //          }
  //        }
  //      }
  //    }
  //  }
  //  grouping bypass-subscription-type {
  //    // uses apply-advanced;
  //    leaf subscription {
  //      description "Subscription percentage for bandwidth protection";
  //      default "100";
  //      type string;
  //    }
  //  }
  //  grouping juniper-protocols-stp {
  //    // uses apply-advanced;
  //    choice enable-disable {
  //      case case_1 {
  //        leaf disable {
  //          description "Disable STP";
  //          type empty;
  //        }
  //      }
  //    }
  //    leaf bpdu-destination-mac-address {
  //      description "Destination MAC address in the spanning tree BPDUs";
  //      type enumeration {
  //        enum "provider-bridge-group" {
  //          description "802.1ad provider bridge group address";
  //        }
  //      }
  //    }
  //    leaf bridge-priority {
  //      description "Priority of the bridge (in increments of 4k - 0,4k,8k,..60k)";
  //      type string {
  //      }
  //    }
  //    leaf backup-bridge-priority {
  //      description "Priority of the bridge (in increments of 4k - 4k,8k,..60k)";
  //      type string {
  //      }
  //    }
  //    leaf max-age {
  //      description "Maximum age of received protocol bpdu";
  //      units "seconds";
  //      type union {
  //        type string {
  //          pattern "<.*>|$.*";
  //        }
  //        type uint16 {
  //          range "6 .. 40";
  //        }
  //      }
  //    }
  //    leaf hello-time {
  //      description "Time interval between configuration BPDUs";
  //      units "seconds";
  //      type union {
  //        type string {
  //          pattern "<.*>|$.*";
  //        }
  //        type uint16 {
  //          range "1 .. 10";
  //        }
  //      }
  //    }
  //    leaf forward-delay {
  //      description "Time spent in listening or learning state";
  //      units "seconds";
  //      type union {
  //        type string {
  //          pattern "<.*>|$.*";
  //        }
  //        type uint16 {
  //          range "4 .. 30";
  //        }
  //      }
  //    }
  //    leaf system-identifier {
  //      description "Sytem identifier to represent this node";
  //      type jt:mac-unicast;
  //    }
  //    container traceoptions {
  //      description "Tracing options for debugging protocol operation";
  //      uses stp-trace-options;
  //    }
  //    leaf vpls-flush-on-topology-change {
  //      description "Enable VPLS MAC flush on root protected CE interface receving topology change";
  //      type empty;
  //    }
  //    leaf priority-hold-time {
  //      description "Hold time before switching to primary priority when core domain becomes up";
  //      units "seconds";
  //      type union {
  //        type string {
  //          pattern "<.*>|$.*";
  //        }
  //        type uint16 {
  //          range "1 .. 255";
  //        }
  //      }
  //    }
  //    list system-id {
  //      key name;
  //      ordered-by user;
  //      description "System ID to IP mapping";
  //      uses system-id-ip-map;
  //    }
  //    list interface {
  //      key name;
  //      description "Interface options";
  //      uses stp-interface;
  //    }
  //    leaf extended-system-id {
  //      description "Extended system identifier";
  //      type union {
  //        type string {
  //          pattern "<.*>|$.*";
  //        }
  //        type uint16 {
  //          range "0 .. 4095";
  //        }
  //      }
  //    }
  //    leaf force-version {
  //      description "Force protocol version";
  //      type enumeration {
  //        enum "stp" {
  //          description "Spanning tree protocol";
  //        }
  //      }
  //    }
  //    leaf bpdu-block-on-edge {
  //      description "Block BPDU on all interfaces configured as edge (BPDU Protect)";
  //      type empty;
  //    }
  //  }
  //  grouping juniper-protocols-vstp {
  //    // uses apply-advanced;
  //    choice enable-disable {
  //      case case_1 {
  //        leaf disable {
  //          description "Disable VSTP";
  //          type empty;
  //        }
  //      }
  //    }
  //    leaf force-version {
  //      description "Force protocol version";
  //      type enumeration {
  //        enum "stp" {
  //          description "Spanning tree protocol";
  //        }
  //      }
  //    }
  //    leaf bpdu-block-on-edge {
  //      description "Block BPDU on all interfaces configured as edge (BPDU Protect)";
  //      type empty;
  //    }
  //    leaf vpls-flush-on-topology-change {
  //      description "Enable VPLS MAC flush on root protected CE interface receving topology change";
  //      type empty;
  //    }
  //    leaf priority-hold-time {
  //      description "Hold time before switching to primary priority when core domain becomes up";
  //      units "seconds";
  //      type union {
  //        type string {
  //          pattern "<.*>|$.*";
  //        }
  //        type uint16 {
  //          range "1 .. 255";
  //        }
  //      }
  //    }
  //    list system-id {
  //      key name;
  //      ordered-by user;
  //      description "System ID to IP mapping";
  //      uses system-id-ip-map;
  //    }
  //    list interface {
  //      key name;
  //      description "Interface options";
  //      uses stp-interface;
  //    }
  //    list vlan {
  //      key name;
  //      description "VLAN spanning tree options";
  //      leaf name {
  //        description "VLAN id or all";
  //        type string;
  //      }
  //      // uses apply-advanced;
  //      leaf bridge-priority {
  //        description "Priority of the bridge (in increments of 4k - 0,4k,8k,..60k)";
  //        type string {
  //        }
  //      }
  //      leaf backup-bridge-priority {
  //        description "Priority of the bridge (in increments of 4k - 4k,8k,..60k)";
  //        type string {
  //        }
  //      }
  //      leaf max-age {
  //        description "Maximum age of received protocol bpdu";
  //        units "seconds";
  //        type union {
  //          type string {
  //            pattern "<.*>|$.*";
  //          }
  //          type uint16 {
  //            range "6 .. 40";
  //          }
  //        }
  //      }
  //      leaf hello-time {
  //        description "Time interval between configuration BPDUs";
  //        units "seconds";
  //        type union {
  //          type string {
  //            pattern "<.*>|$.*";
  //          }
  //          type uint16 {
  //            range "1 .. 10";
  //          }
  //        }
  //      }
  //      leaf forward-delay {
  //        description "Time spent in listening or learning state";
  //        units "seconds";
  //        type union {
  //          type string {
  //            pattern "<.*>|$.*";
  //          }
  //          type uint16 {
  //            range "4 .. 30";
  //          }
  //        }
  //      }
  //      leaf system-identifier {
  //        description "Sytem identifier to represent this node";
  //        type jt:mac-unicast;
  //      }
  //      container traceoptions {
  //        description "Tracing options for debugging protocol operation";
  //        uses stp-trace-options;
  //      }
  //      list interface {
  //        key name;
  //        description "Interface options";
  //        uses stp-interface;
  //      }
  //    }
  //    container vlan-group {
  //      presence "enable vlan-group";
  //      description "Spanning tree options for group of VLANs";
  //      // uses apply-advanced;
  //      list group {
  //        key name;
  //        ordered-by user;
  //        description "Name if VLAN group";
  //        leaf name {
  //          description "VLAN group name";
  //          type string {
  //            length "1 .. 63";
  //          }
  //        }
  //        // uses apply-advanced;
  //        leaf-list vlan {
  //          ordered-by user;
  //          description "VLAN ID or VLAN ID range [1..4094]";
  //          type string;
  //        }
  //        leaf bridge-priority {
  //          description "Priority of the bridge (in increments of 4k - 0,4k,8k,..60k)";
  //          type string {
  //          }
  //        }
  //        leaf backup-bridge-priority {
  //          description "Priority of the bridge (in increments of 4k - 4k,8k,..60k)";
  //          type string {
  //          }
  //        }
  //        leaf max-age {
  //          description "Maximum age of received protocol bpdu";
  //          units "seconds";
  //          type union {
  //            type string {
  //              pattern "<.*>|$.*";
  //            }
  //            type uint16 {
  //              range "6 .. 40";
  //            }
  //          }
  //        }
  //        leaf hello-time {
  //          description "Time interval between configuration BPDUs";
  //          units "seconds";
  //          type union {
  //            type string {
  //              pattern "<.*>|$.*";
  //            }
  //            type uint16 {
  //              range "1 .. 10";
  //            }
  //          }
  //        }
  //        leaf forward-delay {
  //          description "Time spent in listening or learning state";
  //          units "seconds";
  //          type union {
  //            type string {
  //              pattern "<.*>|$.*";
  //            }
  //            type uint16 {
  //              range "4 .. 30";
  //            }
  //          }
  //        }
  //        leaf system-identifier {
  //          description "Sytem identifier to represent this node";
  //          type jt:mac-unicast;
  //        }
  //        container traceoptions {
  //          description "Tracing options for debugging protocol operation";
  //          uses stp-trace-options;
  //        }
  //        list interface {
  //          key name;
  //          description "Interface options";
  //          uses stp-interface;
  //        }
  //      }
  //    }
  //  }
   grouping juniper-ri-protocols-bfd {
     // uses apply-advanced;
     container sbfd {
       description "Seamless BFD parameters";
       // uses apply-advanced;
       leaf-list pool {
         description "List of seamless BFD endpoints";
         type union {
           type uint32;
           type string {
             pattern "<.*>|$.*";
           }
         }
       }
       list local-discriminator {
         key name;
         ordered-by user;
         description "Local discriminator for seamless BFD responder";
         leaf name {
           description "Local discriminator for seamless BFD responder";
           type union {
             type string {
               pattern "<.*>|$.*";
             }
             type uint32 {
               range "1 .. 4294967295";
             }
           }
         }
         // uses apply-advanced;
         leaf minimum-receive-interval {
           description "Minimum receive interval for seamless BFD responder";
           units "milliseconds";
           type union {
             type string {
               pattern "<.*>|$.*";
             }
             type uint32 {
               range "10 .. 255000";
             }
           }
         }
         leaf local-ip-address {
           description "IPv4 source address";
           type jt:ipv4addr;
         }
         leaf local-ipv6-address {
           description "IPv6 source address";
           type jt:ipv6addr;
         }
       }
       list local-discriminator-ip {
         key name;
         ordered-by user;
         description "Local discriminator IP address for sBFD responder";
         leaf name {
           description "Local discriminator IP address for sBFD responder";
           type jt:ipv4addr;
         }
         // uses apply-advanced;
         leaf minimum-receive-interval {
           description "Minimum receive interval for seamless BFD responder";
           units "milliseconds";
           type union {
             type string {
               pattern "<.*>|$.*";
             }
             type uint32 {
               range "10 .. 255000";
             }
           }
         }
         leaf local-ip-address {
           description "IPv4 source address";
           type jt:ipv4addr;
         }
       }
     }
   }
  //  grouping juniper-ri-protocols-igmp-snooping {
  //    description "IGMP snooping options";
  //    // uses apply-advanced;
  //    container traceoptions {
  //      description "Trace options for IGMP Snooping";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "packets" {
  //              description "Trace all IGMP packets";
  //            }
  //            enum "query" {
  //              description "Trace IGMP membership query messages";
  //            }
  //            enum "report" {
  //              description "Trace membership report messages";
  //            }
  //            enum "leave" {
  //              description "Trace leave group messages (IGMPv2 only)";
  //            }
  //            enum "group" {
  //              description "Trace group operations";
  //            }
  //            enum "client-notification" {
  //              description "Trace notifications";
  //            }
  //            enum "host-notification" {
  //              description "Trace host notifications";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    leaf query-interval {
  //      description "When to send host query messages";
  //      default "125";
  //      units "seconds";
  //      type union {
  //        type string {
  //          pattern "<.*>|$.*";
  //        }
  //        type uint32 {
  //          range "1 .. 1024";
  //        }
  //      }
  //    }
  //    container l2-querier {
  //      description "Enable L2 querier mode";
  //      // uses apply-advanced;
  //      leaf source-address {
  //        description "Source IP address to use for L2 querier";
  //        type jt:ipv4addr;
  //      }
  //    }
  //    leaf query-response-interval {
  //      description "How long to wait for a host query response";
  //      default "10";
  //      units "seconds";
  //      type string {
  //      }
  //    }
  //    leaf query-last-member-interval {
  //      description "When to send group query messages";
  //      default "1";
  //      units "seconds";
  //      type string {
  //      }
  //    }
  //    leaf robust-count {
  //      description "Expected packet loss on a subnet";
  //      default "2";
  //      type union {
  //        type string {
  //          pattern "<.*>|$.*";
  //        }
  //        type uint32 {
  //          range "2 .. 10";
  //        }
  //      }
  //    }
  //    leaf learn-pim-router {
  //      description "Learn PIM router interfaces from PIM hellos";
  //      type empty;
  //    }
  //    leaf immediate-leave {
  //      description "Enable immediate group leave on interfaces";
  //      type empty;
  //    }
  //    leaf evpn-ssm-reports-only {
  //      description "Accept and process only <s,g> reports of SSM groups";
  //      type empty;
  //    }
  //    leaf version {
  //      description "Set IGMP snooping version number";
  //      type union {
  //        type string {
  //          pattern "<.*>|$.*";
  //        }
  //        type uint8 {
  //          range "2 .. 3";
  //        }
  //      }
  //    }
  //    container proxy {
  //      presence "enable proxy";
  //      description "Enable proxy mode";
  //      // uses apply-advanced;
  //      leaf source-address {
  //        description "Source IP address to use for proxy";
  //        type jt:ipv4addr;
  //      }
  //      leaf irb {
  //        description "Proxy IGMP reports to IRB";
  //        type empty;
  //      }
  //    }
  //    list interface {
  //      key name;
  //      ordered-by user;
  //      description "Interface options for IGMP";
  //      leaf name {
  //        description "Interface name";
  //        type union {
  //          type jt:interface-name;
  //          type string {
  //            pattern "<.*>|$.*";
  //          }
  //        }
  //      }
  //      // uses apply-advanced;
  //      leaf multicast-router-interface {
  //        description "Enabling multicast-router-interface on the interface";
  //        type empty;
  //      }
  //      leaf immediate-leave {
  //        description "Enable immediate group leave on interfaces";
  //        type empty;
  //      }
  //      leaf host-only-interface {
  //        description "Enable interfaces to be treated as host-side interfaces";
  //        type empty;
  //      }
  //      leaf group-limit {
  //        description "Maximum number of (source,group) per interface";
  //        type union {
  //          type string {
  //            pattern "<.*>|$.*";
  //          }
  //          type uint16 {
  //            range "1 .. 65535";
  //          }
  //        }
  //      }
  //      container static {
  //        description "Static group or source membership";
  //        // uses apply-advanced;
  //        list group {
  //          key name;
  //          ordered-by user;
  //          description "IP multicast group address";
  //          leaf name {
  //            description "IP multicast group address";
  //            type jt:ipv4addr;
  //          }
  //          // uses apply-advanced;
  //          list source {
  //            key name;
  //            ordered-by user;
  //            description "IP multicast source address";
  //            leaf name {
  //              description "Source address of IP multicast data";
  //              type jt:ipv4addr;
  //            }
  //            // uses apply-advanced;
  //          }
  //        }
  //      }
  //    }
  //    list pseudowire-remote-address {
  //      key name;
  //      ordered-by user;
  //      description "Pseudowire interface options for IGMP";
  //      leaf name {
  //        description "Pseudowire endpoint address";
  //        type jt:ipv4addr;
  //      }
  //      // uses apply-advanced;
  //      leaf multicast-router-interface {
  //        description "Enabling multicast-router-interface on the interface";
  //        type empty;
  //      }
  //      leaf immediate-leave {
  //        description "Enable immediate group leave on interfaces";
  //        type empty;
  //      }
  //    }
  //    list qualified-vlan {
  //      key name;
  //      ordered-by user;
  //      description "VLAN options for qualified-learning";
  //      leaf name {
  //        description "VLAN ID of the learning-domain";
  //        type union {
  //          type string {
  //            pattern "<.*>|$.*";
  //          }
  //          type uint32 {
  //            range "0 .. 1023";
  //          }
  //        }
  //      }
  //      // uses apply-advanced;
  //      leaf query-interval {
  //        description "When to send host query messages";
  //        units "seconds";
  //        type union {
  //          type string {
  //            pattern "<.*>|$.*";
  //          }
  //          type uint32 {
  //            range "1 .. 1024";
  //          }
  //        }
  //      }
  //      leaf query-response-interval {
  //        description "How long to wait for a host query response";
  //        units "seconds";
  //        type string {
  //        }
  //      }
  //      leaf query-last-member-interval {
  //        description "When to send group query messages";
  //        units "seconds";
  //        type string {
  //        }
  //      }
  //      leaf robust-count {
  //        description "Expected packet loss on a subnet";
  //        type union {
  //          type string {
  //            pattern "<.*>|$.*";
  //          }
  //          type uint32 {
  //            range "2 .. 10";
  //          }
  //        }
  //      }
  //      leaf immediate-leave {
  //        description "Enable immediate group leave on interfaces";
  //        type empty;
  //      }
  //      container proxy {
  //        presence "enable proxy";
  //        description "Enable proxy mode";
  //        // uses apply-advanced;
  //        leaf source-address {
  //          description "Source IP address to use for proxy";
  //          type jt:ipv4addr;
  //        }
  //      }
  //      leaf evpn-ssm-reports-only {
  //        description "Accept and process only <s,g> reports of SSM groups";
  //        type empty;
  //      }
  //      list interface {
  //        key name;
  //        ordered-by user;
  //        description "Interface options for IGMP";
  //        leaf name {
  //          description "Interface name";
  //          type union {
  //            type jt:interface-name;
  //            type string {
  //              pattern "<.*>|$.*";
  //            }
  //          }
  //        }
  //        // uses apply-advanced;
  //        leaf multicast-router-interface {
  //          description "Enabling multicast-router-interface on the interface";
  //          type empty;
  //        }
  //        leaf immediate-leave {
  //          description "Enable immediate group leave on interfaces";
  //          type empty;
  //        }
  //        leaf host-only-interface {
  //          description "Enable interfaces to be treated as host-side interfaces";
  //          type empty;
  //        }
  //        leaf group-limit {
  //          description "Maximum number of (source,group) per interface";
  //          type union {
  //            type string {
  //              pattern "<.*>|$.*";
  //            }
  //            type uint16 {
  //              range "1 .. 65535";
  //            }
  //          }
  //        }
  //        container static {
  //          description "Static group or source membership";
  //          // uses apply-advanced;
  //          list group {
  //            key name;
  //            ordered-by user;
  //            description "IP multicast group address";
  //            leaf name {
  //              description "IP multicast group address";
  //              type jt:ipv4addr;
  //            }
  //            // uses apply-advanced;
  //            list source {
  //              key name;
  //              ordered-by user;
  //              description "IP multicast source address";
  //              leaf name {
  //                description "Source address of IP multicast data";
  //                type jt:ipv4addr;
  //              }
  //              // uses apply-advanced;
  //            }
  //          }
  //        }
  //      }
  //      list pseudowire-remote-address {
  //        key name;
  //        ordered-by user;
  //        description "Pseudowire interface options for IGMP";
  //        leaf name {
  //          description "Pseudowire endpoint address";
  //          type jt:ipv4addr;
  //        }
  //        // uses apply-advanced;
  //        leaf multicast-router-interface {
  //          description "Enabling multicast-router-interface on the interface";
  //          type empty;
  //        }
  //        leaf immediate-leave {
  //          description "Enable immediate group leave on interfaces";
  //          type empty;
  //        }
  //      }
  //    }
  //    list vlan {
  //      key name;
  //      ordered-by user;
  //      description "Vlan options";
  //      leaf name {
  //        description "VLAN name";
  //        type string;
  //      }
  //      // uses apply-advanced;
  //      leaf query-interval {
  //        description "When to send host query messages";
  //        units "seconds";
  //        type union {
  //          type string {
  //            pattern "<.*>|$.*";
  //          }
  //          type uint32 {
  //            range "1 .. 1024";
  //          }
  //        }
  //      }
  //      leaf query-response-interval {
  //        description "How long to wait for a host query response";
  //        units "seconds";
  //        type string {
  //        }
  //      }
  //      leaf query-last-member-interval {
  //        description "When to send group query messages";
  //        units "seconds";
  //        type string {
  //        }
  //      }
  //      leaf robust-count {
  //        description "Expected packet loss on a subnet";
  //        type union {
  //          type string {
  //            pattern "<.*>|$.*";
  //          }
  //          type uint32 {
  //            range "2 .. 10";
  //          }
  //        }
  //      }
  //      leaf immediate-leave {
  //        description "Enable immediate group leave on interfaces";
  //        type empty;
  //      }
  //      container proxy {
  //        presence "enable proxy";
  //        description "Enable proxy mode";
  //        // uses apply-advanced;
  //        leaf source-address {
  //          description "Source IP address to use for proxy";
  //          type jt:ipv4addr;
  //        }
  //      }
  //      container l2-querier {
  //        description "Enable L2 querier mode";
  //        // uses apply-advanced;
  //        leaf source-address {
  //          description "Source IP address to use for L2 querier";
  //          type jt:ipv4addr;
  //        }
  //      }
  //      leaf evpn-ssm-reports-only {
  //        description "Accept and process only <s,g> reports of SSM groups";
  //        type empty;
  //      }
  //      list interface {
  //        key name;
  //        ordered-by user;
  //        description "Interface options for IGMP";
  //        leaf name {
  //          description "Interface name";
  //          type union {
  //            type jt:interface-name;
  //            type string {
  //              pattern "<.*>|$.*";
  //            }
  //          }
  //        }
  //        // uses apply-advanced;
  //        leaf multicast-router-interface {
  //          description "Enabling multicast-router-interface on the interface";
  //          type empty;
  //        }
  //        leaf immediate-leave {
  //          description "Enable immediate group leave on interfaces";
  //          type empty;
  //        }
  //        leaf host-only-interface {
  //          description "Enable interfaces to be treated as host-side interfaces";
  //          type empty;
  //        }
  //        leaf group-limit {
  //          description "Maximum number of (source,group) per interface";
  //          type union {
  //            type string {
  //              pattern "<.*>|$.*";
  //            }
  //            type uint16 {
  //              range "1 .. 65535";
  //            }
  //          }
  //        }
  //        container static {
  //          description "Static group or source membership";
  //          // uses apply-advanced;
  //          list group {
  //            key name;
  //            ordered-by user;
  //            description "IP multicast group address";
  //            leaf name {
  //              description "IP multicast group address";
  //              type jt:ipv4addr;
  //            }
  //            // uses apply-advanced;
  //            list source {
  //              key name;
  //              ordered-by user;
  //              description "IP multicast source address";
  //              leaf name {
  //                description "Source address of IP multicast data";
  //                type jt:ipv4addr;
  //              }
  //              // uses apply-advanced;
  //            }
  //          }
  //        }
  //      }
  //      list pseudowire-remote-address {
  //        key name;
  //        ordered-by user;
  //        description "Pseudowire interface options for IGMP";
  //        leaf name {
  //          description "Pseudowire endpoint address";
  //          type jt:ipv4addr;
  //        }
  //        // uses apply-advanced;
  //        leaf multicast-router-interface {
  //          description "Enabling multicast-router-interface on the interface";
  //          type empty;
  //        }
  //        leaf immediate-leave {
  //          description "Enable immediate group leave on interfaces";
  //          type empty;
  //        }
  //      }
  //      list qualified-vlan {
  //        key name;
  //        ordered-by user;
  //        description "VLAN options for qualified-learning";
  //        leaf name {
  //          description "VLAN ID of the learning-domain";
  //          type union {
  //            type string {
  //              pattern "<.*>|$.*";
  //            }
  //            type uint32 {
  //              range "0 .. 1023";
  //            }
  //          }
  //        }
  //        // uses apply-advanced;
  //        leaf query-interval {
  //          description "When to send host query messages";
  //          units "seconds";
  //          type union {
  //            type string {
  //              pattern "<.*>|$.*";
  //            }
  //            type uint32 {
  //              range "1 .. 1024";
  //            }
  //          }
  //        }
  //        leaf query-response-interval {
  //          description "How long to wait for a host query response";
  //          units "seconds";
  //          type string {
  //          }
  //        }
  //        leaf query-last-member-interval {
  //          description "When to send group query messages";
  //          units "seconds";
  //          type string {
  //          }
  //        }
  //        leaf robust-count {
  //          description "Expected packet loss on a subnet";
  //          type union {
  //            type string {
  //              pattern "<.*>|$.*";
  //            }
  //            type uint32 {
  //              range "2 .. 10";
  //            }
  //          }
  //        }
  //        leaf immediate-leave {
  //          description "Enable immediate group leave on interfaces";
  //          type empty;
  //        }
  //        container proxy {
  //          presence "enable proxy";
  //          description "Enable proxy mode";
  //          // uses apply-advanced;
  //          leaf source-address {
  //            description "Source IP address to use for proxy";
  //            type jt:ipv4addr;
  //          }
  //        }
  //        leaf evpn-ssm-reports-only {
  //          description "Accept and process only <s,g> reports of SSM groups";
  //          type empty;
  //        }
  //        list interface {
  //          key name;
  //          ordered-by user;
  //          description "Interface options for IGMP";
  //          leaf name {
  //            description "Interface name";
  //            type union {
  //              type jt:interface-name;
  //              type string {
  //                pattern "<.*>|$.*";
  //              }
  //            }
  //          }
  //          // uses apply-advanced;
  //          leaf multicast-router-interface {
  //            description "Enabling multicast-router-interface on the interface";
  //            type empty;
  //          }
  //          leaf immediate-leave {
  //            description "Enable immediate group leave on interfaces";
  //            type empty;
  //          }
  //          leaf host-only-interface {
  //            description "Enable interfaces to be treated as host-side interfaces";
  //            type empty;
  //          }
  //          leaf group-limit {
  //            description "Maximum number of (source,group) per interface";
  //            type union {
  //              type string {
  //                pattern "<.*>|$.*";
  //              }
  //              type uint16 {
  //                range "1 .. 65535";
  //              }
  //            }
  //          }
  //          container static {
  //            description "Static group or source membership";
  //            // uses apply-advanced;
  //            list group {
  //              key name;
  //              ordered-by user;
  //              description "IP multicast group address";
  //              leaf name {
  //                description "IP multicast group address";
  //                type jt:ipv4addr;
  //              }
  //              // uses apply-advanced;
  //              list source {
  //                key name;
  //                ordered-by user;
  //                description "IP multicast source address";
  //                leaf name {
  //                  description "Source address of IP multicast data";
  //                  type jt:ipv4addr;
  //                }
  //                // uses apply-advanced;
  //              }
  //            }
  //          }
  //        }
  //        list pseudowire-remote-address {
  //          key name;
  //          ordered-by user;
  //          description "Pseudowire interface options for IGMP";
  //          leaf name {
  //            description "Pseudowire endpoint address";
  //            type jt:ipv4addr;
  //          }
  //          // uses apply-advanced;
  //          leaf multicast-router-interface {
  //            description "Enabling multicast-router-interface on the interface";
  //            type empty;
  //          }
  //          leaf immediate-leave {
  //            description "Enable immediate group leave on interfaces";
  //            type empty;
  //          }
  //        }
  //      }
  //      leaf version {
  //        description "Set IGMP snooping version number";
  //        type union {
  //          type string {
  //            pattern "<.*>|$.*";
  //          }
  //          type uint8 {
  //            range "2 .. 3";
  //          }
  //        }
  //      }
  //    }
  //  }
  //  grouping juniper-ri-protocols-mld-snooping {
  //    description "MLD snooping options";
  //    // uses apply-advanced;
  //    container traceoptions {
  //      description "Trace options for MLD Snooping";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "packets" {
  //              description "Trace all MLD packets";
  //            }
  //            enum "query" {
  //              description "Trace MLD membership query messages";
  //            }
  //            enum "report" {
  //              description "Trace membership report messages";
  //            }
  //            enum "leave" {
  //              description "Trace leave group messages (MLDv2 only)";
  //            }
  //            enum "group" {
  //              description "Trace group operations";
  //            }
  //            enum "client-notification" {
  //              description "Trace notifications";
  //            }
  //            enum "host-notification" {
  //              description "Trace host notifications";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //        leaf send {
  //          description "Trace transmitted packets";
  //          type empty;
  //        }
  //        leaf receive {
  //          description "Trace received packets";
  //          type empty;
  //        }
  //        leaf detail {
  //          description "Trace detailed information";
  //          type empty;
  //        }
  //        leaf disable {
  //          description "Disable this trace flag";
  //          type empty;
  //        }
  //      }
  //    }
  //    leaf query-interval {
  //      description "When to send host query messages";
  //      default "125";
  //      units "seconds";
  //      type union {
  //        type string {
  //          pattern "<.*>|$.*";
  //        }
  //        type uint32 {
  //          range "1 .. 1024";
  //        }
  //      }
  //    }
  //    container l2-querier {
  //      description "Enable L2 querier mode";
  //      // uses apply-advanced;
  //      leaf source-address {
  //        description "Source IP address to use for L2 querier";
  //        type jt:ipv6addr;
  //      }
  //    }
  //    leaf query-response-interval {
  //      description "How long to wait for a host query response";
  //      default "10";
  //      units "seconds";
  //      type string {
  //      }
  //    }
  //    leaf query-last-member-interval {
  //      description "When to send group query messages";
  //      default "1";
  //      units "seconds";
  //      type string {
  //      }
  //    }
  //    leaf robust-count {
  //      description "Expected packet loss on a subnet";
  //      default "2";
  //      type union {
  //        type string {
  //          pattern "<.*>|$.*";
  //        }
  //        type uint32 {
  //          range "2 .. 10";
  //        }
  //      }
  //    }
  //    leaf immediate-leave {
  //      description "Enable immediate group leave on interfaces";
  //      type empty;
  //    }
  //    leaf evpn-ssm-reports-only {
  //      description "Accept and process only <s,g> reports of SSM groups";
  //      type empty;
  //    }
  //    leaf version {
  //      description "Set MLD snooping version number";
  //      type union {
  //        type string {
  //          pattern "<.*>|$.*";
  //        }
  //        type uint8 {
  //          range "1 .. 2";
  //        }
  //      }
  //    }
  //    container proxy {
  //      description "Enable proxy mode";
  //      // uses apply-advanced;
  //      leaf source-address {
  //        description "Source IP address to use for proxy";
  //        type jt:ipv6addr;
  //      }
  //      leaf irb {
  //        description "Proxy IGMP reports to IRB";
  //        type empty;
  //      }
  //    }
  //    list interface {
  //      key name;
  //      ordered-by user;
  //      description "Interface options for MLD";
  //      leaf name {
  //        description "Interface name";
  //        type union {
  //          type jt:interface-name;
  //          type string {
  //            pattern "<.*>|$.*";
  //          }
  //        }
  //      }
  //      // uses apply-advanced;
  //      leaf multicast-router-interface {
  //        description "Enabling multicast-router-interface on the interface";
  //        type empty;
  //      }
  //      leaf immediate-leave {
  //        description "Enable immediate group leave on interfaces";
  //        type empty;
  //      }
  //      leaf host-only-interface {
  //        description "Enable interfaces to be treated as host-side interfaces";
  //        type empty;
  //      }
  //      leaf group-limit {
  //        description "Maximum number of (source,group) per interface";
  //        type union {
  //          type string {
  //            pattern "<.*>|$.*";
  //          }
  //          type uint16 {
  //            range "1 .. 65535";
  //          }
  //        }
  //      }
  //      container static {
  //        description "Static group or source membership";
  //        // uses apply-advanced;
  //        list group {
  //          key name;
  //          ordered-by user;
  //          description "IP multicast group address";
  //          leaf name {
  //            description "IP multicast group address";
  //            type jt:ipv6addr;
  //          }
  //          // uses apply-advanced;
  //          list source {
  //            key name;
  //            ordered-by user;
  //            description "IP multicast source address";
  //            leaf name {
  //              description "Source address of IP multicast data";
  //              type jt:ipv6addr;
  //            }
  //            // uses apply-advanced;
  //          }
  //        }
  //      }
  //    }
  //    list pseudowire-remote-address {
  //      key name;
  //      ordered-by user;
  //      description "Pseudowire interface options for MLD";
  //      leaf name {
  //        description "Pseudowire endpoint address";
  //        type jt:ipv4addr;
  //      }
  //      // uses apply-advanced;
  //      leaf multicast-router-interface {
  //        description "Enabling multicast-router-interface on the interface";
  //        type empty;
  //      }
  //      leaf immediate-leave {
  //        description "Enable immediate group leave on interfaces";
  //        type empty;
  //      }
  //    }
  //    list qualified-vlan {
  //      key name;
  //      ordered-by user;
  //      description "VLAN options for qualified-learning";
  //      leaf name {
  //        description "VLAN ID of the learning-domain";
  //        type union {
  //          type string {
  //            pattern "<.*>|$.*";
  //          }
  //          type uint32 {
  //            range "0 .. 1023";
  //          }
  //        }
  //      }
  //      // uses apply-advanced;
  //      leaf query-interval {
  //        description "When to send host query messages";
  //        units "seconds";
  //        type union {
  //          type string {
  //            pattern "<.*>|$.*";
  //          }
  //          type uint32 {
  //            range "1 .. 1024";
  //          }
  //        }
  //      }
  //      leaf query-response-interval {
  //        description "How long to wait for a host query response";
  //        units "seconds";
  //        type string {
  //        }
  //      }
  //      leaf query-last-member-interval {
  //        description "When to send group query messages";
  //        units "seconds";
  //        type string {
  //        }
  //      }
  //      leaf robust-count {
  //        description "Expected packet loss on a subnet";
  //        type union {
  //          type string {
  //            pattern "<.*>|$.*";
  //          }
  //          type uint32 {
  //            range "2 .. 10";
  //          }
  //        }
  //      }
  //      leaf immediate-leave {
  //        description "Enable immediate group leave on interfaces";
  //        type empty;
  //      }
  //      container proxy {
  //        description "Enable proxy mode";
  //        // uses apply-advanced;
  //        leaf source-address {
  //          description "Source IP address to use for proxy";
  //          type jt:ipv6addr;
  //        }
  //      }
  //      leaf evpn-ssm-reports-only {
  //        description "Accept and process only <s,g> reports of SSM groups";
  //        type empty;
  //      }
  //      list interface {
  //        key name;
  //        ordered-by user;
  //        description "Interface options for MLD";
  //        leaf name {
  //          description "Interface name";
  //          type union {
  //            type jt:interface-name;
  //            type string {
  //              pattern "<.*>|$.*";
  //            }
  //          }
  //        }
  //        // uses apply-advanced;
  //        leaf multicast-router-interface {
  //          description "Enabling multicast-router-interface on the interface";
  //          type empty;
  //        }
  //        leaf immediate-leave {
  //          description "Enable immediate group leave on interfaces";
  //          type empty;
  //        }
  //        leaf host-only-interface {
  //          description "Enable interfaces to be treated as host-side interfaces";
  //          type empty;
  //        }
  //        leaf group-limit {
  //          description "Maximum number of (source,group) per interface";
  //          type union {
  //            type string {
  //              pattern "<.*>|$.*";
  //            }
  //            type uint16 {
  //              range "1 .. 65535";
  //            }
  //          }
  //        }
  //        container static {
  //          description "Static group or source membership";
  //          // uses apply-advanced;
  //          list group {
  //            key name;
  //            ordered-by user;
  //            description "IP multicast group address";
  //            leaf name {
  //              description "IP multicast group address";
  //              type jt:ipv6addr;
  //            }
  //            // uses apply-advanced;
  //            list source {
  //              key name;
  //              ordered-by user;
  //              description "IP multicast source address";
  //              leaf name {
  //                description "Source address of IP multicast data";
  //                type jt:ipv6addr;
  //              }
  //              // uses apply-advanced;
  //            }
  //          }
  //        }
  //      }
  //      list pseudowire-remote-address {
  //        key name;
  //        ordered-by user;
  //        description "Pseudowire interface options for MLD";
  //        leaf name {
  //          description "Pseudowire endpoint address";
  //          type jt:ipv4addr;
  //        }
  //        // uses apply-advanced;
  //        leaf multicast-router-interface {
  //          description "Enabling multicast-router-interface on the interface";
  //          type empty;
  //        }
  //        leaf immediate-leave {
  //          description "Enable immediate group leave on interfaces";
  //          type empty;
  //        }
  //      }
  //    }
  //    list vlan {
  //      key name;
  //      ordered-by user;
  //      description "Vlan options";
  //      leaf name {
  //        description "Vlan of the bridge-domain";
  //        type string;
  //      }
  //      // uses apply-advanced;
  //      leaf query-interval {
  //        description "When to send host query messages";
  //        units "seconds";
  //        type union {
  //          type string {
  //            pattern "<.*>|$.*";
  //          }
  //          type uint32 {
  //            range "1 .. 1024";
  //          }
  //        }
  //      }
  //      leaf query-response-interval {
  //        description "How long to wait for a host query response";
  //        units "seconds";
  //        type string {
  //        }
  //      }
  //      leaf query-last-member-interval {
  //        description "When to send group query messages";
  //        units "seconds";
  //        type string {
  //        }
  //      }
  //      leaf robust-count {
  //        description "Expected packet loss on a subnet";
  //        type union {
  //          type string {
  //            pattern "<.*>|$.*";
  //          }
  //          type uint32 {
  //            range "2 .. 10";
  //          }
  //        }
  //      }
  //      leaf immediate-leave {
  //        description "Enable immediate group leave on interfaces";
  //        type empty;
  //      }
  //      container proxy {
  //        description "Enable proxy mode";
  //        // uses apply-advanced;
  //        leaf source-address {
  //          description "Source IP address to use for proxy";
  //          type jt:ipv6addr;
  //        }
  //      }
  //      container l2-querier {
  //        description "Enable L2 querier mode";
  //        // uses apply-advanced;
  //        leaf source-address {
  //          description "Source IP address to use for L2 querier";
  //          type jt:ipv6addr;
  //        }
  //      }
  //      leaf evpn-ssm-reports-only {
  //        description "Accept and process only <s,g> reports of SSM groups";
  //        type empty;
  //      }
  //      list interface {
  //        key name;
  //        ordered-by user;
  //        description "Interface options for MLD";
  //        leaf name {
  //          description "Interface name";
  //          type union {
  //            type jt:interface-name;
  //            type string {
  //              pattern "<.*>|$.*";
  //            }
  //          }
  //        }
  //        // uses apply-advanced;
  //        leaf multicast-router-interface {
  //          description "Enabling multicast-router-interface on the interface";
  //          type empty;
  //        }
  //        leaf immediate-leave {
  //          description "Enable immediate group leave on interfaces";
  //          type empty;
  //        }
  //        leaf host-only-interface {
  //          description "Enable interfaces to be treated as host-side interfaces";
  //          type empty;
  //        }
  //        leaf group-limit {
  //          description "Maximum number of (source,group) per interface";
  //          type union {
  //            type string {
  //              pattern "<.*>|$.*";
  //            }
  //            type uint16 {
  //              range "1 .. 65535";
  //            }
  //          }
  //        }
  //        container static {
  //          description "Static group or source membership";
  //          // uses apply-advanced;
  //          list group {
  //            key name;
  //            ordered-by user;
  //            description "IP multicast group address";
  //            leaf name {
  //              description "IP multicast group address";
  //              type jt:ipv6addr;
  //            }
  //            // uses apply-advanced;
  //            list source {
  //              key name;
  //              ordered-by user;
  //              description "IP multicast source address";
  //              leaf name {
  //                description "Source address of IP multicast data";
  //                type jt:ipv6addr;
  //              }
  //              // uses apply-advanced;
  //            }
  //          }
  //        }
  //      }
  //      list pseudowire-remote-address {
  //        key name;
  //        ordered-by user;
  //        description "Pseudowire interface options for MLD";
  //        leaf name {
  //          description "Pseudowire endpoint address";
  //          type jt:ipv4addr;
  //        }
  //        // uses apply-advanced;
  //        leaf multicast-router-interface {
  //          description "Enabling multicast-router-interface on the interface";
  //          type empty;
  //        }
  //        leaf immediate-leave {
  //          description "Enable immediate group leave on interfaces";
  //          type empty;
  //        }
  //      }
  //      list qualified-vlan {
  //        key name;
  //        ordered-by user;
  //        description "VLAN options for qualified-learning";
  //        leaf name {
  //          description "VLAN ID of the learning-domain";
  //          type union {
  //            type string {
  //              pattern "<.*>|$.*";
  //            }
  //            type uint32 {
  //              range "0 .. 1023";
  //            }
  //          }
  //        }
  //        // uses apply-advanced;
  //        leaf query-interval {
  //          description "When to send host query messages";
  //          units "seconds";
  //          type union {
  //            type string {
  //              pattern "<.*>|$.*";
  //            }
  //            type uint32 {
  //              range "1 .. 1024";
  //            }
  //          }
  //        }
  //        leaf query-response-interval {
  //          description "How long to wait for a host query response";
  //          units "seconds";
  //          type string {
  //          }
  //        }
  //        leaf query-last-member-interval {
  //          description "When to send group query messages";
  //          units "seconds";
  //          type string {
  //          }
  //        }
  //        leaf robust-count {
  //          description "Expected packet loss on a subnet";
  //          type union {
  //            type string {
  //              pattern "<.*>|$.*";
  //            }
  //            type uint32 {
  //              range "2 .. 10";
  //            }
  //          }
  //        }
  //        leaf immediate-leave {
  //          description "Enable immediate group leave on interfaces";
  //          type empty;
  //        }
  //        container proxy {
  //          description "Enable proxy mode";
  //          // uses apply-advanced;
  //          leaf source-address {
  //            description "Source IP address to use for proxy";
  //            type jt:ipv6addr;
  //          }
  //        }
  //        leaf evpn-ssm-reports-only {
  //          description "Accept and process only <s,g> reports of SSM groups";
  //          type empty;
  //        }
  //        list interface {
  //          key name;
  //          ordered-by user;
  //          description "Interface options for MLD";
  //          leaf name {
  //            description "Interface name";
  //            type union {
  //              type jt:interface-name;
  //              type string {
  //                pattern "<.*>|$.*";
  //              }
  //            }
  //          }
  //          // uses apply-advanced;
  //          leaf multicast-router-interface {
  //            description "Enabling multicast-router-interface on the interface";
  //            type empty;
  //          }
  //          leaf immediate-leave {
  //            description "Enable immediate group leave on interfaces";
  //            type empty;
  //          }
  //          leaf host-only-interface {
  //            description "Enable interfaces to be treated as host-side interfaces";
  //            type empty;
  //          }
  //          leaf group-limit {
  //            description "Maximum number of (source,group) per interface";
  //            type union {
  //              type string {
  //                pattern "<.*>|$.*";
  //              }
  //              type uint16 {
  //                range "1 .. 65535";
  //              }
  //            }
  //          }
  //          container static {
  //            description "Static group or source membership";
  //            // uses apply-advanced;
  //            list group {
  //              key name;
  //              ordered-by user;
  //              description "IP multicast group address";
  //              leaf name {
  //                description "IP multicast group address";
  //                type jt:ipv6addr;
  //              }
  //              // uses apply-advanced;
  //              list source {
  //                key name;
  //                ordered-by user;
  //                description "IP multicast source address";
  //                leaf name {
  //                  description "Source address of IP multicast data";
  //                  type jt:ipv6addr;
  //                }
  //                // uses apply-advanced;
  //              }
  //            }
  //          }
  //        }
  //        list pseudowire-remote-address {
  //          key name;
  //          ordered-by user;
  //          description "Pseudowire interface options for MLD";
  //          leaf name {
  //            description "Pseudowire endpoint address";
  //            type jt:ipv4addr;
  //          }
  //          // uses apply-advanced;
  //          leaf multicast-router-interface {
  //            description "Enabling multicast-router-interface on the interface";
  //            type empty;
  //          }
  //          leaf immediate-leave {
  //            description "Enable immediate group leave on interfaces";
  //            type empty;
  //          }
  //        }
  //      }
  //      leaf version {
  //        description "Set MLD snooping version number";
  //        type union {
  //          type string {
  //            pattern "<.*>|$.*";
  //          }
  //          type uint8 {
  //            range "1 .. 2";
  //          }
  //        }
  //      }
  //    }
  //  }
  //  grouping juniper-routing-instance-pbb-options {
  //    description "PBB options for the routing instance";
  //    // uses apply-advanced;
  //    leaf peer-instance {
  //      description "Set the peer-pbbn routing instance";
  //      type string;
  //    }
  //    list vlan-id {
  //      key name;
  //      ordered-by user;
  //      description "Set B-VLAN to ISID mapping";
  //      leaf name {
  //        description "Configure B-Vlan";
  //        type union {
  //          type string {
  //            pattern "<.*>|$.*";
  //          }
  //          type uint32 {
  //            range "1 .. 4094";
  //          }
  //        }
  //      }
  //      leaf-list isid-list {
  //        ordered-by user;
  //        description "Configure ISID(Valid Range:256..16777214) for the B-VLAN";
  //        type string;
  //      }
  //    }
  //    leaf default-bvlan {
  //      description "Default B-VLAN for all un-mapped ISIDs";
  //      type union {
  //        type string {
  //          pattern "<.*>|$.*";
  //        }
  //        type uint32 {
  //          range "1 .. 4094";
  //        }
  //      }
  //    }
  //  }
  //  grouping juniper-routing-instance-service-groups {
  //    description "Service-groups configuration";
  //    leaf name {
  //      description "Service-group name";
  //      type string;
  //    }
  //    // uses apply-advanced;
  //    leaf service-type {
  //      description "Service type as ethernet LAN or point-to-point";
  //      type enumeration {
  //        enum "eline" {
  //          description "Ethernet point-to-point";
  //        }
  //        enum "elan" {
  //          description "Ethernet LAN service";
  //        }
  //      }
  //    }
  //    container pbb-service-options {
  //      presence "enable pbb-service-options";
  //      description "Provider backbone instance service options";
  //      // uses apply-advanced;
  //      list isid {
  //        key name;
  //        ordered-by user;
  //        description "ISID to S-VLAN configuration";
  //        leaf name {
  //          description "Configure ISID";
  //          type union {
  //            type string {
  //              pattern "<.*>|$.*";
  //            }
  //            type uint32 {
  //              range "256 .. 16777214";
  //            }
  //          }
  //        }
  //        choice service-data {
  //          case case_1 {
  //            leaf-list vlan-id-list {
  //              description "List of S-VLANs";
  //              type jt:vlan-range;
  //            }
  //          }
  //          case case_2 {
  //            leaf interface {
  //              description "Point to point interface name";
  //              type union {
  //                type jt:interface-name;
  //                type string {
  //                  pattern "<.*>|$.*";
  //                }
  //              }
  //            }
  //          }
  //        }
  //      }
  //      leaf default-isid {
  //        description "Default ISID for all un-mapped S-VLANs";
  //        type union {
  //          type string {
  //            pattern "<.*>|$.*";
  //          }
  //          type uint32 {
  //            range "256 .. 16777214";
  //          }
  //        }
  //      }
  //      leaf mac-address {
  //        description "Unicast or multicast mac address";
  //        type jt:mac-addr;
  //      }
  //      leaf source-bmac {
  //        description "Unicast Source B Mac address";
  //        type jt:mac-addr;
  //      }
  //    }
  //  }
  //  grouping juniper-routing-instance-switch-options {
  //    description "Bridge options for the routing instance";
  //    // uses apply-advanced;
  //    container mac-table-size {
  //      description "Size of MAC address forwarding table";
  //      // uses apply-advanced;
  //      leaf limit {
  //        description "Maximum number of MAC addresses";
  //        type union {
  //          type string {
  //            pattern "<.*>|$.*";
  //          }
  //          type uint32;
  //        }
  //      }
  //      leaf packet-action {
  //        description "Action when MAC limit is reached";
  //        type enumeration {
  //          enum "none" {
  //            description "Forward the packet";
  //          }
  //          enum "drop" {
  //            description "Drop packets and do not learn. Default is forward";
  //          }
  //        }
  //      }
  //    }
  //    container mac-ip-table-size {
  //      description "Size of MAC+IP bindings table";
  //      // uses apply-advanced;
  //      leaf limit {
  //        description "Maximum number of MAC+IP bindings";
  //        type union {
  //          type string {
  //            pattern "<.*>|$.*";
  //          }
  //          type uint32;
  //        }
  //      }
  //    }
  //    container interface-mac-limit {
  //      description "Maximum MAC address learned per interface";
  //      // uses apply-advanced;
  //      leaf limit {
  //        description "Maximum number of MAC addresses per interface";
  //        type union {
  //          type string {
  //            pattern "<.*>|$.*";
  //          }
  //          type uint32;
  //        }
  //      }
  //      leaf packet-action {
  //        description "Action when MAC limit is reached";
  //        type enumeration {
  //          enum "none" {
  //            description "Forward the packet";
  //          }
  //          enum "drop" {
  //            description "Drop packets and do not learn. Default is forward";
  //          }
  //          enum "log" {
  //            description "Do not drop the packet but generate an alarm, an SNMP trap or a system log entry";
  //          }
  //          enum "shutdown" {
  //            description "Disable the interface and generate an alarm, an SNMP trap or a system log entry";
  //          }
  //          enum "drop-and-log" {
  //            description "Drop the packet and generate an alarm, an SNMP trap or a system log entry";
  //          }
  //        }
  //      }
  //    }
  //    container interface-mac-ip-limit {
  //      description "Maximum MAC+IP bindings learned per interface";
  //      // uses apply-advanced;
  //      leaf limit {
  //        description "Maximum number of MAC+IP bindings per interface";
  //        type union {
  //          type string {
  //            pattern "<.*>|$.*";
  //          }
  //          type uint32;
  //        }
  //      }
  //    }
  //    container mac-move-limit {
  //      presence "enable mac-move-limit";
  //      description "Number of MAC movements allowed on this VLAN";
  //      // uses apply-advanced;
  //      choice limit-choice {
  //        case case_1 {
  //          leaf none {
  //            description "Disable mac-move-limit for this VLAN";
  //            type empty;
  //          }
  //        }
  //        case case_2 {
  //          leaf limit {
  //            description "Number of MAC movements allowed on this VLAN";
  //            type union {
  //              type string {
  //                pattern "<.*>|$.*";
  //              }
  //              type uint32 {
  //                range "1 .. 4294967295";
  //              }
  //            }
  //          }
  //        }
  //      }
  //      leaf packet-action {
  //        description "Action to be taken in case the MAC movement limit is exceeded";
  //        default "drop";
  //        type enumeration {
  //          enum "none" {
  //            description "Take no action";
  //          }
  //          enum "drop" {
  //            description "Drop the packet and do not generate an alarm";
  //          }
  //          enum "log" {
  //            description "Do not drop the packet but generate an alarm, an SNMP trap, or a system log entry.";
  //          }
  //          enum "shutdown" {
  //            description "Disable the interface and generate an alarm, an SNMP trap, or a system log entry.";
  //          }
  //          enum "drop-and-log" {
  //            description "Drop the packet and generate an alarm, an SNMP trap, or a system log entry.";
  //          }
  //          enum "vlan-member-shutdown" {
  //            description "Disable the interface of this VLAN";
  //          }
  //        }
  //      }
  //      list interface {
  //        key name;
  //        description "Interface that connect this site to the VPN";
  //        leaf name {
  //          description "Interface name";
  //          type union {
  //            type jt:interface-name;
  //            type string {
  //              pattern "<.*>|$.*";
  //            }
  //          }
  //        }
  //        // uses apply-advanced;
  //        leaf action-priority {
  //          description "Blocking priority of this interface on mac move detection";
  //          type union {
  //            type string {
  //              pattern "<.*>|$.*";
  //            }
  //            type uint32 {
  //              range "0 .. 7";
  //            }
  //          }
  //        }
  //      }
  //    }
  //    container mac-notification {
  //      presence "enable mac-notification";
  //      description "MAC notification options";
  //      // uses apply-advanced;
  //      leaf notification-interval {
  //        description "Interval for sending MAC notifications";
  //        default "30";
  //        units "seconds";
  //        type union {
  //          type string {
  //            pattern "<.*>|$.*";
  //          }
  //          type uint32 {
  //            range "1 .. 60";
  //          }
  //        }
  //      }
  //    }
  //    leaf mac-table-aging-time {
  //      description "Delay for discarding MAC address if no updates are received";
  //      units "seconds";
  //      type union {
  //        type string {
  //          pattern "<.*>|$.*";
  //        }
  //        type uint32;
  //      }
  //    }
  //    leaf no-mac-learning {
  //      description "Disable dynamic MAC address learning";
  //      type empty;
  //    }
  //    leaf no-normalization {
  //      description "Disable vlan id normalization for interfaces";
  //      type empty;
  //    }
  //    leaf drop-unknown-mac-ip {
  //      description "Drop unknown MAC-IP traffic";
  //      type empty;
  //    }
  //    leaf mac-statistics {
  //      description "Enable MAC address statistics";
  //      type empty;
  //    }
  //    container mib {
  //      presence "enable mib";
  //      description "Snmp mib options";
  //      // uses apply-advanced;
  //      container dot1q-mib {
  //        presence "enable dot1q-mib";
  //        description "Dot1q MIB configuration options";
  //        // uses apply-advanced;
  //        leaf port-list {
  //          description "Port list for staticegressports and staticuntaggedports MIB";
  //          type enumeration {
  //            enum "bit-map" {
  //              description "Port list is represented in bit-map format";
  //            }
  //            enum "string" {
  //              description "Port list is represented in string format";
  //            }
  //          }
  //        }
  //      }
  //    }
  //    container static-rvtep-mac {
  //      description "Configure Static MAC and remote VxLAN tunnel endpoint entries";
  //      // uses apply-advanced;
  //      list mac {
  //        key "mac_addr remote-vtep";
  //        description "Unicast MAC address";
  //        leaf mac_addr {
  //          type jt:mac-unicast;
  //        }
  //        leaf remote-vtep {
  //          description "Configure static remote VXLAN tunnel endpoints";
  //          type jt:ipaddr;
  //        }
  //      }
  //    }
  //    leaf service-id {
  //      description "Service ID required if multi-chassis AE is part of a bridge-domain";
  //      type union {
  //        type string {
  //          pattern "<.*>|$.*";
  //        }
  //        type uint32 {
  //          range "1 .. 65535";
  //        }
  //      }
  //    }
  //    leaf ovsdb-managed {
  //      description "All vxlan bridge domains in routing instance are remote managed";
  //      type empty;
  //    }
  //    container network-isolation-profile {
  //      description "Network isolation configuration";
  //      // uses apply-advanced;
  //      list group {
  //        key name;
  //        description "Network isolation group";
  //        leaf name {
  //          description "Group name";
  //          type string;
  //        }
  //        // uses apply-advanced;
  //      }
  //    }
  //    list interface {
  //      key name;
  //      description "Interface that connect this site to the VPN";
  //      leaf name {
  //        description "Interface name";
  //        type union {
  //          type jt:interface-name;
  //          type string {
  //            pattern "<.*>|$.*";
  //          }
  //        }
  //      }
  //      // uses apply-advanced;
  //      container mac-learning-priority {
  //        description "MAC learning priority for the interface";
  //        // uses apply-advanced;
  //        leaf priority {
  //          description "Mac learning priority for the interface";
  //          type union {
  //            type string {
  //              pattern "<.*>|$.*";
  //            }
  //            type uint32 {
  //              range "1 .. 65535";
  //            }
  //          }
  //        }
  //        leaf packet-action {
  //          default "discard";
  //          type enumeration {
  //            enum "discard" {
  //              description "Discard the packets and do not learn. Default is forward";
  //            }
  //            enum "forward" {
  //              description "Forward the packet";
  //            }
  //          }
  //        }
  //      }
  //      container interface-mac-limit {
  //        description "Maximum number of MAC addresses learned on the interface";
  //        // uses apply-advanced;
  //        leaf limit {
  //          description "Maximum number of MAC addresses per interface";
  //          type union {
  //            type string {
  //              pattern "<.*>|$.*";
  //            }
  //            type uint32;
  //          }
  //        }
  //        leaf disable {
  //          description "Disable interface for interface-mac-limit";
  //          type empty;
  //        }
  //        leaf packet-action {
  //          description "Action when MAC limit is reached";
  //          type enumeration {
  //            enum "none" {
  //              description "Forward the packet";
  //            }
  //            enum "drop" {
  //              description "Drop packets and do not learn. Default is forward";
  //            }
  //            enum "log" {
  //              description "Do not drop the packet but generate an alarm, an SNMP trap or a system log entry";
  //            }
  //            enum "shutdown" {
  //              description "Disable the interface and generate an alarm, an SNMP trap or a system log entry";
  //            }
  //            enum "drop-and-log" {
  //              description "Drop the packet and generate an alarm, an SNMP trap or a system log entry";
  //            }
  //          }
  //        }
  //      }
  //      leaf action-priority {
  //        description "Blocking priority of this interface on mac move detection";
  //        type union {
  //          type string {
  //            pattern "<.*>|$.*";
  //          }
  //          type uint32 {
  //            range "0 .. 8";
  //          }
  //        }
  //      }
  //      list static-mac {
  //        key name;
  //        ordered-by user;
  //        description "Static MAC addresses assigned to this interface";
  //        leaf name {
  //          description "MAC address";
  //          type jt:mac-addr;
  //        }
  //        // uses apply-advanced;
  //        list vlan-id {
  //          key name;
  //          ordered-by user;
  //          description "VLAN ID of learning VLAN";
  //          leaf name {
  //            description "Learning VLAN";
  //            type union {
  //              type string {
  //                pattern "<.*>|$.*";
  //              }
  //              type uint32 {
  //                range "0 .. 4094";
  //              }
  //            }
  //          }
  //          // uses apply-advanced;
  //        }
  //      }
  //      list static-mac-ip {
  //        key name;
  //        ordered-by user;
  //        description "Static MAC-IP address bindings";
  //        leaf name {
  //          description "IP address";
  //          type jt:ipaddr;
  //        }
  //        // uses apply-advanced;
  //        leaf-list mac-address {
  //          ordered-by user;
  //          description "MAC address";
  //          type jt:mac-unicast;
  //          max-elements 8;
  //        }
  //        leaf router {
  //          description "Router flag for ipv6 addresses";
  //          type empty;
  //        }
  //      }
  //      container interface-mac-ip-limit {
  //        description "Maximum number of MAC+IP bindings learned on the interface";
  //        // uses apply-advanced;
  //        leaf limit {
  //          description "Maximum number of MAC+IP bindings per interface";
  //          type union {
  //            type string {
  //              pattern "<.*>|$.*";
  //            }
  //            type uint32;
  //          }
  //        }
  //      }
  //      leaf no-mac-learning {
  //        description "Disable dynamic MAC address learning";
  //        type empty;
  //      }
  //      leaf mac-pinning {
  //        description "Enable MAC pinning";
  //        type empty;
  //      }
  //      leaf persistent-learning {
  //        description "Enable persistent MAC learning on this interface";
  //        type empty;
  //      }
  //    }
  //    container traceoptions {
  //      description "Layer 2 trace options for this routing instance";
  //      // uses apply-advanced;
  //      leaf no-remote-trace {
  //        description "Disable remote tracing";
  //        type empty;
  //      }
  //      container file {
  //        description "Trace file information";
  //        leaf filename {
  //          description "Name of file in which to write trace information";
  //          type string {
  //            length "1 .. 1024";
  //          }
  //        }
  //        leaf size {
  //          description "Maximum trace file size";
  //          type string;
  //        }
  //        leaf files {
  //          description "Maximum number of trace files";
  //          default "3";
  //          type union {
  //            type string {
  //              pattern "<.*>|$.*";
  //            }
  //            type uint32 {
  //              range "2 .. 1000";
  //            }
  //          }
  //        }
  //        choice world-readable-choice {
  //          leaf world-readable {
  //            description "Allow any user to read the log file";
  //            type empty;
  //          }
  //          leaf no-world-readable {
  //            description "Don't allow any user to read the log file";
  //            type empty;
  //          }
  //        }
  //        leaf match {
  //          description "Regular expression for lines to be logged";
  //          type jt:regular-expression;
  //        }
  //      }
  //      leaf level {
  //        description "Level of debugging output";
  //        default "error";
  //        type enumeration {
  //          enum "error" {
  //            description "Match error conditions";
  //          }
  //          enum "warning" {
  //            description "Match warning messages";
  //          }
  //          enum "notice" {
  //            description "Match conditions that should be handled specially";
  //          }
  //          enum "info" {
  //            description "Match informational messages";
  //          }
  //          enum "verbose" {
  //            description "Match verbose messages";
  //          }
  //          enum "all" {
  //            description "Match all levels";
  //          }
  //        }
  //      }
  //      list flag {
  //        key name;
  //        ordered-by user;
  //        description "Type of operation or event to include in trace";
  //        leaf name {
  //          type enumeration {
  //            enum "configuration" {
  //              description "Configuration operations";
  //            }
  //            enum "routing-socket" {
  //              description "Routing socket operations";
  //            }
  //            enum "interface-device" {
  //              description "Interface device operations";
  //            }
  //            enum "interface-logical" {
  //              description "Logical interface operations";
  //            }
  //            enum "interface-family" {
  //              description "Interface family operations";
  //            }
  //            enum "bridging-domain" {
  //              description "Bridging domain operations";
  //            }
  //            enum "bridge-interface" {
  //              description "Interface bridge operations";
  //            }
  //            enum "learning-domain" {
  //              description "Learning domain operations";
  //            }
  //            enum "ipc" {
  //              description "Inter-process communications operations";
  //            }
  //            enum "mac-learning" {
  //              description "MAC address learning operations";
  //            }
  //            enum "initialization" {
  //              description "Initialization operations";
  //            }
  //            enum "flood-next-hop" {
  //              description "Flood next hop operations";
  //            }
  //            enum "irb" {
  //              description "Integrated routing and bridging operations";
  //            }
  //            enum "vpls-ping" {
  //              description "VPLS ping operations";
  //            }
  //            enum "vpls-loop-prev" {
  //              description "VPLS loop prevention";
  //            }
  //            enum "storm-control" {
  //              description "Storm-control";
  //            }
  //            enum "unknown-unicast-forwarding" {
  //              description "Trace unknown unicast forwarding events";
  //            }
  //            enum "vxlan" {
  //              description "VXLAN";
  //            }
  //            enum "all" {
  //              description "All operations";
  //            }
  //          }
  //        }
  //      }
  //    }
  //    container voip {
  //      description "Voice-over-IP configuration";
  //      // uses apply-advanced;
  //      list interface {
  //        key name;
  //        ordered-by user;
  //        description "Enable voice over IP on this port";
  //        leaf name {
  //          type string;
  //        }
  //        // uses apply-advanced;
  //        leaf vlan {
  //          description "VLAN for voice over IP";
  //          type string {
  //          }
  //        }
  //        leaf forwarding-class {
  //          description "Forwarding class";
  //          type string {
  //          }
  //        }
  //      }
  //    }
  //    container unknown-unicast-forwarding {
  //      description "Set interface for forwarding of unknown unicast packets";
  //      // uses apply-advanced;
  //      list vlan {
  //        key name;
  //        description "VLAN for the unknown unicast packets";
  //        leaf name {
  //          description "VLAN name or VLAN Tag (1..4095)";
  //          type string {
  //          }
  //        }
  //        // uses apply-advanced;
  //        leaf interface {
  //          description "Interface to send unknown unicast packets for the VLAN";
  //          type union {
  //            type jt:interface-name;
  //            type string {
  //              pattern "<.*>|$.*";
  //            }
  //          }
  //        }
  //      }
  //    }
  //    list authentication-whitelist {
  //      key name;
  //      ordered-by user;
  //      description "MAC authentication-whitelist configuration needed to bypass Authentication";
  //      leaf name {
  //        description "MAC addresses to bypass authentication";
  //        type jt:mac-addr-prefix;
  //      }
  //      // uses apply-advanced;
  //      leaf vlan-assignment {
  //        description "VLAN name or 802.1q tag for the MAC address";
  //        type string {
  //        }
  //      }
  //      leaf bridge-domain-assignment {
  //        description "Bridge-domain name or 802.1q tag for the MAC address";
  //        type string {
  //        }
  //      }
  //      leaf interface {
  //        description "Interface on which authentication is bypassed";
  //        type union {
  //          type jt:interface-name;
  //          type string {
  //            pattern "<.*>|$.*";
  //          }
  //        }
  //      }
  //    }
  //    choice vstp-flooding-option {
  //      case case_1 {
  //        leaf vstp-flooding {
  //          description "Flood vstp bpdu when vstp is disabled";
  //          type empty;
  //        }
  //      }
  //    }
  //    choice arp-trap-option {
  //    }
  //    choice mstp-flooding-option {
  //    }
  //    choice stp-flooding-option {
  //    }
  //  }
   grouping juniper-routing-options {
     // uses apply-advanced;
    //  container rpm-tracking {
    //    description "RPM static route tracking options";
    //    // uses apply-advanced;
    //    list route {
    //      key name;
    //      ordered-by user;
    //      description "Static Route";
    //      leaf name {
    //        description "IP address of destination";
    //        type jt:ipprefix;
    //      }
    //      // uses apply-advanced;
    //      list next-hop {
    //        key name;
    //        ordered-by user;
    //        description "Next hop to destination";
    //        uses rpm-next-hop;
    //      }
    //      leaf metric {
    //        description "Metric value";
    //        type union {
    //          type string {
    //            pattern "<.*>|$.*";
    //          }
    //          type uint32 {
    //            range "1 .. 16";
    //          }
    //        }
    //      }
    //      leaf preference {
    //        description "Preference value";
    //        type union {
    //          type uint32;
    //          type string {
    //            pattern "<.*>|$.*";
    //          }
    //        }
    //      }
    //      leaf tag {
    //        description "Tag value";
    //        type union {
    //          type uint32;
    //          type string {
    //            pattern "<.*>|$.*";
    //          }
    //        }
    //      }
    //      list rpm-probe {
    //        key name;
    //        ordered-by user;
    //        leaf name {
    //          description "RPM probe to track";
    //          type string;
    //        }
    //        leaf rpm-test {
    //          description "RPM test to track";
    //          type string;
    //        }
    //      }
    //    }
    //  }
    //  container logical-system-mux {
    //    description "Logical system control daemon information";
    //    // uses apply-advanced;
    //    container traceoptions {
    //      description "Trace options";
    //      // uses apply-advanced;
    //      container file {
    //        description "Trace file options";
    //        leaf filename {
    //          description "Name of file in which to write trace information";
    //          type string {
    //            length "1 .. 1024";
    //          }
    //        }
    //        leaf replace {
    //          description "Replace trace file rather than appending to it";
    //          status deprecated;
    //          type empty;
    //        }
    //        leaf size {
    //          description "Maximum trace file size";
    //          type string;
    //        }
    //        leaf files {
    //          description "Maximum number of trace files";
    //          default "10";
    //          type union {
    //            type string {
    //              pattern "<.*>|$.*";
    //            }
    //            type uint32 {
    //              range "2 .. 1000";
    //            }
    //          }
    //        }
    //        leaf no-stamp {
    //          description "Do not timestamp trace file";
    //          status deprecated;
    //          type empty;
    //        }
    //        choice world-readable-choice {
    //          leaf world-readable {
    //            description "Allow any user to read the log file";
    //            type empty;
    //          }
    //          leaf no-world-readable {
    //            description "Don't allow any user to read the log file";
    //            type empty;
    //          }
    //        }
    //      }
    //      list flag {
    //        key name;
    //        ordered-by user;
    //        description "Tracing parameters";
    //        leaf name {
    //          type enumeration {
    //            enum "debug" {
    //              description "Trace debug-level lrmuxd activities";
    //            }
    //            enum "parse" {
    //              description "Trace configuration parsing";
    //            }
    //            enum "route" {
    //              description "Trace routing information";
    //            }
    //            enum "normal" {
    //              description "Trace normal events";
    //            }
    //            enum "general" {
    //              description "Trace general events";
    //            }
    //            enum "state" {
    //              description "Trace state transitions";
    //            }
    //            enum "policy" {
    //              description "Trace policy processing";
    //            }
    //            enum "task" {
    //              description "Trace routing protocol task processing";
    //            }
    //            enum "timer" {
    //              description "Trace routing protocol timer processing";
    //            }
    //            enum "all" {
    //              description "Trace everything";
    //            }
    //          }
    //        }
    //        leaf send {
    //          description "Trace transmitted packets";
    //          type empty;
    //        }
    //        leaf receive {
    //          description "Trace received packets";
    //          type empty;
    //        }
    //        leaf detail {
    //          description "Trace detailed information";
    //          type empty;
    //        }
    //        leaf disable {
    //          description "Disable this trace flag";
    //          type empty;
    //        }
    //      }
    //    }
    //  }
     container auto-bandwidth {
       presence "enable auto-bandwidth";
       description "Auto bandwidth";
       // uses apply-advanced;
       list template {
         key name;
         ordered-by user;
         description "Auto bandwidth template";
         leaf name {
           description "Auto bandwidth template name (Maximum length 64)";
           type string {
             length "1 .. 64";
           }
         }
         // uses apply-advanced;
         leaf adjust-interval {
           description "Adjust interval";
           type union {
             type string {
               pattern "<.*>|$.*";
             }
             type uint32 {
               range "30 .. 3600";
             }
           }
         }
         leaf adjust-threshold {
           description "Percentage threshhold";
           type union {
             type string {
               pattern "<.*>|$.*";
             }
             type uint32 {
               range "0 .. 100";
             }
           }
         }
         leaf statistic-collection-interval {
           description "Collection interval";
           type union {
             type string {
               pattern "<.*>|$.*";
             }
             type uint32 {
               range "10 .. 300";
             }
           }
         }
         leaf auto-bandwidth-subscription {
           description "Percentage threshhold for subscription";
           type union {
             type string {
               pattern "<.*>|$.*";
             }
             type uint32 {
               range "0 .. 200";
             }
           }
         }
       }
       container traceoptions {
         description "Trace options for sr stats";
         // uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "all" {
                 description "Trace All";
               }
               enum "timer" {
                 description "Trace traffic recv by periodic timer";
               }
               enum "state" {
                 description "Trace state of sensor";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
    //  container backup-selection {
    //    presence "enable backup-selection";
    //    description "Backup selection options";
    //    // uses apply-advanced;
    //    list destination {
    //      key name;
    //      description "IP/IPv6 prefix for which backup selection policy is configured";
    //      leaf name {
    //        description "IP/IPv6 address (and optional prefix length)";
    //        type jt:ipprefix-mandatory;
    //      }
    //      // uses apply-advanced;
    //      list interface {
    //        key name;
    //        description "Primary nexthop interface for which backup selection policy is configured";
    //        leaf name {
    //          description "Interface name";
    //          type union {
    //            type jt:interface-name;
    //            type string {
    //              pattern "<.*>|$.*";
    //            }
    //          }
    //        }
    //        // uses apply-advanced;
    //        container admin-group {
    //          description "Administrative group policies for backup-selection";
    //          // uses apply-advanced;
    //          leaf-list exclude {
    //            description "Do not use interface if any admin group available";
    //            type string;
    //          }
    //          leaf-list include-all {
    //            description "Use interface if admin groups available entirely";
    //            type string;
    //          }
    //          leaf-list include-any {
    //            description "Use interface if any admin group is available";
    //            type string;
    //          }
    //          leaf-list preference {
    //            ordered-by user;
    //            description "Administrative groups in descending preference order";
    //            type string;
    //          }
    //        }
    //        leaf srlg {
    //          description "Evaluate Shared Risk Link Group(SRLG) characteristics for backup selection";
    //          default "loose";
    //          type enumeration {
    //            enum "loose" {
    //              description "Loose SRLG";
    //            }
    //            enum "strict" {
    //              description "Strict SRLG";
    //            }
    //          }
    //        }
    //        leaf protection-type {
    //          description "Type of protection to be considered";
    //          type enumeration {
    //            enum "link" {
    //              description "Protect the primary interface from link faults only";
    //            }
    //            enum "node" {
    //              description "Protect the primary interface from node faults only";
    //            }
    //            enum "node-link" {
    //              description "Protect the primary interface from either link or node faults; prefer node protection";
    //            }
    //          }
    //        }
    //        leaf downstream-paths-only {
    //          description "Choose only the downstream nodes for backup";
    //          type empty;
    //        }
    //        leaf bandwidth-greater-equal-primary {
    //          description "Use backup nexthop only if bandwidth is >= bandwidth of primary nexthop";
    //          type empty;
    //        }
    //        container backup-neighbor {
    //          description "Backup Neighbor ID based policies for backup selection";
    //          // uses apply-advanced;
    //          leaf-list exclude {
    //            description "List of backup neighbors to be excluded";
    //            type jt:ipv4addr;
    //          }
    //          leaf-list preference {
    //            ordered-by user;
    //            description "List of backup neighbors in descending order preference";
    //            type jt:ipv4addr;
    //          }
    //        }
    //        container node {
    //          description "Node ID based policies for backup selection";
    //          // uses apply-advanced;
    //          leaf-list exclude {
    //            description "List of nodes to be excluded";
    //            type jt:ipv4addr;
    //          }
    //          leaf-list preference {
    //            ordered-by user;
    //            description "List of nodes in the descending order of preference";
    //            type jt:ipv4addr;
    //          }
    //        }
    //        container node-tag {
    //          description "Node  tag policies";
    //          // uses apply-advanced;
    //          leaf-list exclude {
    //            description "The set of node tags to be excluded";
    //            type union {
    //              type uint32;
    //              type string {
    //                pattern "<.*>|$.*";
    //              }
    //            }
    //          }
    //          leaf-list preference {
    //            ordered-by user;
    //            description "The set of node tags in the descending order of preference";
    //            type union {
    //              type uint32;
    //              type string {
    //                pattern "<.*>|$.*";
    //              }
    //            }
    //          }
    //        }
    //        leaf root-metric {
    //          description "Root metric";
    //          type enumeration {
    //            enum "lowest" {
    //              description "Choose lowest root metric";
    //            }
    //            enum "highest" {
    //              description "Choose highest root metric";
    //            }
    //          }
    //        }
    //        leaf dest-metric {
    //          description "Destination metric";
    //          type enumeration {
    //            enum "lowest" {
    //              description "Choose lowest destination metric";
    //            }
    //            enum "highest" {
    //              description "Choose highest destination metric";
    //            }
    //          }
    //        }
    //        leaf-list metric-order {
    //          ordered-by user;
    //          description "Metric evaluation order";
    //          type enumeration {
    //            enum "root" {
    //            }
    //            enum "dest" {
    //            }
    //          }
    //          max-elements 2;
    //        }
    //        leaf-list evaluation-order {
    //          ordered-by user;
    //          description "Interface policy criteria evaluation order";
    //          type enumeration {
    //            enum "admin-group" {
    //              description "Administrative Group/Link Color";
    //            }
    //            enum "srlg" {
    //              description "SRLG";
    //            }
    //            enum "bandwidth" {
    //              description "Bandwidth";
    //            }
    //            enum "protection-type" {
    //              description "Type of protection";
    //            }
    //            enum "backup-neighbor" {
    //              description "Backup Neighbor";
    //            }
    //            enum "node" {
    //              description "Node";
    //            }
    //            enum "node-tag" {
    //              description "Node tag";
    //            }
    //            enum "metric" {
    //              description "Metric related parameters";
    //            }
    //          }
    //        }
    //      }
    //    }
    //  }
    //  list flex-algorithm {
    //    key name;
    //    description "Configure flex-algorithms supported by this node.";
    //    leaf name {
    //      description "Algorithm id";
    //      type union {
    //        type string {
    //          pattern "<.*>|$.*";
    //        }
    //        type uint32 {
    //          range "128 .. 255";
    //        }
    //      }
    //    }
    //    // uses apply-advanced;
    //    container definition {
    //      description "Configure flex-algorithm definition.";
    //      // uses apply-advanced;
    //      leaf metric-type {
    //        type enumeration {
    //          enum "igp-metric" {
    //            description "Metric configured to be used for IGP";
    //          }
    //          enum "te-metric" {
    //            description "Traffic-engineering metric";
    //          }
    //          enum "delay-metric" {
    //            description "Min unidirectional link delay metric";
    //          }
    //        }
    //      }
    //      choice calculation-type {
    //        case case_1 {
    //          leaf spf {
    //            description "Normal SPF of type 0";
    //            type empty;
    //          }
    //        }
    //        case case_2 {
    //          leaf strict-spf {
    //            description "Strict SPF";
    //            type empty;
    //          }
    //        }
    //      }
    //      leaf use-flex-algorithm-prefix-metric {
    //        description "Set M flag in the flex-algorithm definition flags";
    //        type empty;
    //      }
    //      leaf priority {
    //        description "Priority of the flex-algorithm advertisement.";
    //        type union {
    //          type string {
    //            pattern "<.*>|$.*";
    //          }
    //          type uint32 {
    //            range "0 .. 255";
    //          }
    //        }
    //      }
    //      container admin-group {
    //        description "Administrative group policy";
    //        uses admin_group_include_exclude;
    //      }
    //    }
    //    leaf color {
    //      description "Color to be associated with this flex-algorithm";
    //      type union {
    //        type uint32;
    //        type string {
    //          pattern "<.*>|$.*";
    //        }
    //      }
    //    }
    //    container use-transport-class {
    //      presence "enable use-transport-class";
    //      description "Install ingress routes via transport class RIBs";
    //      // uses apply-advanced;
    //      leaf inet3-install {
    //        description "Install flex-algo routes in inet{6}.3 table";
    //        type empty;
    //      }
    //    }
    //  }
    //  container source-packet-routing {
    //    description "Source packet routing (SPRING)";
    //    // uses apply-advanced;
    //    list mapping-server-entry {
    //      key name;
    //      ordered-by user;
    //      description "Mapping server entry";
    //      leaf name {
    //        description "Mapping server entry name";
    //        type string {
    //          length "1 .. 64";
    //        }
    //      }
    //      // uses apply-advanced;
    //      list prefix-segment {
    //        key name;
    //        ordered-by user;
    //        description "Prefix segment";
    //        max-elements 256;
    //        leaf name {
    //          description "Prefix segment prefix";
    //          type jt:ipprefix;
    //        }
    //        // uses apply-advanced;
    //        leaf index {
    //          description "Prefix segment index";
    //          type union {
    //            type string {
    //              pattern "<.*>|$.*";
    //            }
    //            type uint32 {
    //              range "0 .. 199999";
    //            }
    //          }
    //        }
    //        leaf attached {
    //          description "Set attached flag in IS-IS mapping server advertisement";
    //          type empty;
    //        }
    //        leaf domain-wide-flooding {
    //          description "Set S-flag in IS-IS mapping server advertisement";
    //          type empty;
    //        }
    //        leaf no-node-segment {
    //          description "Clear node segment flag in mapping server prefix segment";
    //          type empty;
    //        }
    //      }
    //      list prefix-segment-range {
    //        key name;
    //        ordered-by user;
    //        description "Prefix segment range";
    //        max-elements 256;
    //        leaf name {
    //          description "Prefix segment range name";
    //          type string {
    //            length "1 .. 64";
    //          }
    //        }
    //        // uses apply-advanced;
    //        leaf start-prefix {
    //          description "Start prefix";
    //          type jt:ipprefix;
    //        }
    //        leaf start-index {
    //          description "Start index";
    //          type union {
    //            type string {
    //              pattern "<.*>|$.*";
    //            }
    //            type uint32 {
    //              range "0 .. 199999";
    //            }
    //          }
    //        }
    //        leaf size {
    //          description "Size of prefix segment range";
    //          type union {
    //            type string {
    //              pattern "<.*>|$.*";
    //            }
    //            type uint32 {
    //              range "1 .. 1024";
    //            }
    //          }
    //        }
    //        leaf attached {
    //          description "Set attached flag in IS-IS mapping server advertisement";
    //          type empty;
    //        }
    //        leaf domain-wide-flooding {
    //          description "Set S-flag in IS-IS mapping server advertisement";
    //          type empty;
    //        }
    //        leaf no-node-segment {
    //          description "Clear node segment flag in mapping server prefix segment";
    //          type empty;
    //        }
    //      }
    //    }
    //    container srv6 {
    //      description "SRv6 source-packet-routing";
    //      // uses apply-advanced;
    //      list block {
    //        key name;
    //        ordered-by user;
    //        description "Block configuration options";
    //        leaf name {
    //          description "Block name";
    //          type string {
    //            length "1 .. 63";
    //          }
    //        }
    //        // uses apply-advanced;
    //        leaf address {
    //          description "Block prefix for SRv6";
    //          type jt:ipv6prefix-mandatory;
    //        }
    //        container global-micro-sid {
    //          description "Global micro SID block range parameters";
    //          // uses apply-advanced;
    //          leaf maximum-sids {
    //            description "Maximum number of SIDs used for global block";
    //            type union {
    //              type string {
    //                pattern "<.*>|$.*";
    //              }
    //              type uint32 {
    //                range "0 .. 65536";
    //              }
    //            }
    //          }
    //          leaf maximum-static-sids {
    //            description "Maximum number of static SIDs used for global block";
    //            type union {
    //              type string {
    //                pattern "<.*>|$.*";
    //              }
    //              type uint32 {
    //                range "0 .. 65536";
    //              }
    //            }
    //          }
    //        }
    //        container local-micro-sid {
    //          description "Local micro SID block range parameters";
    //          // uses apply-advanced;
    //          leaf maximum-static-sids {
    //            description "Maximum number of static SIDs used for local block";
    //            type union {
    //              type string {
    //                pattern "<.*>|$.*";
    //              }
    //              type uint32 {
    //                range "0 .. 65536";
    //              }
    //            }
    //          }
    //        }
    //      }
    //      list locator {
    //        key name;
    //        ordered-by user;
    //        leaf name {
    //          description "Locator entry name";
    //          type string {
    //            length "1 .. 64";
    //          }
    //        }
    //        // uses apply-advanced;
    //        leaf algorithm {
    //          description "Algorithm associated with this locator";
    //          type union {
    //            type string {
    //              pattern "<.*>|$.*";
    //            }
    //            type uint32 {
    //              range "0 .. 255";
    //            }
    //          }
    //        }
    //        leaf address {
    //          description "Configure Locator Service for SRv6";
    //          type jt:ipv6prefix;
    //        }
    //        leaf block-length {
    //          description "Block length associated with this locator";
    //          type union {
    //            type string {
    //              pattern "<.*>|$.*";
    //            }
    //            type uint32 {
    //              range "0 .. 112";
    //            }
    //          }
    //        }
    //        leaf function-length {
    //          description "Function length associated with this locator";
    //          type union {
    //            type string {
    //              pattern "<.*>|$.*";
    //            }
    //            type uint32 {
    //              range "16 .. 32";
    //            }
    //          }
    //        }
    //        leaf static-function-max-entries {
    //          description "Static function maximum entries";
    //          type union {
    //            type string {
    //              pattern "<.*>|$.*";
    //            }
    //            type uint32 {
    //              range "0 .. 4294967295";
    //            }
    //          }
    //        }
    //        container micro-sid {
    //          presence "enable micro-sid";
    //          description "Enable micro SID locator";
    //          // uses apply-advanced;
    //          leaf block-name {
    //            description "Block name of micro SID locator";
    //            type string {
    //              length "1 .. 63";
    //            }
    //          }
    //          container flavor {
    //            description "Flavor of micro SID locator";
    //            // uses apply-advanced;
    //            leaf psp {
    //              description "Penultimate segment pop of the SRH";
    //              type empty;
    //            }
    //            leaf usp {
    //              description "Ultimate segment pop of the SRH";
    //              type empty;
    //            }
    //            leaf usd {
    //              description "Ultimate segment decapsulation";
    //              type empty;
    //            }
    //            leaf none {
    //              description "No flavor";
    //              type empty;
    //            }
    //          }
    //          leaf anycast {
    //            description "Anycast locator";
    //            type empty;
    //          }
    //        }
    //      }
    //      leaf no-reduced-srh {
    //        description "SRv6 Encapsulation mode non reduced SRH";
    //        type empty;
    //      }
    //      leaf transit-srh-insert {
    //        description "SRv6 SRH insert mode on transit";
    //        type empty;
    //      }
    //      leaf no-psp {
    //        description "Disable PSP";
    //        type empty;
    //      }
    //      container traceoptions {
    //        presence "enable traceoptions";
    //        description "Trace options for SRv6 process";
    //        // uses apply-advanced;
    //        leaf no-remote-trace {
    //          description "Disable remote tracing";
    //          type empty;
    //        }
    //        container file {
    //          description "Trace file information";
    //          leaf filename {
    //            description "Name of file in which to write trace information";
    //            type string {
    //              length "1 .. 1024";
    //            }
    //          }
    //          leaf size {
    //            description "Maximum trace file size";
    //            type string;
    //          }
    //          leaf files {
    //            description "Maximum number of trace files";
    //            default "3";
    //            type union {
    //              type string {
    //                pattern "<.*>|$.*";
    //              }
    //              type uint32 {
    //                range "2 .. 1000";
    //              }
    //            }
    //          }
    //          choice world-readable-choice {
    //            leaf world-readable {
    //              description "Allow any user to read the log file";
    //              type empty;
    //            }
    //            leaf no-world-readable {
    //              description "Don't allow any user to read the log file";
    //              type empty;
    //            }
    //          }
    //          leaf match {
    //            description "Regular expression for lines to be logged";
    //            type jt:regular-expression;
    //          }
    //        }
    //        list flag {
    //          key name;
    //          ordered-by user;
    //          description "Tracing parameters";
    //          leaf name {
    //            type enumeration {
    //              enum "srv6-oam-recv" {
    //                description "Trace recv activity";
    //              }
    //              enum "srv6-oam-err" {
    //                description "Trace error activity";
    //              }
    //            }
    //          }
    //        }
    //      }
    //      container oam {
    //        description "OAM options";
    //        // uses apply-advanced;
    //        container traceoptions {
    //          description "Trace options for MPLSOAM process";
    //          // uses apply-advanced;
    //          leaf no-remote-trace {
    //            description "Disable remote tracing";
    //            type empty;
    //          }
    //          container file {
    //            description "Trace file information";
    //            leaf filename {
    //              description "Name of file in which to write trace information";
    //              type string {
    //                length "1 .. 1024";
    //              }
    //            }
    //            leaf size {
    //              description "Maximum trace file size";
    //              type string;
    //            }
    //            leaf files {
    //              description "Maximum number of trace files";
    //              default "3";
    //              type union {
    //                type string {
    //                  pattern "<.*>|$.*";
    //                }
    //                type uint32 {
    //                  range "2 .. 1000";
    //                }
    //              }
    //            }
    //            choice world-readable-choice {
    //              leaf world-readable {
    //                description "Allow any user to read the log file";
    //                type empty;
    //              }
    //              leaf no-world-readable {
    //                description "Don't allow any user to read the log file";
    //                type empty;
    //              }
    //            }
    //            leaf match {
    //              description "Regular expression for lines to be logged";
    //              type jt:regular-expression;
    //            }
    //          }
    //          list flag {
    //            key name;
    //            ordered-by user;
    //            description "Tracing parameters";
    //            leaf name {
    //              type enumeration {
    //                enum "configuration" {
    //                  description "Trace configuration events";
    //                }
    //                enum "pipe" {
    //                  description "Trace pipe activity";
    //                }
    //                enum "rpc-packet-details" {
    //                  description "Trace SRv6 RPC packet details";
    //                }
    //                enum "database" {
    //                  description "Trace SRv6 database activity";
    //                }
    //                enum "network" {
    //                  description "Trace SRv6 network activity";
    //                }
    //                enum "traceroute" {
    //                  description "Trace SRv6 traceroute activity";
    //                }
    //                enum "all" {
    //                  description "Trace everything";
    //                }
    //              }
    //            }
    //          }
    //        }
    //      }
    //    }
    //  }
     leaf route-distinguisher-id {
       description "Identifier used in route distinguishers for routing instances";
       type jt:ipv4addr;
     }
    //  list domain-path-id {
    //    key name;
    //    ordered-by user;
    //    description "VRF domain id path configuration";
    //    max-elements 2;
    //    uses domain-id-type;
    //  }
     list rib {
       key name;
       description "Routing table options";
       leaf name {
         description "Routing table name";
         type string;
       }
       // uses apply-advanced;
       container static {
         description "Static routes";
         // uses apply-advanced;
         leaf rib-group {
           description "Routing table group";
           type string;
         }
         container defaults {
           description "Global route options";
           // uses apply-advanced;
           choice retain-choice {
             leaf retain {
               description "Always keep route in forwarding table";
               type empty;
             }
             leaf no-retain {
               description "Don't always keep route in forwarding table";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           leaf explicit-null {
             description "Allows service label to be popped and will lookup nexthop-table inet6.0";
             type empty;
           }
           choice longest-match-choice {
             leaf longest-match {
               description "Always use longest prefix match to resolve next hops";
               type empty;
             }
             leaf no-longest-match {
               description "Don't always use longest prefix match to resolve next hops";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             // uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
         list route {
           key name;
           description "Static route";
           leaf name {
             type jt:ipprefix;
           }
           // uses apply-advanced;
           leaf priority {
             description "Static route priority high/medium/low";
             type enumeration {
               enum "medium" {
                 description "Static route medium priority";
               }
               enum "low" {
                 description "Static route low priority";
               }
               enum "high" {
                 description "Static route high priority";
               }
             }
           }
           choice next_hop {
             case case_1 {
               leaf-list next-hop {
                 ordered-by user;
                 description "Next hop to destination";
                 type union {
                   type jt:ipaddr-or-interface;
                   type string {
                     pattern "<.*>|$.*";
                   }
                 }
               }
             }
             case case_2 {
               leaf reject {
                 description "Drop packets to destination; send ICMP unreachables";
                 type empty;
               }
             }
             case case_3 {
               leaf discard {
                 description "Drop packets to destination; send no ICMP unreachables";
                 type empty;
               }
             }
             case case_4 {
               leaf receive {
                 description "Install a receive route for the destination";
                 type empty;
               }
             }
             case case_5 {
               leaf next-table {
                 description "Next hop to another table";
                 type string {
                 }
               }
             }
           }
           leaf description {
             description "Static route description";
             type string {
             }
           }
          //  list qualified-next-hop {
          //    key name;
          //    ordered-by user;
          //    description "Next hop with qualifiers";
          //    uses qualified_nh_obj;
          //  }
          //  leaf backup-pe-group {
          //    description "Multicast source redundancy group";
          //    type string;
          //  }
          //  container bfd-liveness-detection {
          //    description "Bidirectional Forwarding Detection (BFD) options";
          //    // uses apply-advanced;
          //    leaf version {
          //      description "BFD protocol version number";
          //      default "automatic";
          //      type enumeration {
          //        enum "0" {
          //          description "BFD version 0 (deprecated)";
          //        }
          //        enum "1" {
          //          description "BFD version 1";
          //        }
          //        enum "automatic" {
          //          description "Choose BFD version automatically";
          //        }
          //      }
          //    }
          //    leaf minimum-interval {
          //      description "Minimum transmit and receive interval";
          //      units "milliseconds";
          //      type union {
          //        type string {
          //          pattern "<.*>|$.*";
          //        }
          //        type uint32 {
          //          range "1 .. 255000";
          //        }
          //      }
          //    }
          //    leaf minimum-transmit-interval {
          //      description "Minimum transmit interval";
          //      status deprecated;
          //      units "milliseconds";
          //      type union {
          //        type string {
          //          pattern "<.*>|$.*";
          //        }
          //        type uint32 {
          //          range "1 .. 255000";
          //        }
          //      }
          //    }
          //    leaf minimum-receive-interval {
          //      description "Minimum receive interval";
          //      units "milliseconds";
          //      type union {
          //        type string {
          //          pattern "<.*>|$.*";
          //        }
          //        type uint32 {
          //          range "1 .. 255000";
          //        }
          //      }
          //    }
          //    leaf multiplier {
          //      description "Detection time multiplier";
          //      default "3";
          //      type union {
          //        type string {
          //          pattern "<.*>|$.*";
          //        }
          //        type uint32 {
          //          range "1 .. 255";
          //        }
          //      }
          //    }
          //    leaf inline-disable {
          //      description "Disable inline mode for this BFD session";
          //      type empty;
          //    }
          //    leaf pdu-size {
          //      description "BFD transport protocol payload size";
          //      default "24";
          //      type union {
          //        type string {
          //          pattern "<.*>|$.*";
          //        }
          //        type uint32 {
          //          range "24 .. 9000";
          //        }
          //      }
          //    }
          //    choice adaptation-choice {
          //      case case_1 {
          //        leaf no-adaptation {
          //          description "Disable adaptation";
          //          type empty;
          //        }
          //      }
          //    }
          //    container transmit-interval {
          //      description "Transmit-interval options";
          //      // uses apply-advanced;
          //      leaf minimum-interval {
          //        description "Minimum transmit interval";
          //        units "milliseconds";
          //        type union {
          //          type string {
          //            pattern "<.*>|$.*";
          //          }
          //          type uint32 {
          //            range "1 .. 255000";
          //          }
          //        }
          //      }
          //      leaf threshold {
          //        description "High transmit interval triggering a trap";
          //        units "milliseconds";
          //        type union {
          //          type uint32;
          //          type string {
          //            pattern "<.*>|$.*";
          //          }
          //        }
          //      }
          //    }
          //    container detection-time {
          //      description "Detection-time options";
          //      // uses apply-advanced;
          //      leaf threshold {
          //        description "High detection-time triggering a trap";
          //        units "milliseconds";
          //        type union {
          //          type uint32;
          //          type string {
          //            pattern "<.*>|$.*";
          //          }
          //        }
          //      }
          //    }
          //    container authentication {
          //      description "Authentication options";
          //      // uses apply-advanced;
          //      leaf key-chain {
          //        description "Key chain name";
          //        type string;
          //      }
          //      leaf algorithm {
          //        description "Algorithm name";
          //        type enumeration {
          //          enum "simple-password" {
          //            description "Simple password";
          //          }
          //          enum "keyed-md5" {
          //            description "Keyed message Digest 5";
          //          }
          //          enum "meticulous-keyed-md5" {
          //            description "Meticulous keyed message Digest 5";
          //          }
          //          enum "keyed-sha-1" {
          //            description "Keyed secure hash algorithm (SHA1) ";
          //          }
          //          enum "meticulous-keyed-sha-1" {
          //            description "Meticulous keyed secure hash algorithm (SHA1) ";
          //          }
          //        }
          //      }
          //      leaf loose-check {
          //        description "Verify authentication only if authentication is negotiated";
          //        type empty;
          //      }
          //    }
          //    container echo {
          //      description "Echo mode parameters";
          //      // uses apply-advanced;
          //      leaf minimum-interval {
          //        description "Minimum transmit and receive interval";
          //        units "milliseconds";
          //        type union {
          //          type string {
          //            pattern "<.*>|$.*";
          //          }
          //          type uint32 {
          //            range "100 .. 255000";
          //          }
          //        }
          //      }
          //    }
          //    container echo-lite {
          //      description "Echo-lite more parameters";
          //      // uses apply-advanced;
          //      leaf minimum-interval {
          //        description "Minimum transmit and receive interval";
          //        units "milliseconds";
          //        type union {
          //          type string {
          //            pattern "<.*>|$.*";
          //          }
          //          type uint32 {
          //            range "100 .. 255000";
          //          }
          //        }
          //      }
          //    }
          //    leaf neighbor {
          //      description "BFD neighbor address";
          //      type jt:ipaddr;
          //    }
          //    leaf local-address {
          //      description "BFD local address (for multihop only)";
          //      type jt:ipaddr;
          //    }
          //    leaf holddown-interval {
          //      description "Time to hold the session-UP notification to the client";
          //      units "milliseconds";
          //      type union {
          //        type string {
          //          pattern "<.*>|$.*";
          //        }
          //        type uint32 {
          //          range "0 .. 255000";
          //        }
          //      }
          //    }
          //    leaf minimum-receive-ttl {
          //      description "Minimum receive TTL below which to drop";
          //      type union {
          //        type string {
          //          pattern "<.*>|$.*";
          //        }
          //        type uint8 {
          //          range "1 .. 255";
          //        }
          //      }
          //    }
          //  }
          //  choice retain-choice {
          //    leaf retain {
          //      description "Always keep route in forwarding table";
          //      type empty;
          //    }
          //    leaf no-retain {
          //      description "Don't always keep route in forwarding table";
          //      type empty;
          //    }
          //  }
          //  choice install-choice {
          //    leaf install {
          //      description "Install route into forwarding table";
          //      type empty;
          //    }
          //    leaf no-install {
          //      description "Don't install route into forwarding table";
          //      type empty;
          //    }
          //  }
          //  choice readvertise-choice {
          //    leaf readvertise {
          //      description "Mark route as eligible to be readvertised";
          //      type empty;
          //    }
          //    leaf no-readvertise {
          //      description "Don't mark route as eligible to be readvertised";
          //      type empty;
          //    }
          //  }
          //  choice resolve-choice {
          //    leaf resolve {
          //      description "Allow resolution of indirectly connected next hops";
          //      type empty;
          //    }
          //    leaf no-resolve {
          //      description "Don't allow resolution of indirectly connected next hops";
          //      type empty;
          //    }
          //  }
          //  leaf explicit-null {
          //    description "Allows service label to be popped and will lookup nexthop-table inet6.0";
          //    type empty;
          //  }
          //  choice longest-match-choice {
          //    leaf longest-match {
          //      description "Always use longest prefix match to resolve next hops";
          //      type empty;
          //    }
          //    leaf no-longest-match {
          //      description "Don't always use longest prefix match to resolve next hops";
          //      type empty;
          //    }
          //  }
          //  choice passive_flag {
          //    case case_1 {
          //      leaf active {
          //        description "Remove inactive route from forwarding table";
          //        type empty;
          //      }
          //    }
          //    case case_2 {
          //      leaf passive {
          //        description "Retain inactive route in forwarding table";
          //        type empty;
          //      }
          //    }
          //  }
           container metric {
             description "Metric value";
             presence "enable metric";
             uses rib_static_metric_type;
           }
          //  container metric2 {
          //    description "Metric value 2";
          //    presence "enable metric2";
          //    uses rib_static_metric_type;
          //  }
          //  container metric3 {
          //    description "Metric value 3";
          //    presence "enable metric3";
          //    uses rib_static_metric_type;
          //  }
          //  container metric4 {
          //    description "Metric value 4";
          //    presence "enable metric4";
          //    uses rib_static_metric_type;
          //  }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             // uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
           list lsp-next-hop {
             key name;
             ordered-by user;
             description "LSP next hop";
             uses lsp_nh_obj;
           }
          //  list p2mp-lsp-next-hop {
          //    key name;
          //    ordered-by user;
          //    description "Point-to-multipoint LSP next hop";
          //    max-elements 1;
          //    uses lsp_nh_obj;
          //  }
          //  container spring-te-lsp-next-hop {
          //    description "SPRING-TE LSP next hop";
          //    uses springte_lsp_nh_obj;
          //  }
          //  container p2mp-ldp-next-hop {
          //    description "Point-to-multipoint LDP LSP next hop";
          //    uses p2mp_ldp_lsp_nh_obj;
          //  }
           list static-lsp-next-hop {
             key name;
             ordered-by user;
             description "Static LSP next hop";
             uses lsp_nh_obj;
           }
         }
         leaf protocol-instance-name {
           description "Name of protocol instance under routing instance";
           type string;
         }
         container static-route {
           description "Static route Status";
           leaf bfd-admin-down {
             description "Static route State on BFD ADMIN DOWN";
             type enumeration {
               enum "active" {
                 description "Static route will be inactive on bfd-admin-down";
               }
               enum "passive" {
                 description "Static route will remain active on bfd-admin-down";
               }
             }
           }
         }
         list iso-route {
           key name;
           ordered-by user;
           description "ISO family static route";
           leaf name {
             type jt:isoprefix;
           }
           // uses apply-advanced;
           leaf priority {
             description "Static route priority high/medium/low";
             type enumeration {
               enum "medium" {
                 description "Static route medium priority";
               }
               enum "low" {
                 description "Static route low priority";
               }
               enum "high" {
                 description "Static route high priority";
               }
             }
           }
           choice next_hop {
             case case_1 {
               leaf-list next-hop {
                 ordered-by user;
                 description "Next hop to destination";
                 type union {
                   type jt:ipaddr-or-interface;
                   type string {
                     pattern "<.*>|$.*";
                   }
                 }
               }
             }
             case case_2 {
               leaf reject {
                 description "Drop packets to destination; send ICMP unreachables";
                 type empty;
               }
             }
             case case_3 {
               leaf discard {
                 description "Drop packets to destination; send no ICMP unreachables";
                 type empty;
               }
             }
             case case_4 {
               leaf receive {
                 description "Install a receive route for the destination";
                 type empty;
               }
             }
             case case_5 {
               leaf next-table {
                 description "Next hop to another table";
                 type string {
                 }
               }
             }
           }
           leaf description {
             description "Static route description";
             type string {
             }
           }
          //  list qualified-next-hop {
          //    key name;
          //    ordered-by user;
          //    description "Next hop with qualifiers";
          //    uses qualified_nh_obj;
          //  }
          //  leaf backup-pe-group {
          //    description "Multicast source redundancy group";
          //    type string;
          //  }
          //  container bfd-liveness-detection {
          //    description "Bidirectional Forwarding Detection (BFD) options";
          //    // uses apply-advanced;
          //    leaf version {
          //      description "BFD protocol version number";
          //      default "automatic";
          //      type enumeration {
          //        enum "0" {
          //          description "BFD version 0 (deprecated)";
          //        }
          //        enum "1" {
          //          description "BFD version 1";
          //        }
          //        enum "automatic" {
          //          description "Choose BFD version automatically";
          //        }
          //      }
          //    }
          //    leaf minimum-interval {
          //      description "Minimum transmit and receive interval";
          //      units "milliseconds";
          //      type union {
          //        type string {
          //          pattern "<.*>|$.*";
          //        }
          //        type uint32 {
          //          range "1 .. 255000";
          //        }
          //      }
          //    }
          //    leaf minimum-transmit-interval {
          //      description "Minimum transmit interval";
          //      status deprecated;
          //      units "milliseconds";
          //      type union {
          //        type string {
          //          pattern "<.*>|$.*";
          //        }
          //        type uint32 {
          //          range "1 .. 255000";
          //        }
          //      }
          //    }
          //    leaf minimum-receive-interval {
          //      description "Minimum receive interval";
          //      units "milliseconds";
          //      type union {
          //        type string {
          //          pattern "<.*>|$.*";
          //        }
          //        type uint32 {
          //          range "1 .. 255000";
          //        }
          //      }
          //    }
          //    leaf multiplier {
          //      description "Detection time multiplier";
          //      default "3";
          //      type union {
          //        type string {
          //          pattern "<.*>|$.*";
          //        }
          //        type uint32 {
          //          range "1 .. 255";
          //        }
          //      }
          //    }
          //    leaf inline-disable {
          //      description "Disable inline mode for this BFD session";
          //      type empty;
          //    }
          //    leaf pdu-size {
          //      description "BFD transport protocol payload size";
          //      default "24";
          //      type union {
          //        type string {
          //          pattern "<.*>|$.*";
          //        }
          //        type uint32 {
          //          range "24 .. 9000";
          //        }
          //      }
          //    }
          //    choice adaptation-choice {
          //      case case_1 {
          //        leaf no-adaptation {
          //          description "Disable adaptation";
          //          type empty;
          //        }
          //      }
          //    }
          //    container transmit-interval {
          //      description "Transmit-interval options";
          //      // uses apply-advanced;
          //      leaf minimum-interval {
          //        description "Minimum transmit interval";
          //        units "milliseconds";
          //        type union {
          //          type string {
          //            pattern "<.*>|$.*";
          //          }
          //          type uint32 {
          //            range "1 .. 255000";
          //          }
          //        }
          //      }
          //      leaf threshold {
          //        description "High transmit interval triggering a trap";
          //        units "milliseconds";
          //        type union {
          //          type uint32;
          //          type string {
          //            pattern "<.*>|$.*";
          //          }
          //        }
          //      }
          //    }
          //    container detection-time {
          //      description "Detection-time options";
          //      // uses apply-advanced;
          //      leaf threshold {
          //        description "High detection-time triggering a trap";
          //        units "milliseconds";
          //        type union {
          //          type uint32;
          //          type string {
          //            pattern "<.*>|$.*";
          //          }
          //        }
          //      }
          //    }
          //    container authentication {
          //      description "Authentication options";
          //      // uses apply-advanced;
          //      leaf key-chain {
          //        description "Key chain name";
          //        type string;
          //      }
          //      leaf algorithm {
          //        description "Algorithm name";
          //        type enumeration {
          //          enum "simple-password" {
          //            description "Simple password";
          //          }
          //          enum "keyed-md5" {
          //            description "Keyed message Digest 5";
          //          }
          //          enum "meticulous-keyed-md5" {
          //            description "Meticulous keyed message Digest 5";
          //          }
          //          enum "keyed-sha-1" {
          //            description "Keyed secure hash algorithm (SHA1) ";
          //          }
          //          enum "meticulous-keyed-sha-1" {
          //            description "Meticulous keyed secure hash algorithm (SHA1) ";
          //          }
          //        }
          //      }
          //      leaf loose-check {
          //        description "Verify authentication only if authentication is negotiated";
          //        type empty;
          //      }
          //    }
          //    container echo {
          //      description "Echo mode parameters";
          //      // uses apply-advanced;
          //      leaf minimum-interval {
          //        description "Minimum transmit and receive interval";
          //        units "milliseconds";
          //        type union {
          //          type string {
          //            pattern "<.*>|$.*";
          //          }
          //          type uint32 {
          //            range "100 .. 255000";
          //          }
          //        }
          //      }
          //    }
          //    container echo-lite {
          //      description "Echo-lite more parameters";
          //      // uses apply-advanced;
          //      leaf minimum-interval {
          //        description "Minimum transmit and receive interval";
          //        units "milliseconds";
          //        type union {
          //          type string {
          //            pattern "<.*>|$.*";
          //          }
          //          type uint32 {
          //            range "100 .. 255000";
          //          }
          //        }
          //      }
          //    }
          //    leaf neighbor {
          //      description "BFD neighbor address";
          //      type jt:ipaddr;
          //    }
          //    leaf local-address {
          //      description "BFD local address (for multihop only)";
          //      type jt:ipaddr;
          //    }
          //    leaf holddown-interval {
          //      description "Time to hold the session-UP notification to the client";
          //      units "milliseconds";
          //      type union {
          //        type string {
          //          pattern "<.*>|$.*";
          //        }
          //        type uint32 {
          //          range "0 .. 255000";
          //        }
          //      }
          //    }
          //    leaf minimum-receive-ttl {
          //      description "Minimum receive TTL below which to drop";
          //      type union {
          //        type string {
          //          pattern "<.*>|$.*";
          //        }
          //        type uint8 {
          //          range "1 .. 255";
          //        }
          //      }
          //    }
          //  }
          //  choice retain-choice {
          //    leaf retain {
          //      description "Always keep route in forwarding table";
          //      type empty;
          //    }
          //    leaf no-retain {
          //      description "Don't always keep route in forwarding table";
          //      type empty;
          //    }
          //  }
          //  choice install-choice {
          //    leaf install {
          //      description "Install route into forwarding table";
          //      type empty;
          //    }
          //    leaf no-install {
          //      description "Don't install route into forwarding table";
          //      type empty;
          //    }
          //  }
          //  choice readvertise-choice {
          //    leaf readvertise {
          //      description "Mark route as eligible to be readvertised";
          //      type empty;
          //    }
          //    leaf no-readvertise {
          //      description "Don't mark route as eligible to be readvertised";
          //      type empty;
          //    }
          //  }
          //  choice resolve-choice {
          //    leaf resolve {
          //      description "Allow resolution of indirectly connected next hops";
          //      type empty;
          //    }
          //    leaf no-resolve {
          //      description "Don't allow resolution of indirectly connected next hops";
          //      type empty;
          //    }
          //  }
          //  leaf explicit-null {
          //    description "Allows service label to be popped and will lookup nexthop-table inet6.0";
          //    type empty;
          //  }
          //  choice longest-match-choice {
          //    leaf longest-match {
          //      description "Always use longest prefix match to resolve next hops";
          //      type empty;
          //    }
          //    leaf no-longest-match {
          //      description "Don't always use longest prefix match to resolve next hops";
          //      type empty;
          //    }
          //  }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             // uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
           list lsp-next-hop {
             key name;
             ordered-by user;
             description "LSP next hop";
             uses lsp_nh_obj;
           }
          //  list p2mp-lsp-next-hop {
          //    key name;
          //    ordered-by user;
          //    description "Point-to-multipoint LSP next hop";
          //    max-elements 1;
          //    uses lsp_nh_obj;
          //  }
          //  container spring-te-lsp-next-hop {
          //    description "SPRING-TE LSP next hop";
          //    uses springte_lsp_nh_obj;
          //  }
          //  container p2mp-ldp-next-hop {
          //    description "Point-to-multipoint LDP LSP next hop";
          //    uses p2mp_ldp_lsp_nh_obj;
          //  }
         }
         list route-target-filter {
           key name;
           ordered-by user;
           description "Route-target-filter route";
           leaf name {
             type string {
               length "1 .. 47";
             }
           }
           // uses apply-advanced;
           leaf-list neighbor {
             ordered-by user;
             description "BGP peers for filter";
             type jt:ipaddr-scoped;
           }
           leaf-list group {
             ordered-by user;
             description "BGP groups for filter";
             type string;
           }
           leaf local {
             description "Locally originated filter";
             type empty;
           }
         }
       }
       list martians {
         key "address choice-ident choice-value";
         ordered-by user;
         description "Invalid routes";
         uses martian_type;
       }
       container aggregate {
         description "Coalesced routes";
         uses rib_aggregate_type;
       }
       container generate {
         description "Route of last resort";
         uses rib_aggregate_type;
       }
       choice maximum-paths-type {
         case case_1 {
           container maximum-routes {
             description "Maximum number of routes";
             status deprecated;
             leaf limit {
               description "Maximum number of routes";
               type union {
                 type string {
                   pattern "<.*>|$.*";
                 }
                 type uint32 {
                   range "1 .. 4294967295";
                 }
               }
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
         case case_2 {
           container maximum-paths {
             description "Maximum number of paths";
             leaf limit {
               description "Maximum number of paths";
               type union {
                 type string {
                   pattern "<.*>|$.*";
                 }
                 type uint32 {
                   range "1 .. 4294967295";
                 }
               }
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
       }
       container maximum-prefixes {
         description "Maximum number of prefixes";
         leaf limit {
           description "Maximum number of prefixes";
           type union {
             type string {
               pattern "<.*>|$.*";
             }
             type uint32 {
               range "1 .. 4294967295";
             }
           }
         }
         choice log_type {
           case case_1 {
             leaf threshold {
               description "Percentage of limit at which to start generating warnings";
               type union {
                 type string {
                   pattern "<.*>|$.*";
                 }
                 type uint32 {
                   range "1 .. 100";
                 }
               }
             }
           }
           case case_2 {
             leaf log-only {
               description "Generate warning messages only";
               type empty;
             }
           }
         }
         leaf log-interval {
           description "Minimum interval between log messages";
           units "seconds";
           type union {
             type string {
               pattern "<.*>|$.*";
             }
             type uint32 {
               range "5 .. 86400";
             }
           }
         }
       }
       container multipath {
         presence "enable multipath";
         description "Protocol-independent load balancing";
         // uses apply-advanced;
         container vpn-unequal-cost {
           presence "enable vpn-unequal-cost";
           description "Include VPN routes with unequal IGP metrics";
           leaf equal-external-internal {
             description "Include external and internal VPN routes";
             type empty;
           }
         }
         leaf as-path-compare {
           description "Compare AS path sequences in addition to AS path length";
           type empty;
         }
         leaf preserve-nexthop-hierarchy {
           description "Force multipath to create List nexthop";
           type empty;
         }
       }
       container policy-multipath {
         description "Policy based multipath";
         // uses apply-advanced;
         leaf-list policy {
           ordered-by user;
           description "Import policy to create policy based multipath";
           type jt:policy-algebra;
         }
        //  container traceoptions {
        //    description "Trace options";
        //    // uses apply-advanced;
        //    container file {
        //      description "Trace file options";
        //      leaf filename {
        //        description "Name of file in which to write trace information";
        //        type string {
        //          length "1 .. 1024";
        //        }
        //      }
        //      leaf replace {
        //        description "Replace trace file rather than appending to it";
        //        status deprecated;
        //        type empty;
        //      }
        //      leaf size {
        //        description "Maximum trace file size";
        //        type string;
        //      }
        //      leaf files {
        //        description "Maximum number of trace files";
        //        default "10";
        //        type union {
        //          type string {
        //            pattern "<.*>|$.*";
        //          }
        //          type uint32 {
        //            range "2 .. 1000";
        //          }
        //        }
        //      }
        //      leaf no-stamp {
        //        description "Do not timestamp trace file";
        //        status deprecated;
        //        type empty;
        //      }
        //      choice world-readable-choice {
        //        leaf world-readable {
        //          description "Allow any user to read the log file";
        //          type empty;
        //        }
        //        leaf no-world-readable {
        //          description "Don't allow any user to read the log file";
        //          type empty;
        //        }
        //      }
        //    }
        //    list flag {
        //      key name;
        //      ordered-by user;
        //      description "Tracing parameters";
        //      leaf name {
        //        type enumeration {
        //          enum "route" {
        //            description "Policy-multipath route tracing.";
        //          }
        //        }
        //      }
        //      leaf send {
        //        description "Trace transmitted packets";
        //        type empty;
        //      }
        //      leaf receive {
        //        description "Trace received packets";
        //        type empty;
        //      }
        //      leaf detail {
        //        description "Trace detailed information";
        //        type empty;
        //      }
        //      leaf disable {
        //        description "Disable this trace flag";
        //        type empty;
        //      }
        //    }
        //  }
         leaf preserve-nexthop-hierarchy {
           description "Enable preserved nexthop hierarchy";
           type empty;
         }
       }
       container protect {
         description "Protocol-independent protection";
         leaf core {
           description "Protect against unreachability to service-edge router";
           type empty;
         }
       }
      //  container access {
      //    description "Access routes";
      //    // uses apply-advanced;
      //    list route {
      //      key name;
      //      ordered-by user;
      //      description "Access route";
      //      leaf name {
      //        description "IP address of destination";
      //        type jt:ipprefix;
      //      }
      //      // uses apply-advanced;
      //      leaf-list next-hop {
      //        ordered-by user;
      //        description "Next hop to destination";
      //        type union {
      //          type jt:ipaddr-or-interface;
      //          type string {
      //            pattern "<.*>|$.*";
      //          }
      //        }
      //      }
      //     //  list qualified-next-hop {
      //     //    key name;
      //     //    ordered-by user;
      //     //    description "Next hop with qualifiers";
      //     //    uses qualified_nh_obj;
      //     //  }
      //      leaf metric {
      //        description "Metric value";
      //        type union {
      //          type string {
      //            pattern "<.*>|$.*";
      //          }
      //          type uint32 {
      //            range "1 .. 255";
      //          }
      //        }
      //      }
      //      leaf preference {
      //        description "Preference value";
      //        type union {
      //          type uint32;
      //          type string {
      //            pattern "<.*>|$.*";
      //          }
      //        }
      //      }
      //      leaf tag {
      //        description "Tag string";
      //        type union {
      //          type uint32;
      //          type string {
      //            pattern "<.*>|$.*";
      //          }
      //        }
      //      }
      //      leaf tag2 {
      //        description "Tag2 string";
      //        type union {
      //          type uint32;
      //          type string {
      //            pattern "<.*>|$.*";
      //          }
      //        }
      //      }
      //    }
      //  }
      //  container access-internal {
      //    description "Access-internal routes";
      //    // uses apply-advanced;
      //    list route {
      //      key name;
      //      ordered-by user;
      //      description "Access-internal route";
      //      leaf name {
      //        description "IP address and optional prefix length of destination";
      //        type jt:ipprefix;
      //      }
      //      // uses apply-advanced;
      //      leaf-list next-hop {
      //        ordered-by user;
      //        description "Next hop to destination";
      //        type union {
      //          type jt:ipaddr-or-interface;
      //          type string {
      //            pattern "<.*>|$.*";
      //          }
      //        }
      //      }
      //      list qualified-next-hop {
      //        key name;
      //        ordered-by user;
      //        description "Next hop with qualifiers";
      //        uses qualified_nh_obj;
      //      }
      //    }
      //  }
       container bgp-static {
         description "Routes for BGP static advertisements";
         // uses apply-advanced;
         list route {
           key name;
           ordered-by user;
           description "BGP-static route";
           leaf name {
             description "IP address and optional prefix length of destination";
             type jt:ipprefix;
           }
           // uses apply-advanced;
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             // uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
       }
      //  container flow {
      //    description "Locally defined flow routing information";
      //    // uses apply-advanced;
      //    container validation {
      //      description "Flow route validation options";
      //      presence "enable validation";
      //      uses flow-validation;
      //    }
      //    list route {
      //      key name;
      //      ordered-by user;
      //      description "Flow route";
      //      uses flow-route-inet6;
      //    }
      //    list security-group {
      //      key name;
      //      ordered-by user;
      //      description "Security groups";
      //      leaf name {
      //        description "Name of the security group";
      //        type string {
      //          length "1 .. 16";
      //        }
      //      }
      //      // uses apply-advanced;
      //      list rule {
      //        key name;
      //        ordered-by user;
      //        description "Flow route";
      //        uses flow-rule-inet6;
      //      }
      //    }
      //    container interface-group {
      //      description "Interface-group for applying flow-spec filter";
      //      uses flow-interface-group;
      //    }
      //    leaf discard-action-for-unresolved-redir-addr {
      //      description "For action redirect IP if redirect address is unresolved install discard action filter";
      //      type empty;
      //    }
      //    choice per-route-accounting-choice {
      //      leaf per-route-accounting {
      //        description "Enable traffic accounting per flowspec route";
      //        type empty;
      //      }
      //      leaf no-per-route-accounting {
      //        description "Don't enable traffic accounting per flowspec route";
      //        type empty;
      //      }
      //    }
      //  }
       container label {
         presence "enable label";
         description "Label processing";
         // uses apply-advanced;
         leaf-list allocation {
           ordered-by user;
           description "Label allocation policy";
           type jt:policy-algebra;
         }
         leaf-list substitution {
           ordered-by user;
           description "Label substitution policy";
           type jt:policy-algebra;
         }
       }
     }
     container label {
       presence "enable label";
       description "Label processing";
       // uses apply-advanced;
       leaf-list allocation {
         ordered-by user;
         description "Label allocation policy";
         type jt:policy-algebra;
       }
       leaf-list substitution {
         ordered-by user;
         description "Label substitution policy";
         type jt:policy-algebra;
       }
     }
     container options {
       description "Miscellaneous options";
       // uses apply-advanced;
       leaf no-send {
         description "Listen only; do not send protocol packets";
         status deprecated;
         type empty;
       }
       leaf no-resolve {
         description "Do not use DNS name resolution";
         status deprecated;
         type empty;
       }
       container syslog {
         description "Set system logging level";
         // uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
       }
       leaf mark {
         description "Periodically mark the trace file";
         units "seconds";
         type union {
           type int32;
           type string {
             pattern "<.*>|$.*";
           }
         }
       }
     }
     container resolution {
       presence "enable resolution";
       description "Route next-hop resolution options";
       // uses apply-advanced;
       leaf-list tracefilter {
         ordered-by user;
         description "Filter policy";
         type jt:policy-algebra;
       }
       container traceoptions {
         description "Trace options";
         // uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "event" {
                 description "Event processing";
               }
               enum "flash" {
                 description "Flash processing";
               }
               enum "kernel" {
                 description "Kernel communication";
               }
               enum "indirect" {
                 description "Indirect next-hop addition, change, or deletion";
               }
               enum "task" {
                 description "Task or job processing";
               }
               enum "igp-frr" {
                 description "IGP triggered FRR events";
               }
               enum "igp-frr-extensive" {
                 description "IGP triggered FRR Extensive events";
               }
               enum "tunnel" {
                 description "Resolver dynamic tunnel events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       choice preserve-nexthop-hierarchy-choice {
         leaf preserve-nexthop-hierarchy {
           description "Preserve nexthop hierarchy when installing nexthop to forwarding plane";
           type empty;
         }
         leaf no-preserve-nexthop-hierarchy {
           description "Don't preserve nexthop hierarchy when installing nexthop to forwarding plane";
           type empty;
         }
       }
       list rib {
         key name;
         ordered-by user;
         description "Routing table resolution options";
         leaf name {
           description "Routing table name";
           type string;
         }
         // uses apply-advanced;
         leaf-list resolution-family {
           ordered-by user;
           description "Family of resultion tree";
           type string;
         }
         leaf-list resolution-ribs {
           ordered-by user;
           description "Routing tables to use for default routing table family resolution";
           type string;
         }
         leaf-list inet-resolution-ribs {
           ordered-by user;
           description "Routing tables to use for ipv4 family protocol-next-hop resolution";
           type string;
         }
         leaf-list inet6-resolution-ribs {
           ordered-by user;
           description "Routing tables to use for ipv6 family protocol-next-hop resolution";
           type string;
         }
         leaf-list iso-resolution-ribs {
           ordered-by user;
           description "Routing tables to use for iso family protocol-next-hop resolution";
           type string;
         }
         leaf-list import {
           ordered-by user;
           description "Import policy";
           type jt:policy-algebra;
         }
         leaf-list inet-import {
           ordered-by user;
           description "Import policy for IPV4 family resolution tree";
           type jt:policy-algebra;
         }
         leaf-list inet6-import {
           ordered-by user;
           description "Import policy for IPV6 family resolution tree";
           type jt:policy-algebra;
         }
         leaf-list iso-import {
           ordered-by user;
           description "Import policy for ISO family resolution tree";
           type jt:policy-algebra;
         }
         leaf-list inetcolor-import {
           ordered-by user;
           description "Import policy for INETCOLOR family resolution tree";
           type jt:policy-algebra;
         }
         leaf-list inet6color-import {
           ordered-by user;
           description "Import policy for INET6COLOR family resolution tree";
           type jt:policy-algebra;
         }
         leaf preserve-nexthop-hierarchy {
           description "Preserve nexthop hierarchy when installing nexthop to forwarding plane";
           type empty;
         }
       }
       choice prefer-recursive-primary-path-choice {
         leaf prefer-recursive-primary-path {
           description "Prefer primary path to resolve nexthop during recursive-resolution";
           type empty;
         }
         leaf no-prefer-recursive-primary-path {
           description "Don't prefer primary path to resolve nexthop during recursive-resolution";
           type empty;
         }
       }
       leaf disable-auto-resolve-on-scheme-changes {
         description "Manually trigger route re-resolution on Resolution Scheme changes.";
         type empty;
       }
       list scheme {
         key name;
         ordered-by user;
         description "Nexthop resolution fallback";
         leaf name {
           description "Name the resolution scheme";
           type string;
         }
         // uses apply-advanced;
         leaf-list resolution-ribs {
           ordered-by user;
           description "Routing tables to use for nexthop resolution, in fallback order";
           type string;
         }
         leaf mapping-community {
           description "Community on route that maps to this resolution scheme";
           type string;
         }
       }
     }
     container interface-routes {
       description "Define routing table groups for interface routes";
       // uses apply-advanced;
       container rib-group {
         description "Routing table group";
         uses rib_group_type;
       }
       list family {
         key name;
         ordered-by user;
         description "Address family";
         leaf name {
           type enumeration {
             enum "inet" {
               description "IPv4 family";
             }
             enum "inet6" {
               description "IPv6 family";
             }
           }
         }
         // uses apply-advanced;
         leaf-list import {
           ordered-by user;
           description "Import policy";
           type jt:policy-algebra;
         }
         container export {
           description "Control exportability of local routes";
           // uses apply-advanced;
           leaf point-to-point {
             description "Make point-to-point routes exportable";
             type empty;
           }
           leaf lan {
             description "Make LAN routes exportable";
             type empty;
           }
         }
       }
     }
     leaf loopback-strict-disable {
       description "Completely disable lo0 host prefix when in admin-down state";
       type empty;
     }
     container traceoptions {
       description "Global routing protocol trace options";
       // uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "regex-parse" {
               description "Trace regular-expression parsing";
             }
             enum "config-internal" {
               description "Trace configuration internals";
             }
             enum "nsr-synchronization" {
               description "Trace nonstop routing synchronization events";
             }
             enum "condition-manager" {
               description "Trace condition manager events";
             }
             enum "graceful-restart" {
               description "Trace Graceful Restart events";
             }
             enum "session" {
               description "Trace Session ID allocations/deallocations";
             }
             enum "hfrr-fsm" {
               description "Host FRR FSM events tracing";
             }
             enum "hfrr-route" {
               description "Host FRR route events tracing";
             }
             enum "statistics-id-group" {
               description "Trace Statistics ID Group operations";
             }
             enum "route-record" {
               description "Trace route-record server-side events";
             }
             enum "jvision-lsp" {
               description "Trace Jvision events and errors";
             }
             enum "dyn-nh-template" {
               description "Dynamic nexthops template events tracing";
             }
             enum "read-route" {
               description "Read route events tracing";
             }
             enum "events" {
               description "Trace-events events tracing";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container topologies {
       description "Define routing topologies";
       // uses apply-advanced;
       list family {
         key name;
         ordered-by user;
         description "Address family";
         leaf name {
           type enumeration {
             enum "inet" {
               description "IPv4 family";
             }
             enum "inet6" {
               description "IPv6 family";
             }
           }
         }
         // uses apply-advanced;
         list topology {
           key name;
           ordered-by user;
           description "Topology information";
           leaf name {
             description "Topology name";
             type string {
             }
           }
           // uses apply-advanced;
           leaf table-id {
             description "Table-id";
             type union {
               type uint16;
               type string {
                 pattern "<.*>|$.*";
               }
             }
           }
         }
       }
     }
     leaf router-id {
       description "Router identifier";
       type jt:ipv4addr;
     }
     container autonomous-system {
       description "Autonomous system number";
       // uses apply-advanced;
       leaf as-number {
         description " Autonomous system number in plain number or 'higher 16bits'.'Lower 16 bits' (asdot notation) format";
         type string {
         }
       }
       leaf loops {
         description "Maximum number of times this AS can be in an AS path";
         type union {
           type string {
             pattern "<.*>|$.*";
           }
           type int32 {
             range "1 .. 10";
           }
         }
       }
       leaf asdot-notation {
         description "Use AS-Dot notation to display true 4 byte AS numbers";
         type empty;
       }
       container independent-domain {
         presence "enable independent-domain";
         description "Independent autonomous-system domain from master instance";
         // uses apply-advanced;
         container no-attrset {
           presence "enable no-attrset";
           description "Do not tunnel ce bgp attributes across provider network";
         }
       }
     }
     container confederation {
       description "Confederation autonomous system number";
       leaf confederation-as {
         description " Autonomous system number in plain number or 'higher 16bits'.'Lower 16 bits' (asdot notation) format";
         type string {
         }
       }
       leaf-list members {
         ordered-by user;
         description " Autonomous system number in plain number or 'higher 16bits'.'Lower 16 bits' (asdot notation) format";
         type string;
       }
     }
     leaf ipv6-router-id {
       description "IPv6 router identifier";
       type string;
     }
     container graceful-restart {
       presence "enable graceful-restart";
       description "Graceful or hitless routing restart options";
       // uses apply-advanced;
       choice enable-disable {
         case case_1 {
           leaf disable {
             description "Disable graceful restart";
             type empty;
           }
         }
       }
       leaf restart-duration {
         description "Maximum time for which router is in graceful restart";
         type union {
           type string {
             pattern "<.*>|$.*";
           }
           type uint32 {
             range "120 .. 10000";
           }
         }
       }
     }
    //  container flow {
    //    description "Locally defined flow routing information";
    //    // uses apply-advanced;
    //    leaf firewall-install-disable {
    //      description "Disable installing flowspec firewall filters in dfwd ";
    //      type empty;
    //    }
    //    choice per-route-accounting-choice {
    //      leaf per-route-accounting {
    //        description "Enable traffic accounting per flowspec route";
    //        type empty;
    //      }
    //      leaf no-per-route-accounting {
    //        description "Don't enable traffic accounting per flowspec route";
    //        type empty;
    //      }
    //    }
    //    container validation {
    //      description "Flow route validation options";
    //      presence "enable validation";
    //      uses flow-validation;
    //    }
    //    container interface-group {
    //      description "Interface-group for applying flow-spec filter";
    //      uses flow-interface-group;
    //    }
    //    list route {
    //      key name;
    //      ordered-by user;
    //      description "Flow route";
    //      uses flow-route-inet;
    //    }
    //    leaf term-order {
    //      description "Term evaluation order for flow routes";
    //      type enumeration {
    //        enum "legacy" {
    //          description "Legacy term order (default)";
    //        }
    //        enum "standard" {
    //          description "RFC compliant term order";
    //        }
    //      }
    //    }
    //    leaf discard-action-for-unresolved-redir-addr {
    //      description "For action redirect IP if redirect address is unresolved install discard action filter";
    //      type empty;
    //    }
    //    list security-group {
    //      key name;
    //      ordered-by user;
    //      description "Security groups";
    //      leaf name {
    //        description "Name of the security group";
    //        type string {
    //          length "1 .. 16";
    //        }
    //      }
    //      // uses apply-advanced;
    //      list rule {
    //        key name;
    //        ordered-by user;
    //        description "Flow route";
    //        uses flow-rule-inet;
    //      }
    //    }
    //  }
     leaf no-soft-core {
       description "Disable soft assert to generate core and just log the event";
       type empty;
     }
     leaf med-igp-update-interval {
       description "Delay (in minutes) in updating MED IGP for bgp groups with 'delay-med-update' ";
       type union {
         type string {
           pattern "<.*>|$.*";
         }
         type uint32 {
           range "10 .. 600";
         }
       }
     }
    //  container bmp {
    //    presence "enable bmp";
    //    description "BGP Monitoring Protocol (BMP) configuration";
    //    // uses apply-advanced;
    //    leaf authentication-key {
    //      description "MD5 authentication key";
    //      type string {
    //        length "1 .. 126";
    //      }
    //    }
    //    leaf authentication-algorithm {
    //      description "Authentication algorithm name";
    //      default "hmac-sha-1-96";
    //      type enumeration {
    //        enum "md5" {
    //          description "Message Digest 5";
    //        }
    //        enum "hmac-sha-1-96" {
    //          description "Hash-based Message Authentication Code (SHA1) (96 bits)";
    //        }
    //        enum "aes-128-cmac-96" {
    //          description "Cipher-based Message Authentication Code (AES128) (96 bits)";
    //        }
    //        enum "ao" {
    //          description "TCP Authentication Option";
    //        }
    //      }
    //    }
    //    leaf tcpao-auth-mismatch {
    //      description "Continue without TCP-AO if any one TCP endpoint does not have TCP-AO configured";
    //      type enumeration {
    //        enum "allow-without-tcpao" {
    //          description "Allow the connection establishment without TCP-AO";
    //        }
    //      }
    //    }
    //    leaf authentication-key-chain {
    //      description "Key chain name";
    //      type string {
    //        length "1 .. 128";
    //      }
    //    }
    //    container hold-down {
    //      presence "enable hold-down";
    //      leaf hold-down-time {
    //        description "Prevent re-establishment for this time";
    //        units "seconds";
    //        type union {
    //          type string {
    //            pattern "<.*>|$.*";
    //          }
    //          type uint32 {
    //            range "30 .. 65535";
    //          }
    //        }
    //      }
    //      leaf flaps {
    //        description "Number of flaps before damping";
    //        type union {
    //          type string {
    //            pattern "<.*>|$.*";
    //          }
    //          type uint32 {
    //            range "2 .. 10";
    //          }
    //        }
    //      }
    //      leaf period {
    //        description "Time period for flaps";
    //        units "seconds";
    //        type union {
    //          type string {
    //            pattern "<.*>|$.*";
    //          }
    //          type uint32 {
    //            range "30 .. 65535";
    //          }
    //        }
    //      }
    //    }
    //    leaf initiation-message {
    //      description "User string sent with the initiation message";
    //      type string {
    //        length "1 .. 255";
    //      }
    //    }
    //    leaf local-address {
    //      description "Address of local end of BMP session";
    //      type jt:ipaddr;
    //    }
    //    leaf local-port {
    //      description "Local port for listening";
    //      type union {
    //        type string {
    //          pattern "<.*>|$.*";
    //        }
    //        type uint32 {
    //          range "1024 .. 65535";
    //        }
    //      }
    //    }
    //    leaf connection-mode {
    //      description "Specify active or passive";
    //      type enumeration {
    //        enum "active" {
    //          description "Initiate the connection";
    //        }
    //        enum "passive" {
    //          description "Listen for the connection";
    //        }
    //      }
    //    }
    //    leaf priority {
    //      description "Relative dispatch priority";
    //      type enumeration {
    //        enum "low" {
    //          description "Lowest priority";
    //        }
    //        enum "medium" {
    //          description "Medium priority";
    //        }
    //        enum "high" {
    //          description "Highest priority";
    //        }
    //      }
    //    }
    //    leaf monitor {
    //      description "Enable/Disable monitoring";
    //      type enumeration {
    //        enum "enable" {
    //          description "Enable monitoring of BGP peer(s)";
    //        }
    //        enum "disable" {
    //          description "Disable monitoring of BGP peer(s)";
    //        }
    //      }
    //    }
    //    container route-monitoring {
    //      description "Control route monitoring settings";
    //      // uses apply-advanced;
    //      leaf none {
    //        description "Do not send route monitoring messages";
    //        type empty;
    //      }
    //      container loc-rib {
    //        presence "enable loc-rib";
    //        description "Send local-rib route monitoring messages";
    //        // uses apply-advanced;
    //        leaf-list rib-filter {
    //          ordered-by user;
    //          description "Policy for RIB filtering";
    //          type jt:policy-algebra;
    //        }
    //        leaf-list route-filter {
    //          ordered-by user;
    //          description "Policy for route filtering";
    //          type jt:policy-algebra;
    //        }
    //      }
    //      container pre-policy {
    //        presence "enable pre-policy";
    //        description "Send pre policy route monitoring messages";
    //        leaf exclude-non-feasible {
    //          description "Exclude looped routes, etc";
    //          type empty;
    //        }
    //      }
    //      container post-policy {
    //        presence "enable post-policy";
    //        description "Send post policy route monitoring messages";
    //        leaf exclude-non-eligible {
    //          description "Exclude unresolved routes, etc.";
    //          type empty;
    //        }
    //      }
    //      container rib-out {
    //        presence "enable rib-out";
    //        description "Send adj-ribs-out route monitoring messages";
    //        leaf pre-policy {
    //          description "Send pre-policy adj-ribs-out route monitoring messages";
    //          type empty;
    //        }
    //        leaf post-policy {
    //          description "Send post-policy adj-ribs-out route monitoring messages";
    //          type empty;
    //        }
    //      }
    //    }
    //    leaf max-loc-rib-buffer-count {
    //      description "Max number of loc-rib outstanding buffers before blocking";
    //      type union {
    //        type string {
    //          pattern "<.*>|$.*";
    //        }
    //        type uint32 {
    //          range "1 .. 50";
    //        }
    //      }
    //    }
    //    leaf station-address {
    //      description "Address/name of monitoring station";
    //      type jt:ipaddr;
    //    }
    //    leaf routing-instance {
    //      description "Routing-instance through which BMP station is reachable";
    //      type string;
    //    }
    //    leaf station-port {
    //      description "Port of monitoring station";
    //      type union {
    //        type string {
    //          pattern "<.*>|$.*";
    //        }
    //        type uint32 {
    //          range "1 .. 65535";
    //        }
    //      }
    //    }
    //    leaf statistics-timeout {
    //      description "Statistics message timer, 15-65535, or 0 for no messages";
    //      units "seconds";
    //      type union {
    //        type string {
    //          pattern "<.*>|$.*";
    //        }
    //        type uint32 {
    //          range "0 .. 65535";
    //        }
    //      }
    //    }
    //   //  leaf bmp-server {
    //   //    description "BMP server";
    //   //    type empty;
    //   //  }
    //   //  leaf max-clients {
    //   //    description "Max number of BMP server clients";
    //   //    type union {
    //   //      type string {
    //   //        pattern "<.*>|$.*";
    //   //      }
    //   //      type uint32 {
    //   //        range "1 .. 20";
    //   //      }
    //   //    }
    //   //  }
    //   //  container traceoptions {
    //   //    description "Trace options";
    //   //    // uses apply-advanced;
    //   //    container file {
    //   //      description "Trace file options";
    //   //      leaf filename {
    //   //        description "Name of file in which to write trace information";
    //   //        type string {
    //   //          length "1 .. 1024";
    //   //        }
    //   //      }
    //   //      leaf replace {
    //   //        description "Replace trace file rather than appending to it";
    //   //        status deprecated;
    //   //        type empty;
    //   //      }
    //   //      leaf size {
    //   //        description "Maximum trace file size";
    //   //        type string;
    //   //      }
    //   //      leaf files {
    //   //        description "Maximum number of trace files";
    //   //        default "10";
    //   //        type union {
    //   //          type string {
    //   //            pattern "<.*>|$.*";
    //   //          }
    //   //          type uint32 {
    //   //            range "2 .. 1000";
    //   //          }
    //   //        }
    //   //      }
    //   //      leaf no-stamp {
    //   //        description "Do not timestamp trace file";
    //   //        status deprecated;
    //   //        type empty;
    //   //      }
    //   //      choice world-readable-choice {
    //   //        leaf world-readable {
    //   //          description "Allow any user to read the log file";
    //   //          type empty;
    //   //        }
    //   //        leaf no-world-readable {
    //   //          description "Don't allow any user to read the log file";
    //   //          type empty;
    //   //        }
    //   //      }
    //   //    }
    //   //    list flag {
    //   //      key name;
    //   //      ordered-by user;
    //   //      description "Trace flag information";
    //   //      leaf name {
    //   //        type enumeration {
    //   //          enum "packets" {
    //   //            description "Trace all messages";
    //   //          }
    //   //          enum "up" {
    //   //            description "Trace up messages";
    //   //          }
    //   //          enum "down" {
    //   //            description "Trace down messages";
    //   //          }
    //   //          enum "statistics" {
    //   //            description "Trace statistics messages";
    //   //          }
    //   //          enum "route-monitoring" {
    //   //            description "Trace route monitoring messages";
    //   //          }
    //   //          enum "event" {
    //   //            description "Trace major events, station establishment, errors, events";
    //   //          }
    //   //          enum "error" {
    //   //            description "Trace error conditions";
    //   //          }
    //   //          enum "write" {
    //   //            description "Trace writing of messages";
    //   //          }
    //   //          enum "route" {
    //   //            description "Trace routing information";
    //   //          }
    //   //          enum "normal" {
    //   //            description "Trace normal events";
    //   //          }
    //   //          enum "general" {
    //   //            description "Trace general events";
    //   //          }
    //   //          enum "state" {
    //   //            description "Trace state transitions";
    //   //          }
    //   //          enum "policy" {
    //   //            description "Trace policy processing";
    //   //          }
    //   //          enum "task" {
    //   //            description "Trace routing protocol task processing";
    //   //          }
    //   //          enum "timer" {
    //   //            description "Trace routing protocol timer processing";
    //   //          }
    //   //          enum "all" {
    //   //            description "Trace everything";
    //   //          }
    //   //        }
    //   //      }
    //   //      leaf send {
    //   //        description "Trace transmitted packets";
    //   //        type empty;
    //   //      }
    //   //      leaf receive {
    //   //        description "Trace received packets";
    //   //        type empty;
    //   //      }
    //   //      leaf detail {
    //   //        description "Trace detailed information";
    //   //        type empty;
    //   //      }
    //   //      leaf disable {
    //   //        description "Disable this trace flag";
    //   //        type empty;
    //   //      }
    //   //    }
    //   //  }
    //   //  container bmp-loc-rib-add-path {
    //   //    description "Advertise multiple paths for a prefix";
    //   //    presence "enable bmp-loc-rib-add-path";
    //   //    uses bmp-loc-rib-apath-options;
    //   //  }
    //   //  container kafka {
    //   //    presence "enable kafka";
    //   //    description "Kafka broker configuration";
    //   //    // uses apply-advanced;
    //   //    leaf broker-address {
    //   //      description "Kafka broker address";
    //   //      type string;
    //   //    }
    //   //    container producer {
    //   //      presence "enable producer";
    //   //      description "Producer of a topic";
    //   //      // uses apply-advanced;
    //   //      leaf topic-metadata {
    //   //        description "Metadata string for all messages";
    //   //        type string {
    //   //          length "1 .. 255";
    //   //        }
    //   //      }
    //   //    }
    //   //  }
    //   //  list station {
    //   //    key name;
    //   //    description "Define a BMP station";
    //   //    leaf name {
    //   //      description "Station name";
    //   //      type string;
    //   //    }
    //   //    // uses apply-advanced;
    //   //    leaf authentication-key {
    //   //      description "MD5 authentication key";
    //   //      type string {
    //   //        length "1 .. 126";
    //   //      }
    //   //    }
    //   //    leaf authentication-algorithm {
    //   //      description "Authentication algorithm name";
    //   //      type enumeration {
    //   //        enum "md5" {
    //   //          description "Message Digest 5";
    //   //        }
    //   //        enum "hmac-sha-1-96" {
    //   //          description "Hash-based Message Authentication Code (SHA1) (96 bits)";
    //   //        }
    //   //        enum "aes-128-cmac-96" {
    //   //          description "Cipher-based Message Authentication Code (AES128) (96 bits)";
    //   //        }
    //   //        enum "ao" {
    //   //          description "TCP Authentication Option";
    //   //        }
    //   //      }
    //   //    }
    //   //    leaf tcpao-auth-mismatch {
    //   //      description "Continue without TCP-AO if any one TCP endpoint does not have TCP-AO configured";
    //   //      type enumeration {
    //   //        enum "allow-without-tcpao" {
    //   //          description "Allow the connection establishment without TCP-AO";
    //   //        }
    //   //      }
    //   //    }
    //   //    leaf authentication-key-chain {
    //   //      description "Key chain name";
    //   //      type string {
    //   //        length "1 .. 128";
    //   //      }
    //   //    }
    //   //    container hold-down {
    //   //      presence "enable hold-down";
    //   //      leaf hold-down-time {
    //   //        description "Prevent re-establishment for this time";
    //   //        units "seconds";
    //   //        type union {
    //   //          type string {
    //   //            pattern "<.*>|$.*";
    //   //          }
    //   //          type uint32 {
    //   //            range "30 .. 65535";
    //   //          }
    //   //        }
    //   //      }
    //   //      leaf flaps {
    //   //        description "Number of flaps before damping";
    //   //        type union {
    //   //          type string {
    //   //            pattern "<.*>|$.*";
    //   //          }
    //   //          type uint32 {
    //   //            range "2 .. 10";
    //   //          }
    //   //        }
    //   //      }
    //   //      leaf period {
    //   //        description "Time period for flaps";
    //   //        units "seconds";
    //   //        type union {
    //   //          type string {
    //   //            pattern "<.*>|$.*";
    //   //          }
    //   //          type uint32 {
    //   //            range "30 .. 65535";
    //   //          }
    //   //        }
    //   //      }
    //   //    }
    //   //    leaf initiation-message {
    //   //      description "User string sent with the initiation message";
    //   //      type string {
    //   //        length "1 .. 255";
    //   //      }
    //   //    }
    //   //    leaf local-address {
    //   //      description "Address of local end of BMP session";
    //   //      type jt:ipaddr;
    //   //    }
    //   //    leaf local-port {
    //   //      description "Local port for listening";
    //   //      type union {
    //   //        type string {
    //   //          pattern "<.*>|$.*";
    //   //        }
    //   //        type uint32 {
    //   //          range "1024 .. 65535";
    //   //        }
    //   //      }
    //   //    }
    //   //    leaf connection-mode {
    //   //      description "Specify active or passive";
    //   //      type enumeration {
    //   //        enum "active" {
    //   //          description "Initiate the connection";
    //   //        }
    //   //        enum "passive" {
    //   //          description "Listen for the connection";
    //   //        }
    //   //      }
    //   //    }
    //   //    leaf priority {
    //   //      description "Relative dispatch priority";
    //   //      type enumeration {
    //   //        enum "low" {
    //   //          description "Lowest priority";
    //   //        }
    //   //        enum "medium" {
    //   //          description "Medium priority";
    //   //        }
    //   //        enum "high" {
    //   //          description "Highest priority";
    //   //        }
    //   //      }
    //   //    }
    //   //    leaf monitor {
    //   //      description "Enable/Disable monitoring";
    //   //      type enumeration {
    //   //        enum "enable" {
    //   //          description "Enable monitoring of BGP peer(s)";
    //   //        }
    //   //        enum "disable" {
    //   //          description "Disable monitoring of BGP peer(s)";
    //   //        }
    //   //      }
    //   //    }
    //   //    container route-monitoring {
    //   //      description "Control route monitoring settings";
    //   //      // uses apply-advanced;
    //   //      leaf none {
    //   //        description "Do not send route monitoring messages";
    //   //        type empty;
    //   //      }
    //   //      container loc-rib {
    //   //        presence "enable loc-rib";
    //   //        description "Send local-rib route monitoring messages";
    //   //        // uses apply-advanced;
    //   //        leaf-list rib-filter {
    //   //          ordered-by user;
    //   //          description "Policy for RIB filtering";
    //   //          type jt:policy-algebra;
    //   //        }
    //   //        leaf-list route-filter {
    //   //          ordered-by user;
    //   //          description "Policy for route filtering";
    //   //          type jt:policy-algebra;
    //   //        }
    //   //      }
    //   //      container pre-policy {
    //   //        presence "enable pre-policy";
    //   //        description "Send pre policy route monitoring messages";
    //   //        leaf exclude-non-feasible {
    //   //          description "Exclude looped routes, etc";
    //   //          type empty;
    //   //        }
    //   //      }
    //   //      container post-policy {
    //   //        presence "enable post-policy";
    //   //        description "Send post policy route monitoring messages";
    //   //        leaf exclude-non-eligible {
    //   //          description "Exclude unresolved routes, etc.";
    //   //          type empty;
    //   //        }
    //   //      }
    //   //      container rib-out {
    //   //        presence "enable rib-out";
    //   //        description "Send adj-ribs-out route monitoring messages";
    //   //        leaf pre-policy {
    //   //          description "Send pre-policy adj-ribs-out route monitoring messages";
    //   //          type empty;
    //   //        }
    //   //        leaf post-policy {
    //   //          description "Send post-policy adj-ribs-out route monitoring messages";
    //   //          type empty;
    //   //        }
    //   //      }
    //   //    }
    //   //    leaf max-loc-rib-buffer-count {
    //   //      description "Max number of loc-rib outstanding buffers before blocking";
    //   //      type union {
    //   //        type string {
    //   //          pattern "<.*>|$.*";
    //   //        }
    //   //        type uint32 {
    //   //          range "1 .. 50";
    //   //        }
    //   //      }
    //   //    }
    //   //    leaf station-address {
    //   //      description "Address/name of monitoring station";
    //   //      type jt:ipaddr;
    //   //    }
    //   //    leaf routing-instance {
    //   //      description "Routing-instance through which BMP station is reachable";
    //   //      type string;
    //   //    }
    //   //    leaf station-port {
    //   //      description "Port of monitoring station";
    //   //      type union {
    //   //        type string {
    //   //          pattern "<.*>|$.*";
    //   //        }
    //   //        type uint32 {
    //   //          range "1 .. 65535";
    //   //        }
    //   //      }
    //   //    }
    //   //    leaf statistics-timeout {
    //   //      description "Statistics message timer, 15-65535, or 0 for no messages";
    //   //      units "seconds";
    //   //      type union {
    //   //        type string {
    //   //          pattern "<.*>|$.*";
    //   //        }
    //   //        type uint32 {
    //   //          range "0 .. 65535";
    //   //        }
    //   //      }
    //   //    }
    //   //    leaf bmp-server {
    //   //      description "BMP server";
    //   //      type empty;
    //   //    }
    //   //    leaf max-clients {
    //   //      description "Max number of BMP server clients";
    //   //      type union {
    //   //        type string {
    //   //          pattern "<.*>|$.*";
    //   //        }
    //   //        type uint32 {
    //   //          range "1 .. 20";
    //   //        }
    //   //      }
    //   //    }
    //   //    container traceoptions {
    //   //      description "Trace options";
    //   //      // uses apply-advanced;
    //   //      container file {
    //   //        description "Trace file options";
    //   //        leaf filename {
    //   //          description "Name of file in which to write trace information";
    //   //          type string {
    //   //            length "1 .. 1024";
    //   //          }
    //   //        }
    //   //        leaf replace {
    //   //          description "Replace trace file rather than appending to it";
    //   //          status deprecated;
    //   //          type empty;
    //   //        }
    //   //        leaf size {
    //   //          description "Maximum trace file size";
    //   //          type string;
    //   //        }
    //   //        leaf files {
    //   //          description "Maximum number of trace files";
    //   //          default "10";
    //   //          type union {
    //   //            type string {
    //   //              pattern "<.*>|$.*";
    //   //            }
    //   //            type uint32 {
    //   //              range "2 .. 1000";
    //   //            }
    //   //          }
    //   //        }
    //   //        leaf no-stamp {
    //   //          description "Do not timestamp trace file";
    //   //          status deprecated;
    //   //          type empty;
    //   //        }
    //   //        choice world-readable-choice {
    //   //          leaf world-readable {
    //   //            description "Allow any user to read the log file";
    //   //            type empty;
    //   //          }
    //   //          leaf no-world-readable {
    //   //            description "Don't allow any user to read the log file";
    //   //            type empty;
    //   //          }
    //   //        }
    //   //      }
    //   //      list flag {
    //   //        key name;
    //   //        ordered-by user;
    //   //        description "Trace flag information";
    //   //        leaf name {
    //   //          type enumeration {
    //   //            enum "packets" {
    //   //              description "Trace all messages";
    //   //            }
    //   //            enum "up" {
    //   //              description "Trace up messages";
    //   //            }
    //   //            enum "down" {
    //   //              description "Trace down messages";
    //   //            }
    //   //            enum "statistics" {
    //   //              description "Trace statistics messages";
    //   //            }
    //   //            enum "route-monitoring" {
    //   //              description "Trace route monitoring messages";
    //   //            }
    //   //            enum "event" {
    //   //              description "Trace major events, station establishment, errors, events";
    //   //            }
    //   //            enum "error" {
    //   //              description "Trace error conditions";
    //   //            }
    //   //            enum "write" {
    //   //              description "Trace writing of messages";
    //   //            }
    //   //            enum "route" {
    //   //              description "Trace routing information";
    //   //            }
    //   //            enum "normal" {
    //   //              description "Trace normal events";
    //   //            }
    //   //            enum "general" {
    //   //              description "Trace general events";
    //   //            }
    //   //            enum "state" {
    //   //              description "Trace state transitions";
    //   //            }
    //   //            enum "policy" {
    //   //              description "Trace policy processing";
    //   //            }
    //   //            enum "task" {
    //   //              description "Trace routing protocol task processing";
    //   //            }
    //   //            enum "timer" {
    //   //              description "Trace routing protocol timer processing";
    //   //            }
    //   //            enum "all" {
    //   //              description "Trace everything";
    //   //            }
    //   //          }
    //   //        }
    //   //        leaf send {
    //   //          description "Trace transmitted packets";
    //   //          type empty;
    //   //        }
    //   //        leaf receive {
    //   //          description "Trace received packets";
    //   //          type empty;
    //   //        }
    //   //        leaf detail {
    //   //          description "Trace detailed information";
    //   //          type empty;
    //   //        }
    //   //        leaf disable {
    //   //          description "Disable this trace flag";
    //   //          type empty;
    //   //        }
    //   //      }
    //   //    }
    //   //    container bmp-loc-rib-add-path {
    //   //      description "Advertise multiple paths for a prefix";
    //   //      presence "enable bmp-loc-rib-add-path";
    //   //      uses bmp-loc-rib-apath-options;
    //   //    }
    //   //    container kafka {
    //   //      presence "enable kafka";
    //   //      description "Kafka broker configuration";
    //   //      // uses apply-advanced;
    //   //      leaf broker-address {
    //   //        description "Kafka broker address";
    //   //        type string;
    //   //      }
    //   //      container producer {
    //   //        presence "enable producer";
    //   //        description "Producer of a topic";
    //   //        // uses apply-advanced;
    //   //        leaf topic-metadata {
    //   //          description "Metadata string for all messages";
    //   //          type string {
    //   //            length "1 .. 255";
    //   //          }
    //   //        }
    //   //      }
    //   //    }
    //   //  }
    //  }
    //  leaf bgp-orf-cisco-mode {
    //    description "Using BGP ORF capability code 130 and Prefix ORF type 128";
    //    type empty;
    //  }
    //  leaf highwatermark-log-interval {
    //    description "High watermark log interval (default 30 seconds)";
    //    units "seconds";
    //    type union {
    //      type string {
    //        pattern "<.*>|$.*";
    //      }
    //      type uint32 {
    //        range "5 .. 1200";
    //      }
    //    }
    //  }
    //  leaf time-averaged-watermark-interval {
    //    description "For calculating average watermark";
    //    units "days";
    //    type union {
    //      type string {
    //        pattern "<.*>|$.*";
    //      }
    //      type uint32 {
    //        range "1 .. 15";
    //      }
    //    }
    //  }
    //  container ppm {
    //    presence "enable ppm";
    //    description "Set periodic packet management properties";
    //    // uses apply-advanced;
    //    leaf delegate-processing {
    //      description "Enable distribution of PPM sessions";
    //      status deprecated;
    //      type empty;
    //    }
    //    leaf no-delegate-processing {
    //      description "Disable PPM sessions distribution";
    //      type empty;
    //    }
    //    leaf bfd-redirect-rule-delay {
    //      description "Time to wait after installing redirect rule for BFD sessions";
    //      type union {
    //        type string {
    //          pattern "<.*>|$.*";
    //        }
    //        type uint32 {
    //          range "1 .. 120";
    //        }
    //      }
    //    }
    //    leaf redistribution-timer {
    //      description "Time to wait after switchover before starting timers";
    //      type union {
    //        type string {
    //          pattern "<.*>|$.*";
    //        }
    //        type uint32 {
    //          range "1 .. 120";
    //        }
    //      }
    //    }
    //  }
    //  leaf no-bfd-triggered-local-repair {
    //    description "Disable bfd triggered local repair";
    //    type empty;
    //  }
    //  leaf enable-sensors {
    //    description "Enable Sensor for MX/PTX/QFX/EX/ACX";
    //    type empty;
    //  }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
         }
         enum "192" {
           description "Maximum 192 ECMP routes";
         }
         enum "224" {
           description "Maximum 224 ECMP routes";
         }
         enum "256" {
           description "Maximum 256 ECMP routes";
         }
         enum "288" {
           description "Maximum 288 ECMP routes";
         }
         enum "320" {
           description "Maximum 320 ECMP routes";
         }
         enum "352" {
           description "Maximum 352 ECMP routes";
         }
         enum "384" {
           description "Maximum 384 ECMP routes";
         }
         enum "416" {
           description "Maximum 416 ECMP routes";
         }
         enum "448" {
           description "Maximum 448 ECMP routes";
         }
         enum "480" {
           description "Maximum 480 ECMP routes";
         }
         enum "512" {
           description "Maximum 512 ECMP routes";
         }
       }
     }
     container static {
       description "Static routes";
       // uses apply-advanced;
       leaf rib-group {
         description "Routing table group";
         type string;
       }
       container defaults {
         description "Global route options";
         // uses apply-advanced;
         choice retain-choice {
           leaf retain {
             description "Always keep route in forwarding table";
             type empty;
           }
           leaf no-retain {
             description "Don't always keep route in forwarding table";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         leaf explicit-null {
           description "Allows service label to be popped and will lookup nexthop-table inet6.0";
           type empty;
         }
         choice longest-match-choice {
           leaf longest-match {
             description "Always use longest prefix match to resolve next hops";
             type empty;
           }
           leaf no-longest-match {
             description "Don't always use longest prefix match to resolve next hops";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           // uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
       list route {
         key name;
         description "Static route";
         leaf name {
           type jt:ipprefix;
         }
         // uses apply-advanced;
         leaf priority {
           description "Static route priority high/medium/low";
           type enumeration {
             enum "medium" {
               description "Static route medium priority";
             }
             enum "low" {
               description "Static route low priority";
             }
             enum "high" {
               description "Static route high priority";
             }
           }
         }
         choice next_hop {
           case case_1 {
             leaf-list next-hop {
               ordered-by user;
               description "Next hop to destination";
               type union {
                 type jt:ipaddr-or-interface;
                 type string {
                   pattern "<.*>|$.*";
                 }
               }
             }
           }
           case case_2 {
             leaf reject {
               description "Drop packets to destination; send ICMP unreachables";
               type empty;
             }
           }
           case case_3 {
             leaf discard {
               description "Drop packets to destination; send no ICMP unreachables";
               type empty;
             }
           }
           case case_4 {
             leaf receive {
               description "Install a receive route for the destination";
               type empty;
             }
           }
           case case_5 {
             leaf next-table {
               description "Next hop to another table";
               type string {
               }
             }
           }
         }
         leaf description {
           description "Static route description";
           type string {
           }
         }
        //  list qualified-next-hop {
        //    key name;
        //    ordered-by user;
        //    description "Next hop with qualifiers";
        //    uses qualified_nh_obj;
        //  }
        //  leaf backup-pe-group {
        //    description "Multicast source redundancy group";
        //    type string;
        //  }
        //  container bfd-liveness-detection {
        //    description "Bidirectional Forwarding Detection (BFD) options";
        //    // uses apply-advanced;
        //    leaf version {
        //      description "BFD protocol version number";
        //      default "automatic";
        //      type enumeration {
        //        enum "0" {
        //          description "BFD version 0 (deprecated)";
        //        }
        //        enum "1" {
        //          description "BFD version 1";
        //        }
        //        enum "automatic" {
        //          description "Choose BFD version automatically";
        //        }
        //      }
        //    }
        //    leaf minimum-interval {
        //      description "Minimum transmit and receive interval";
        //      units "milliseconds";
        //      type union {
        //        type string {
        //          pattern "<.*>|$.*";
        //        }
        //        type uint32 {
        //          range "1 .. 255000";
        //        }
        //      }
        //    }
        //    leaf minimum-transmit-interval {
        //      description "Minimum transmit interval";
        //      status deprecated;
        //      units "milliseconds";
        //      type union {
        //        type string {
        //          pattern "<.*>|$.*";
        //        }
        //        type uint32 {
        //          range "1 .. 255000";
        //        }
        //      }
        //    }
        //    leaf minimum-receive-interval {
        //      description "Minimum receive interval";
        //      units "milliseconds";
        //      type union {
        //        type string {
        //          pattern "<.*>|$.*";
        //        }
        //        type uint32 {
        //          range "1 .. 255000";
        //        }
        //      }
        //    }
        //    leaf multiplier {
        //      description "Detection time multiplier";
        //      default "3";
        //      type union {
        //        type string {
        //          pattern "<.*>|$.*";
        //        }
        //        type uint32 {
        //          range "1 .. 255";
        //        }
        //      }
        //    }
        //    leaf inline-disable {
        //      description "Disable inline mode for this BFD session";
        //      type empty;
        //    }
        //    leaf pdu-size {
        //      description "BFD transport protocol payload size";
        //      default "24";
        //      type union {
        //        type string {
        //          pattern "<.*>|$.*";
        //        }
        //        type uint32 {
        //          range "24 .. 9000";
        //        }
        //      }
        //    }
        //    choice adaptation-choice {
        //      case case_1 {
        //        leaf no-adaptation {
        //          description "Disable adaptation";
        //          type empty;
        //        }
        //      }
        //    }
        //    container transmit-interval {
        //      description "Transmit-interval options";
        //      // uses apply-advanced;
        //      leaf minimum-interval {
        //        description "Minimum transmit interval";
        //        units "milliseconds";
        //        type union {
        //          type string {
        //            pattern "<.*>|$.*";
        //          }
        //          type uint32 {
        //            range "1 .. 255000";
        //          }
        //        }
        //      }
        //      leaf threshold {
        //        description "High transmit interval triggering a trap";
        //        units "milliseconds";
        //        type union {
        //          type uint32;
        //          type string {
        //            pattern "<.*>|$.*";
        //          }
        //        }
        //      }
        //    }
        //    container detection-time {
        //      description "Detection-time options";
        //      // uses apply-advanced;
        //      leaf threshold {
        //        description "High detection-time triggering a trap";
        //        units "milliseconds";
        //        type union {
        //          type uint32;
        //          type string {
        //            pattern "<.*>|$.*";
        //          }
        //        }
        //      }
        //    }
        //    container authentication {
        //      description "Authentication options";
        //      // uses apply-advanced;
        //      leaf key-chain {
        //        description "Key chain name";
        //        type string;
        //      }
        //      leaf algorithm {
        //        description "Algorithm name";
        //        type enumeration {
        //          enum "simple-password" {
        //            description "Simple password";
        //          }
        //          enum "keyed-md5" {
        //            description "Keyed message Digest 5";
        //          }
        //          enum "meticulous-keyed-md5" {
        //            description "Meticulous keyed message Digest 5";
        //          }
        //          enum "keyed-sha-1" {
        //            description "Keyed secure hash algorithm (SHA1) ";
        //          }
        //          enum "meticulous-keyed-sha-1" {
        //            description "Meticulous keyed secure hash algorithm (SHA1) ";
        //          }
        //        }
        //      }
        //      leaf loose-check {
        //        description "Verify authentication only if authentication is negotiated";
        //        type empty;
        //      }
        //    }
        //    container echo {
        //      description "Echo mode parameters";
        //      // uses apply-advanced;
        //      leaf minimum-interval {
        //        description "Minimum transmit and receive interval";
        //        units "milliseconds";
        //        type union {
        //          type string {
        //            pattern "<.*>|$.*";
        //          }
        //          type uint32 {
        //            range "100 .. 255000";
        //          }
        //        }
        //      }
        //    }
        //    container echo-lite {
        //      description "Echo-lite more parameters";
        //      // uses apply-advanced;
        //      leaf minimum-interval {
        //        description "Minimum transmit and receive interval";
        //        units "milliseconds";
        //        type union {
        //          type string {
        //            pattern "<.*>|$.*";
        //          }
        //          type uint32 {
        //            range "100 .. 255000";
        //          }
        //        }
        //      }
        //    }
        //    leaf neighbor {
        //      description "BFD neighbor address";
        //      type jt:ipaddr;
        //    }
        //    leaf local-address {
        //      description "BFD local address (for multihop only)";
        //      type jt:ipaddr;
        //    }
        //    leaf holddown-interval {
        //      description "Time to hold the session-UP notification to the client";
        //      units "milliseconds";
        //      type union {
        //        type string {
        //          pattern "<.*>|$.*";
        //        }
        //        type uint32 {
        //          range "0 .. 255000";
        //        }
        //      }
        //    }
        //    leaf minimum-receive-ttl {
        //      description "Minimum receive TTL below which to drop";
        //      type union {
        //        type string {
        //          pattern "<.*>|$.*";
        //        }
        //        type uint8 {
        //          range "1 .. 255";
        //        }
        //      }
        //    }
        //  }
        //  choice retain-choice {
        //    leaf retain {
        //      description "Always keep route in forwarding table";
        //      type empty;
        //    }
        //    leaf no-retain {
        //      description "Don't always keep route in forwarding table";
        //      type empty;
        //    }
        //  }
        //  choice install-choice {
        //    leaf install {
        //      description "Install route into forwarding table";
        //      type empty;
        //    }
        //    leaf no-install {
        //      description "Don't install route into forwarding table";
        //      type empty;
        //    }
        //  }
        //  choice readvertise-choice {
        //    leaf readvertise {
        //      description "Mark route as eligible to be readvertised";
        //      type empty;
        //    }
        //    leaf no-readvertise {
        //      description "Don't mark route as eligible to be readvertised";
        //      type empty;
        //    }
        //  }
        //  choice resolve-choice {
        //    leaf resolve {
        //      description "Allow resolution of indirectly connected next hops";
        //      type empty;
        //    }
        //    leaf no-resolve {
        //      description "Don't allow resolution of indirectly connected next hops";
        //      type empty;
        //    }
        //  }
        //  leaf explicit-null {
        //    description "Allows service label to be popped and will lookup nexthop-table inet6.0";
        //    type empty;
        //  }
        //  choice longest-match-choice {
        //    leaf longest-match {
        //      description "Always use longest prefix match to resolve next hops";
        //      type empty;
        //    }
        //    leaf no-longest-match {
        //      description "Don't always use longest prefix match to resolve next hops";
        //      type empty;
        //    }
        //  }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           // uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
         list lsp-next-hop {
           key name;
           ordered-by user;
           description "LSP next hop";
           uses lsp_nh_obj;
         }
        //  list p2mp-lsp-next-hop {
        //    key name;
        //    ordered-by user;
        //    description "Point-to-multipoint LSP next hop";
        //    max-elements 1;
        //    uses lsp_nh_obj;
        //  }
        //  container spring-te-lsp-next-hop {
        //    description "SPRING-TE LSP next hop";
        //    uses springte_lsp_nh_obj;
        //  }
        //  container p2mp-ldp-next-hop {
        //    description "Point-to-multipoint LDP LSP next hop";
        //    uses p2mp_ldp_lsp_nh_obj;
        //  }
         list static-lsp-next-hop {
           key name;
           ordered-by user;
           description "Static LSP next hop";
           uses lsp_nh_obj;
         }
       }
       leaf protocol-instance-name {
         description "Name of protocol instance under routing instance";
         type string;
       }
       container static-route {
         description "Static route Status";
         leaf bfd-admin-down {
           description "Static route State on BFD ADMIN DOWN";
           type enumeration {
             enum "active" {
               description "Static route will be inactive on bfd-admin-down";
             }
             enum "passive" {
               description "Static route will remain active on bfd-admin-down";
             }
           }
         }
       }
      //  list iso-route {
      //    key name;
      //    ordered-by user;
      //    description "ISO family static route";
      //    leaf name {
      //      type jt:isoprefix;
      //    }
      //    // uses apply-advanced;
      //    leaf priority {
      //      description "Static route priority high/medium/low";
      //      type enumeration {
      //        enum "medium" {
      //          description "Static route medium priority";
      //        }
      //        enum "low" {
      //          description "Static route low priority";
      //        }
      //        enum "high" {
      //          description "Static route high priority";
      //        }
      //      }
      //    }
      //    choice next_hop {
      //      case case_1 {
      //        leaf-list next-hop {
      //          ordered-by user;
      //          description "Next hop to destination";
      //          type union {
      //            type jt:ipaddr-or-interface;
      //            type string {
      //              pattern "<.*>|$.*";
      //            }
      //          }
      //        }
      //      }
      //      case case_2 {
      //        leaf reject {
      //          description "Drop packets to destination; send ICMP unreachables";
      //          type empty;
      //        }
      //      }
      //      case case_3 {
      //        leaf discard {
      //          description "Drop packets to destination; send no ICMP unreachables";
      //          type empty;
      //        }
      //      }
      //      case case_4 {
      //        leaf receive {
      //          description "Install a receive route for the destination";
      //          type empty;
      //        }
      //      }
      //      case case_5 {
      //        leaf next-table {
      //          description "Next hop to another table";
      //          type string {
      //          }
      //        }
      //      }
      //    }
      //    leaf description {
      //      description "Static route description";
      //      type string {
      //      }
      //    }
      //   //  list qualified-next-hop {
      //   //    key name;
      //   //    ordered-by user;
      //   //    description "Next hop with qualifiers";
      //   //    uses qualified_nh_obj;
      //   //  }
      //   //  leaf backup-pe-group {
      //   //    description "Multicast source redundancy group";
      //   //    type string;
      //   //  }
      //   //  container bfd-liveness-detection {
      //   //    description "Bidirectional Forwarding Detection (BFD) options";
      //   //    // uses apply-advanced;
      //   //    leaf version {
      //   //      description "BFD protocol version number";
      //   //      default "automatic";
      //   //      type enumeration {
      //   //        enum "0" {
      //   //          description "BFD version 0 (deprecated)";
      //   //        }
      //   //        enum "1" {
      //   //          description "BFD version 1";
      //   //        }
      //   //        enum "automatic" {
      //   //          description "Choose BFD version automatically";
      //   //        }
      //   //      }
      //   //    }
      //   //    leaf minimum-interval {
      //   //      description "Minimum transmit and receive interval";
      //   //      units "milliseconds";
      //   //      type union {
      //   //        type string {
      //   //          pattern "<.*>|$.*";
      //   //        }
      //   //        type uint32 {
      //   //          range "1 .. 255000";
      //   //        }
      //   //      }
      //   //    }
      //   //    leaf minimum-transmit-interval {
      //   //      description "Minimum transmit interval";
      //   //      status deprecated;
      //   //      units "milliseconds";
      //   //      type union {
      //   //        type string {
      //   //          pattern "<.*>|$.*";
      //   //        }
      //   //        type uint32 {
      //   //          range "1 .. 255000";
      //   //        }
      //   //      }
      //   //    }
      //   //    leaf minimum-receive-interval {
      //   //      description "Minimum receive interval";
      //   //      units "milliseconds";
      //   //      type union {
      //   //        type string {
      //   //          pattern "<.*>|$.*";
      //   //        }
      //   //        type uint32 {
      //   //          range "1 .. 255000";
      //   //        }
      //   //      }
      //   //    }
      //   //    leaf multiplier {
      //   //      description "Detection time multiplier";
      //   //      default "3";
      //   //      type union {
      //   //        type string {
      //   //          pattern "<.*>|$.*";
      //   //        }
      //   //        type uint32 {
      //   //          range "1 .. 255";
      //   //        }
      //   //      }
      //   //    }
      //   //    leaf inline-disable {
      //   //      description "Disable inline mode for this BFD session";
      //   //      type empty;
      //   //    }
      //   //    leaf pdu-size {
      //   //      description "BFD transport protocol payload size";
      //   //      default "24";
      //   //      type union {
      //   //        type string {
      //   //          pattern "<.*>|$.*";
      //   //        }
      //   //        type uint32 {
      //   //          range "24 .. 9000";
      //   //        }
      //   //      }
      //   //    }
      //   //    choice adaptation-choice {
      //   //      case case_1 {
      //   //        leaf no-adaptation {
      //   //          description "Disable adaptation";
      //   //          type empty;
      //   //        }
      //   //      }
      //   //    }
      //   //    container transmit-interval {
      //   //      description "Transmit-interval options";
      //   //      // uses apply-advanced;
      //   //      leaf minimum-interval {
      //   //        description "Minimum transmit interval";
      //   //        units "milliseconds";
      //   //        type union {
      //   //          type string {
      //   //            pattern "<.*>|$.*";
      //   //          }
      //   //          type uint32 {
      //   //            range "1 .. 255000";
      //   //          }
      //   //        }
      //   //      }
      //   //      leaf threshold {
      //   //        description "High transmit interval triggering a trap";
      //   //        units "milliseconds";
      //   //        type union {
      //   //          type uint32;
      //   //          type string {
      //   //            pattern "<.*>|$.*";
      //   //          }
      //   //        }
      //   //      }
      //   //    }
      //   //    container detection-time {
      //   //      description "Detection-time options";
      //   //      // uses apply-advanced;
      //   //      leaf threshold {
      //   //        description "High detection-time triggering a trap";
      //   //        units "milliseconds";
      //   //        type union {
      //   //          type uint32;
      //   //          type string {
      //   //            pattern "<.*>|$.*";
      //   //          }
      //   //        }
      //   //      }
      //   //    }
      //   //    container authentication {
      //   //      description "Authentication options";
      //   //      // uses apply-advanced;
      //   //      leaf key-chain {
      //   //        description "Key chain name";
      //   //        type string;
      //   //      }
      //   //      leaf algorithm {
      //   //        description "Algorithm name";
      //   //        type enumeration {
      //   //          enum "simple-password" {
      //   //            description "Simple password";
      //   //          }
      //   //          enum "keyed-md5" {
      //   //            description "Keyed message Digest 5";
      //   //          }
      //   //          enum "meticulous-keyed-md5" {
      //   //            description "Meticulous keyed message Digest 5";
      //   //          }
      //   //          enum "keyed-sha-1" {
      //   //            description "Keyed secure hash algorithm (SHA1) ";
      //   //          }
      //   //          enum "meticulous-keyed-sha-1" {
      //   //            description "Meticulous keyed secure hash algorithm (SHA1) ";
      //   //          }
      //   //        }
      //   //      }
      //   //      leaf loose-check {
      //   //        description "Verify authentication only if authentication is negotiated";
      //   //        type empty;
      //   //      }
      //   //    }
      //   //    container echo {
      //   //      description "Echo mode parameters";
      //   //      // uses apply-advanced;
      //   //      leaf minimum-interval {
      //   //        description "Minimum transmit and receive interval";
      //   //        units "milliseconds";
      //   //        type union {
      //   //          type string {
      //   //            pattern "<.*>|$.*";
      //   //          }
      //   //          type uint32 {
      //   //            range "100 .. 255000";
      //   //          }
      //   //        }
      //   //      }
      //   //    }
      //   //    container echo-lite {
      //   //      description "Echo-lite more parameters";
      //   //      // uses apply-advanced;
      //   //      leaf minimum-interval {
      //   //        description "Minimum transmit and receive interval";
      //   //        units "milliseconds";
      //   //        type union {
      //   //          type string {
      //   //            pattern "<.*>|$.*";
      //   //          }
      //   //          type uint32 {
      //   //            range "100 .. 255000";
      //   //          }
      //   //        }
      //   //      }
      //   //    }
      //   //    leaf neighbor {
      //   //      description "BFD neighbor address";
      //   //      type jt:ipaddr;
      //   //    }
      //   //    leaf local-address {
      //   //      description "BFD local address (for multihop only)";
      //   //      type jt:ipaddr;
      //   //    }
      //   //    leaf holddown-interval {
      //   //      description "Time to hold the session-UP notification to the client";
      //   //      units "milliseconds";
      //   //      type union {
      //   //        type string {
      //   //          pattern "<.*>|$.*";
      //   //        }
      //   //        type uint32 {
      //   //          range "0 .. 255000";
      //   //        }
      //   //      }
      //   //    }
      //   //    leaf minimum-receive-ttl {
      //   //      description "Minimum receive TTL below which to drop";
      //   //      type union {
      //   //        type string {
      //   //          pattern "<.*>|$.*";
      //   //        }
      //   //        type uint8 {
      //   //          range "1 .. 255";
      //   //        }
      //   //      }
      //   //    }
      //   //  }
      //   //  choice retain-choice {
      //   //    leaf retain {
      //   //      description "Always keep route in forwarding table";
      //   //      type empty;
      //   //    }
      //   //    leaf no-retain {
      //   //      description "Don't always keep route in forwarding table";
      //   //      type empty;
      //   //    }
      //   //  }
      //   //  choice install-choice {
      //   //    leaf install {
      //   //      description "Install route into forwarding table";
      //   //      type empty;
      //   //    }
      //   //    leaf no-install {
      //   //      description "Don't install route into forwarding table";
      //   //      type empty;
      //   //    }
      //   //  }
      //   //  choice readvertise-choice {
      //   //    leaf readvertise {
      //   //      description "Mark route as eligible to be readvertised";
      //   //      type empty;
      //   //    }
      //   //    leaf no-readvertise {
      //   //      description "Don't mark route as eligible to be readvertised";
      //   //      type empty;
      //   //    }
      //   //  }
      //   //  choice resolve-choice {
      //   //    leaf resolve {
      //   //      description "Allow resolution of indirectly connected next hops";
      //   //      type empty;
      //   //    }
      //   //    leaf no-resolve {
      //   //      description "Don't allow resolution of indirectly connected next hops";
      //   //      type empty;
      //   //    }
      //   //  }
      //   //  leaf explicit-null {
      //   //    description "Allows service label to be popped and will lookup nexthop-table inet6.0";
      //   //    type empty;
      //   //  }
      //   //  choice longest-match-choice {
      //   //    leaf longest-match {
      //   //      description "Always use longest prefix match to resolve next hops";
      //   //      type empty;
      //   //    }
      //   //    leaf no-longest-match {
      //   //      description "Don't always use longest prefix match to resolve next hops";
      //   //      type empty;
      //   //    }
      //   //  }
      //   //  choice passive_flag {
      //   //    case case_1 {
      //   //      leaf active {
      //   //        description "Remove inactive route from forwarding table";
      //   //        type empty;
      //   //      }
      //   //    }
      //   //    case case_2 {
      //   //      leaf passive {
      //   //        description "Retain inactive route in forwarding table";
      //   //        type empty;
      //   //      }
      //   //    }
      //   //  }
      //    container metric {
      //      description "Metric value";
      //      presence "enable metric";
      //      uses rib_static_metric_type;
      //    }
      //    container metric2 {
      //      description "Metric value 2";
      //      presence "enable metric2";
      //      uses rib_static_metric_type;
      //    }
      //    container metric3 {
      //      description "Metric value 3";
      //      presence "enable metric3";
      //      uses rib_static_metric_type;
      //    }
      //    container metric4 {
      //      description "Metric value 4";
      //      presence "enable metric4";
      //      uses rib_static_metric_type;
      //    }
      //    container tag {
      //      description "Tag string";
      //      presence "enable tag";
      //      uses rib_static_metric_type;
      //    }
      //    container tag2 {
      //      description "Tag string 2";
      //      presence "enable tag2";
      //      uses rib_static_metric_type;
      //    }
      //    container preference {
      //      description "Preference value";
      //      presence "enable preference";
      //      uses rib_static_metric_type;
      //    }
      //    container preference2 {
      //      description "Preference value 2";
      //      presence "enable preference2";
      //      uses rib_static_metric_type;
      //    }
      //    container color {
      //      description "Color (preference) value";
      //      presence "enable color";
      //      uses rib_static_metric_type;
      //    }
      //    container color2 {
      //      description "Color (preference) value 2";
      //      presence "enable color2";
      //      uses rib_static_metric_type;
      //    }
      //    leaf-list community {
      //      ordered-by user;
      //      description "BGP community identifier";
      //      type jt:community;
      //    }
      //    container as-path {
      //      description "Autonomous system path";
      //      // uses apply-advanced;
      //      leaf path {
      //        description "Autonomous system path";
      //        type string;
      //      }
      //      leaf origin {
      //        type enumeration {
      //          enum "igp" {
      //            description "Path originated in the local IGP";
      //          }
      //          enum "egp" {
      //            description "Path originated in another AS";
      //          }
      //          enum "incomplete" {
      //            description "Path was learned by some other means";
      //          }
      //        }
      //      }
      //      leaf atomic-aggregate {
      //        description "Add ATOMIC_AGGREGATE path attribute to route";
      //        type empty;
      //      }
      //      container aggregator {
      //        presence "enable aggregator";
      //        description "Add AGGREGATOR path attribute to route";
      //      }
      //      leaf as-number {
      //        description " Autonomous system number in plain number or 'higher 16bits'.'Lower 16 bits' (asdot notation) format";
      //        type string {
      //        }
      //      }
      //      leaf address {
      //        description "Address of BGP system that formed the route";
      //        type jt:ipv4addr;
      //      }
      //    }
      //    list lsp-next-hop {
      //      key name;
      //      ordered-by user;
      //      description "LSP next hop";
      //      uses lsp_nh_obj;
      //    }
      //   //  list p2mp-lsp-next-hop {
      //   //    key name;
      //   //    ordered-by user;
      //   //    description "Point-to-multipoint LSP next hop";
      //   //    max-elements 1;
      //   //    uses lsp_nh_obj;
      //   //  }
      //   //  container spring-te-lsp-next-hop {
      //   //    description "SPRING-TE LSP next hop";
      //   //    uses springte_lsp_nh_obj;
      //   //  }
      //   //  container p2mp-ldp-next-hop {
      //   //    description "Point-to-multipoint LDP LSP next hop";
      //   //    uses p2mp_ldp_lsp_nh_obj;
      //   //  }
      //  }
       list route-target-filter {
         key name;
         ordered-by user;
         description "Route-target-filter route";
         leaf name {
           type string {
             length "1 .. 47";
           }
         }
         // uses apply-advanced;
         leaf-list neighbor {
           ordered-by user;
           description "BGP peers for filter";
           type jt:ipaddr-scoped;
         }
         leaf-list group {
           ordered-by user;
           description "BGP groups for filter";
           type string;
         }
         leaf local {
           description "Locally originated filter";
           type empty;
         }
       }
     }
     list martians {
       key "address choice-ident choice-value";
       ordered-by user;
       description "Invalid routes";
       uses martian_type;
     }
     container aggregate {
       description "Coalesced routes";
       uses rib_aggregate_type;
     }
    //  container generate {
    //    description "Route of last resort";
    //    uses rib_aggregate_type;
    //  }
    //  choice maximum-paths-type {
    //    case case_1 {
    //      container maximum-routes {
    //        description "Maximum number of routes";
    //        status deprecated;
    //        leaf limit {
    //          description "Maximum number of routes";
    //          type union {
    //            type string {
    //              pattern "<.*>|$.*";
    //            }
    //            type uint32 {
    //              range "1 .. 4294967295";
    //            }
    //          }
    //        }
    //        choice log_type {
    //          case case_1 {
    //            leaf threshold {
    //              description "Percentage of limit at which to start generating warnings";
    //              type union {
    //                type string {
    //                  pattern "<.*>|$.*";
    //                }
    //                type uint32 {
    //                  range "1 .. 100";
    //                }
    //              }
    //            }
    //          }
    //          case case_2 {
    //            leaf log-only {
    //              description "Generate warning messages only";
    //              type empty;
    //            }
    //          }
    //        }
    //        leaf log-interval {
    //          description "Minimum interval between log messages";
    //          units "seconds";
    //          type union {
    //            type string {
    //              pattern "<.*>|$.*";
    //            }
    //            type uint32 {
    //              range "5 .. 86400";
    //            }
    //          }
    //        }
    //      }
    //    }
    //    case case_2 {
    //      container maximum-paths {
    //        description "Maximum number of paths";
    //        leaf limit {
    //          description "Maximum number of paths";
    //          type union {
    //            type string {
    //              pattern "<.*>|$.*";
    //            }
    //            type uint32 {
    //              range "1 .. 4294967295";
    //            }
    //          }
    //        }
    //        choice log_type {
    //          case case_1 {
    //            leaf threshold {
    //              description "Percentage of limit at which to start generating warnings";
    //              type union {
    //                type string {
    //                  pattern "<.*>|$.*";
    //                }
    //                type uint32 {
    //                  range "1 .. 100";
    //                }
    //              }
    //            }
    //          }
    //          case case_2 {
    //            leaf log-only {
    //              description "Generate warning messages only";
    //              type empty;
    //            }
    //          }
    //        }
    //        leaf log-interval {
    //          description "Minimum interval between log messages";
    //          units "seconds";
    //          type union {
    //            type string {
    //              pattern "<.*>|$.*";
    //            }
    //            type uint32 {
    //              range "5 .. 86400";
    //            }
    //          }
    //        }
    //      }
    //    }
    //  }
    //  container maximum-prefixes {
    //    description "Maximum number of prefixes";
    //    leaf limit {
    //      description "Maximum number of prefixes";
    //      type union {
    //        type string {
    //          pattern "<.*>|$.*";
    //        }
    //        type uint32 {
    //          range "1 .. 4294967295";
    //        }
    //      }
    //    }
    //    choice log_type {
    //      case case_1 {
    //        leaf threshold {
    //          description "Percentage of limit at which to start generating warnings";
    //          type union {
    //            type string {
    //              pattern "<.*>|$.*";
    //            }
    //            type uint32 {
    //              range "1 .. 100";
    //            }
    //          }
    //        }
    //      }
    //      case case_2 {
    //        leaf log-only {
    //          description "Generate warning messages only";
    //          type empty;
    //        }
    //      }
    //    }
    //    leaf log-interval {
    //      description "Minimum interval between log messages";
    //      units "seconds";
    //      type union {
    //        type string {
    //          pattern "<.*>|$.*";
    //        }
    //        type uint32 {
    //          range "5 .. 86400";
    //        }
    //      }
    //    }
    //  }
    //  container multipath {
    //    presence "enable multipath";
    //    description "Protocol-independent load balancing";
    //    // uses apply-advanced;
    //    container vpn-unequal-cost {
    //      presence "enable vpn-unequal-cost";
    //      description "Include VPN routes with unequal IGP metrics";
    //      leaf equal-external-internal {
    //        description "Include external and internal VPN routes";
    //        type empty;
    //      }
    //    }
    //    leaf as-path-compare {
    //      description "Compare AS path sequences in addition to AS path length";
    //      type empty;
    //    }
    //    leaf preserve-nexthop-hierarchy {
    //      description "Force multipath to create List nexthop";
    //      type empty;
    //    }
    //  }
    //  container policy-multipath {
    //    description "Policy based multipath";
    //    // uses apply-advanced;
    //    leaf-list policy {
    //      ordered-by user;
    //      description "Import policy to create policy based multipath";
    //      type jt:policy-algebra;
    //    }
    //    container traceoptions {
    //      description "Trace options";
    //      // uses apply-advanced;
    //      container file {
    //        description "Trace file options";
    //        leaf filename {
    //          description "Name of file in which to write trace information";
    //          type string {
    //            length "1 .. 1024";
    //          }
    //        }
    //        leaf replace {
    //          description "Replace trace file rather than appending to it";
    //          status deprecated;
    //          type empty;
    //        }
    //        leaf size {
    //          description "Maximum trace file size";
    //          type string;
    //        }
    //        leaf files {
    //          description "Maximum number of trace files";
    //          default "10";
    //          type union {
    //            type string {
    //              pattern "<.*>|$.*";
    //            }
    //            type uint32 {
    //              range "2 .. 1000";
    //            }
    //          }
    //        }
    //        leaf no-stamp {
    //          description "Do not timestamp trace file";
    //          status deprecated;
    //          type empty;
    //        }
    //        choice world-readable-choice {
    //          leaf world-readable {
    //            description "Allow any user to read the log file";
    //            type empty;
    //          }
    //          leaf no-world-readable {
    //            description "Don't allow any user to read the log file";
    //            type empty;
    //          }
    //        }
    //      }
    //      list flag {
    //        key name;
    //        ordered-by user;
    //        description "Tracing parameters";
    //        leaf name {
    //          type enumeration {
    //            enum "route" {
    //              description "Policy-multipath route tracing.";
    //            }
    //          }
    //        }
    //        leaf send {
    //          description "Trace transmitted packets";
    //          type empty;
    //        }
    //        leaf receive {
    //          description "Trace received packets";
    //          type empty;
    //        }
    //        leaf detail {
    //          description "Trace detailed information";
    //          type empty;
    //        }
    //        leaf disable {
    //          description "Disable this trace flag";
    //          type empty;
    //        }
    //      }
    //    }
    //    leaf preserve-nexthop-hierarchy {
    //      description "Enable preserved nexthop hierarchy";
    //      type empty;
    //    }
    //  }
    //  container protect {
    //    description "Protocol-independent protection";
    //    leaf core {
    //      description "Protect against unreachability to service-edge router";
    //      type empty;
    //    }
    //  }
    //  container access {
    //    description "Access routes";
    //    // uses apply-advanced;
    //    list route {
    //      key name;
    //      ordered-by user;
    //      description "Access route";
    //      leaf name {
    //        description "IP address of destination";
    //        type jt:ipprefix;
    //      }
    //      // uses apply-advanced;
    //      leaf-list next-hop {
    //        ordered-by user;
    //        description "Next hop to destination";
    //        type union {
    //          type jt:ipaddr-or-interface;
    //          type string {
    //            pattern "<.*>|$.*";
    //          }
    //        }
    //      }
    //      list qualified-next-hop {
    //        key name;
    //        ordered-by user;
    //        description "Next hop with qualifiers";
    //        uses qualified_nh_obj;
    //      }
    //      leaf metric {
    //        description "Metric value";
    //        type union {
    //          type string {
    //            pattern "<.*>|$.*";
    //          }
    //          type uint32 {
    //            range "1 .. 255";
    //          }
    //        }
    //      }
    //      leaf preference {
    //        description "Preference value";
    //        type union {
    //          type uint32;
    //          type string {
    //            pattern "<.*>|$.*";
    //          }
    //        }
    //      }
    //      leaf tag {
    //        description "Tag string";
    //        type union {
    //          type uint32;
    //          type string {
    //            pattern "<.*>|$.*";
    //          }
    //        }
    //      }
    //      leaf tag2 {
    //        description "Tag2 string";
    //        type union {
    //          type uint32;
    //          type string {
    //            pattern "<.*>|$.*";
    //          }
    //        }
    //      }
    //    }
    //  }
    //  container access-internal {
    //    description "Access-internal routes";
    //    // uses apply-advanced;
    //    list route {
    //      key name;
    //      ordered-by user;
    //      description "Access-internal route";
    //      leaf name {
    //        description "IP address and optional prefix length of destination";
    //        type jt:ipprefix;
    //      }
    //      // uses apply-advanced;
    //      leaf-list next-hop {
    //        ordered-by user;
    //        description "Next hop to destination";
    //        type union {
    //          type jt:ipaddr-or-interface;
    //          type string {
    //            pattern "<.*>|$.*";
    //          }
    //        }
    //      }
    //      list qualified-next-hop {
    //        key name;
    //        ordered-by user;
    //        description "Next hop with qualifiers";
    //        uses qualified_nh_obj;
    //      }
    //    }
    //  }
     container bgp-static {
       description "Routes for BGP static advertisements";
       // uses apply-advanced;
       list route {
         key name;
         ordered-by user;
         description "BGP-static route";
         leaf name {
           description "IP address and optional prefix length of destination";
           type jt:ipprefix;
         }
         // uses apply-advanced;
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           // uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
     }
    //  list rib-groups {
    //    key name;
    //    ordered-by user;
    //    description "Group of routing tables";
    //    uses rpd_rib_group_type;
    //  }
    //  leaf route-record {
    //    description "Enable route recording";
    //    type empty;
    //  }
     container localized-fib {
       presence "enable localized-fib";
       description "Localize vrf routing-instance routes to specific FPC hardware";
       // uses apply-advanced;
       leaf-list fpc-slot {
         ordered-by user;
         description "Local FPC list";
         type union {
           type uint32;
           type string {
             pattern "<.*>|$.*";
           }
         }
       }
     }
     leaf-list instance-import {
       ordered-by user;
       description "Import policy for instance RIBs";
       type jt:policy-algebra;
     }
     leaf-list instance-export {
       ordered-by user;
       description "Export policy for instance RIBs";
       type jt:policy-algebra;
     }
    //  container auto-export {
    //    presence "enable auto-export";
    //    description "Export routes between routing instances";
    //    // uses apply-advanced;
    //    choice enable-disable {
    //      case case_1 {
    //        leaf disable {
    //          description "Disable auto-export";
    //          type empty;
    //        }
    //      }
    //    }
    //    container traceoptions {
    //      description "Trace options";
    //      // uses apply-advanced;
    //      container file {
    //        description "Trace file options";
    //        leaf filename {
    //          description "Name of file in which to write trace information";
    //          type string {
    //            length "1 .. 1024";
    //          }
    //        }
    //        leaf replace {
    //          description "Replace trace file rather than appending to it";
    //          status deprecated;
    //          type empty;
    //        }
    //        leaf size {
    //          description "Maximum trace file size";
    //          type string;
    //        }
    //        leaf files {
    //          description "Maximum number of trace files";
    //          default "10";
    //          type union {
    //            type string {
    //              pattern "<.*>|$.*";
    //            }
    //            type uint32 {
    //              range "2 .. 1000";
    //            }
    //          }
    //        }
    //        leaf no-stamp {
    //          description "Do not timestamp trace file";
    //          status deprecated;
    //          type empty;
    //        }
    //        choice world-readable-choice {
    //          leaf world-readable {
    //            description "Allow any user to read the log file";
    //            type empty;
    //          }
    //          leaf no-world-readable {
    //            description "Don't allow any user to read the log file";
    //            type empty;
    //          }
    //        }
    //      }
    //      list flag {
    //        key name;
    //        ordered-by user;
    //        description "Tracing parameters";
    //        leaf name {
    //          type enumeration {
    //            enum "export" {
    //              description "Export processing";
    //            }
    //            enum "route" {
    //              description "Trace routing information";
    //            }
    //            enum "normal" {
    //              description "Trace normal events";
    //            }
    //            enum "general" {
    //              description "Trace general events";
    //            }
    //            enum "state" {
    //              description "Trace state transitions";
    //            }
    //            enum "policy" {
    //              description "Trace policy processing";
    //            }
    //            enum "task" {
    //              description "Trace routing protocol task processing";
    //            }
    //            enum "timer" {
    //              description "Trace routing protocol timer processing";
    //            }
    //            enum "all" {
    //              description "Trace everything";
    //            }
    //          }
    //        }
    //        leaf send {
    //          description "Trace transmitted packets";
    //          type empty;
    //        }
    //        leaf receive {
    //          description "Trace received packets";
    //          type empty;
    //        }
    //        leaf detail {
    //          description "Trace detailed information";
    //          type empty;
    //        }
    //        leaf disable {
    //          description "Disable this trace flag";
    //          type empty;
    //        }
    //      }
    //    }
    //    container family {
    //      container inet {
    //        description "IPv4 parameters";
    //        uses export-af-obj;
    //      }
    //      container inet6 {
    //        description "IPv6 parameters";
    //        uses export-af-obj;
    //      }
    //      container iso {
    //        description "ISO parameters";
    //        uses export-af-obj;
    //      }
    //    }
    //  }
     container transport-class {
       presence "enable transport-class";
       description "Transport layer options";
       // uses apply-advanced;
       leaf auto-create {
         description "Auto create on color discovery";
         type empty;
       }
       container fallback {
         description "Service routes resolution fallback";
         // uses apply-advanced;
         leaf none {
           description "Resolve associated service-routes using this transport-class tunnels only";
           type empty;
         }
       }
       list name {
         key name;
         ordered-by user;
         description "Transport layer collecting Tunnels with similar characteristics";
         leaf name {
           description "Transport class name";
           type string;
         }
         // uses apply-advanced;
         leaf color {
           description "Color(0..4294967295). This auto derives the Mapping Community and Route Target";
           type union {
             type uint32;
             type string {
               pattern "<.*>|$.*";
             }
           }
         }
         container fallback {
           description "Service routes resolution fallback";
           // uses apply-advanced;
           leaf none {
             description "Resolve associated service-routes using this transport-class tunnels only";
             type empty;
           }
         }
         container tunnel-egress {
           description "Tunnel-Egress endpoint origination";
           // uses apply-advanced;
           list end-point {
             key name;
             ordered-by user;
             description "Configure Tunnel-Egress endpoints";
             leaf name {
               description "Address of Tunnel egress endpoint";
               type jt:ipaddr;
             }
             // uses apply-advanced;
             leaf-list import {
               ordered-by user;
               description "Import policy to set attributes";
               type jt:policy-algebra;
             }
           }
         }
       }
       container any-class {
         description "Predefined transport class collecting Tunnels of all transport classes";
         // uses apply-advanced;
         leaf color {
           description "Color 32bit value. This auto derives the Mapping Community.";
           type union {
             type uint32;
             type string {
               pattern "<.*>|$.*";
             }
           }
         }
         container fallback {
           description "Service routes resolution fallback";
           // uses apply-advanced;
           leaf none {
             description "Resolve associated service-routes using this transport-class tunnels only";
             type empty;
           }
         }
       }
       container best-effort {
         description "Best effort transport class";
         // uses apply-advanced;
         leaf color {
           description "Color 32 bit value";
           type union {
             type uint32;
             type string {
               pattern "<.*>|$.*";
             }
           }
         }
         container fallback {
           description "Service routes resolution fallback";
           // uses apply-advanced;
           leaf none {
             description "Resolve associated service-routes using this transport-class tunnels only";
             type empty;
           }
         }
       }
     }
     list diversity-association {
       key name;
       ordered-by user;
       description "Diversity Association Group configuration";
       leaf name {
         description "Diversity Association group name";
         type string {
           length "1 .. 64";
         }
       }
       // uses apply-advanced;
       leaf group-id {
         description "Diversity Association group id";
         type union {
           type string {
             pattern "<.*>|$.*";
           }
           type uint16 {
             range "1 .. 65535";
           }
         }
       }
       leaf association-type {
         description "Association Type";
         type enumeration {
           enum "node" {
             description "Disjoint Level Node";
           }
           enum "link" {
             description "Disjoint Level Link";
           }
           enum "srlg-node" {
             description "Disjoint Level SRLG-Node";
           }
           enum "srlg-link" {
             description "Disjoint Level SRLG-Link";
           }
         }
       }
       leaf strict {
         description "Strict Disjointness";
         type empty;
       }
       leaf association-src-ipv4 {
         description "IPV4 Association Source";
         type jt:ipv4addr;
       }
       leaf association-src-ipv6 {
         description "IPV6 Association Source";
         type jt:ipv6addr;
       }
     }
     list te-policy-association {
       key name;
       ordered-by user;
       description "Policy association group configuration";
       leaf name {
         description "Policy association group name";
         type string {
           length "1 .. 64";
         }
       }
       // uses apply-advanced;
       leaf group-id {
         description "Policy association group id";
         type union {
           type string {
             pattern "<.*>|$.*";
           }
           type uint16 {
             range "1 .. 65535";
           }
         }
       }
       leaf association-src-ipv4 {
         description "IPV4 association source";
         type jt:ipv4addr;
       }
       leaf association-src-ipv6 {
         description "IPV6 association source";
         type jt:ipv6addr;
       }
     }
     container dynamic-tunnels {
       description "Dynamic tunnel definitions";
       // uses apply-advanced;
       list tunnel-attributes {
         key name;
         ordered-by user;
         description "Dynamic tunnel attributes definition";
         leaf name {
           description "Dynamic Tunnel attribute name";
           type string {
           }
         }
         // uses apply-advanced;
         leaf dynamic-tunnel-source-prefix {
           description "Tunnel source address";
           type jt:ipaddr;
         }
         leaf dynamic-tunnel-type {
           type enumeration {
             enum "GRE" {
               description "Tunnel type GRE";
             }
             enum "V4oV6" {
               description "Tunnel type is IPV4oIPV6";
             }
             enum "UDP" {
               description "Tunnel type UDP";
             }
             enum "BGP-SIGNAL" {
               description "Tunnel type BGP-SIGNAL";
             }
             enum "IPIP" {
               description "Tunnel type IPIP";
             }
           }
         }
         leaf dynamic-tunnel-mtu {
           description "Dynamic Tunnel MTU value";
           type union {
             type string {
               pattern "<.*>|$.*";
             }
             type uint32 {
               range "296 .. 9232";
             }
           }
         }
         leaf dynamic-tunnel-gre-key {
           description "RFC 2890 Dynamic Tunnel GRE Key";
           type union {
             type string {
               pattern "<.*>|$.*";
             }
             type uint32 {
               range "1 .. 4294967295";
             }
           }
         }
         leaf dynamic-tunnel-anchor-pfe {
           description "Dynamic Tunnel anchor PFE name of format pfe-x/y/z";
           type string {
           }
         }
         leaf dynamic-tunnel-anti-spoof {
           type enumeration {
             enum "on" {
               description "Enable antispoofing check. Default is enabled";
             }
             enum "off" {
               description "Disable antispoofing check";
             }
           }
         }
         leaf dynamic-tunnel-reassembly {
           type enumeration {
             enum "on" {
               description "Enable reassembly check. Default is disabled";
             }
             enum "off" {
               description "Disable reassembly check";
             }
           }
         }
         leaf dynamic-tunnel-ttl {
           description "Dynamic Tunnel TTL value";
           type union {
             type string {
               pattern "<.*>|$.*";
             }
             type uint32 {
               range "1 .. 255";
             }
           }
         }
         leaf dynamic-tunnel-forwarding-class {
           description "Dynamic Tunnel forwarding class name";
           type string {
             length "1 .. 64";
           }
         }
         leaf dynamic-tunnel-payload-port-profile {
           description "Dynamic Tunnel UDP payload port profile";
           type string;
         }
         leaf dynamic-tunnel-propagate-dscp {
           description "Dynamic Tunnel Propagate DSCP";
           type empty;
         }
       }
       container forwarding-rib {
         presence "enable forwarding-rib";
         description "Forwarding routing table for dynamic-tunnel";
         // uses apply-advanced;
         container inet.0 {
           presence "enable inet.0";
           description "Rib table inet.0";
           // uses apply-advanced;
           leaf-list inet-import {
             ordered-by user;
             description "Import policy for V4 dynamic-tunnel";
             type jt:policy-algebra;
           }
         }
         container inet6.0 {
           presence "enable inet6.0";
           description "Rib table inet6.0";
           // uses apply-advanced;
           leaf-list inet6-import {
             ordered-by user;
             description "Import policy for V6 dynamic-tunnel";
             type jt:policy-algebra;
           }
         }
       }
       container statistics {
         description "Fetch traffic statistics for  dynamic tunnels";
         // uses apply-advanced;
         leaf interval {
           description "Time after which statistics has to be fetched";
           units "seconds";
           type union {
             type string {
               pattern "<.*>|$.*";
             }
             type uint16 {
               range "1 .. 65535";
             }
           }
         }
       }
       container traceoptions {
         description "Trace options";
         // uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "kernel" {
                 description "Trace kernel communication";
               }
               enum "tunnel" {
                 description "Trace tunnel addition, change, or deletion";
               }
               enum "task" {
                 description "Trace task or job processing";
               }
               enum "tunnel-event" {
                 description "Trace create, delete, up, down event for nh based tunnel";
               }
               enum "flash-event" {
                 description "Trace flash event for tunnel forwarding route";
               }
               enum "stats-job" {
                 description "Trace taffic statistics job related stuff";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf v4ov6 {
         description "Enable dynamic tunnel V4oV6 mode";
         type enumeration {
           enum "ipv6-anycast-source-duplication" {
             description "Enable full resolved nh base source-tunnel";
           }
         }
       }
       list gre {
         key name;
         ordered-by user;
         description "Enable dynamic gre tunnel mode";
         leaf name {
           description "Enable dynamic tunnel gre mode";
           type enumeration {
             enum "next-hop-based-tunnel" {
               description "Enable nh base dynamic-tunnel";
             }
             enum "full-resolved-next-hop-based-tunnel" {
               description "Enable full resolved nh base dynamic-tunnel";
             }
             enum "chain-full-resolve-next-hop-based-tunnel" {
               description "Enable chain full resolved nh base dynamic-tunnel";
             }
           }
         }
         // uses apply-advanced;
       }
       container signal-tunnel-preference {
         presence "enable signal-tunnel-preference";
         description "Set tunnel preference for signalled tunnels";
         // uses apply-advanced;
         leaf gre {
           description "Preference of GRE signalled tunnels";
           type union {
             type string {
               pattern "<.*>|$.*";
             }
             type uint32 {
               range "1 .. 10";
             }
           }
         }
         leaf udp {
           description "Preference of UDP signalled tunnels";
           type union {
             type string {
               pattern "<.*>|$.*";
             }
             type uint32 {
               range "1 .. 10";
             }
           }
         }
         leaf ipip {
           description "Preference of IPIP signalled tunnels";
           type union {
             type string {
               pattern "<.*>|$.*";
             }
             type uint32 {
               range "1 .. 10";
             }
           }
         }
       }
      //  list dynamic-tunnel {
      //    key name;
      //    ordered-by user;
      //    uses dynamic_tunnel_type;
      //  }
     }
     list interface {
       key name;
       ordered-by user;
       description "Direct/Host route FRR protection";
       leaf name {
         description "Interface name";
         type union {
           type jt:interface-name;
           type string {
             pattern "<.*>|$.*";
           }
         }
       }
       // uses apply-advanced;
       leaf arp-prefix-limit {
         description "Max ARP/Host FRR routes allowed";
         type union {
           type string {
             pattern "<.*>|$.*";
           }
           type uint32 {
             range "1 .. 10000";
           }
         }
       }
       leaf supplementary-blackout-timer {
         description "ARP plimit blackout timer = kernel ARP timeout + supplementary-blackout-timer minutes.";
         type union {
           type string {
             pattern "<.*>|$.*";
           }
           type uint32 {
             range "1 .. 15";
           }
         }
       }
       choice protection-type {
         case case_1 {
           leaf link-protection {
             description "Protect interface from link faults only";
             type empty;
           }
         }
       }
     }
    //  container host-fast-reroute {
    //    presence "enable host-fast-reroute";
    //    description "Host Fast Re-route global values. Applies to all host FRR profiles.";
    //    // uses apply-advanced;
    //    leaf global-arp-prefix-limit {
    //      description "Max ARP/Host FRR routes allowed per protected IFL";
    //      type union {
    //        type string {
    //          pattern "<.*>|$.*";
    //        }
    //        type uint32 {
    //          range "1 .. 10000";
    //        }
    //      }
    //    }
    //    leaf global-supplementary-blackout-timer {
    //      description "ARP plimit global blackout timer = kernel ARP timeout + global-supplementary-blackout-timer minutes.";
    //      type union {
    //        type string {
    //          pattern "<.*>|$.*";
    //        }
    //        type uint32 {
    //          range "1 .. 15";
    //        }
    //      }
    //    }
    //  }
    //  leaf warm-standby {
    //    description "Enable warm-standby";
    //    type empty;
    //  }
    //  leaf nonstop-routing {
    //    description "Enable nonstop routing";
    //    type empty;
    //  }
    //  container nonstop-routing-options {
    //    presence "enable nonstop-routing-options";
    //    description "Nonstop routing options";
    //    // uses apply-advanced;
    //    leaf precision-timers-max-period {
    //      description "Set Max period for precision timer support from kernel after switchover";
    //      type union {
    //        type string {
    //          pattern "<.*>|$.*";
    //        }
    //        type uint32 {
    //          range "60 .. 1800";
    //        }
    //      }
    //    }
    //  }
    //  leaf nsr-phantom-holdtime {
    //    description "Set NSR phantom route hold time";
    //    type union {
    //      type string {
    //        pattern "<.*>|$.*";
    //      }
    //      type uint32 {
    //        range "0 .. 10000";
    //      }
    //    }
    //  }
    //  list srlg {
    //    key name;
    //    ordered-by user;
    //    description "SRLG configuration";
    //    leaf name {
    //      description "Group name";
    //      type string {
    //        length "1 .. 64";
    //      }
    //    }
    //    // uses apply-advanced;
    //    leaf srlg-value {
    //      description "Group id";
    //      type union {
    //        type string {
    //          pattern "<.*>|$.*";
    //        }
    //        type uint32 {
    //          range "1 .. 4294967295";
    //        }
    //      }
    //    }
    //    leaf srlg-cost {
    //      description "Cost value";
    //      type union {
    //        type string {
    //          pattern "<.*>|$.*";
    //        }
    //        type uint32 {
    //          range "1 .. 65535";
    //        }
    //      }
    //    }
    //  }
    //  container admin-groups-extended-range {
    //    description "Extended administrative groups range";
    //    // uses apply-advanced;
    //    leaf minimum {
    //      description "Minimum value of the range for extended administrative groups";
    //      type union {
    //        type string {
    //          pattern "<.*>|$.*";
    //        }
    //        type uint32 {
    //          range "32 .. 4294967295";
    //        }
    //      }
    //    }
    //    leaf maximum {
    //      description "Maximum value of the range for extended administrative groups";
    //      type union {
    //        type string {
    //          pattern "<.*>|$.*";
    //        }
    //        type uint32 {
    //          range "32 .. 4294967295";
    //        }
    //      }
    //    }
    //  }
    //  list admin-groups-extended {
    //    key name;
    //    ordered-by user;
    //    description "Extended administrative groups";
    //    leaf name {
    //      description "Group name (Maximum length 64)";
    //      type string {
    //        length "1 .. 64";
    //      }
    //    }
    //    // uses apply-advanced;
    //    leaf group-value {
    //      description "Group id";
    //      type union {
    //        type string {
    //          pattern "<.*>|$.*";
    //        }
    //        type uint32 {
    //          range "32 .. 4294967295";
    //        }
    //      }
    //    }
    //  }
    //  leaf lsp-telemetry {
    //    description "Turn on Jvision LSP telemetry";
    //    type empty;
    //  }
    //  container l3vpn-composite-nexthop {
    //    presence "enable l3vpn-composite-nexthop";
    //    description "Enable composite nexthop for l3vpn";
    //    status deprecated;
    //    // uses apply-advanced;
    //  }
    //  container source-routing {
    //    description "Source-routing options";
    //    // uses apply-advanced;
    //    leaf ip {
    //      description "Enable IP Source Routing";
    //      type empty;
    //    }
    //    leaf ipv6 {
    //      description "Enable Type 0 RouteHeader processing";
    //      type empty;
    //    }
    //  }
    //  container forwarding-table {
    //    uses forwarding-table-type;
    //  }
    //  container fate-sharing {
    //    description "Fate-sharing links or nodes database";
    //    // uses apply-advanced;
    //    list group {
    //      key name;
    //      ordered-by user;
    //      description "Group of objects sharing common characteristics";
    //      leaf name {
    //        description "Name of object groups sharing the same fate";
    //        type string {
    //        }
    //      }
    //      // uses apply-advanced;
    //      leaf cost {
    //        description "Cost value";
    //        type union {
    //          type string {
    //            pattern "<.*>|$.*";
    //          }
    //          type uint32 {
    //            range "1 .. 65535";
    //          }
    //        }
    //      }
    //      leaf use-for-post-convergence-lfa {
    //        description "Use this fate-sharing group as a constraint for post-convergence-lfa";
    //        type empty;
    //      }
    //      list from {
    //        key name;
    //        uses fate_sharing_links;
    //      }
    //    }
    //  }
    //  container multicast {
    //    description "Global multicast options";
    //    // uses apply-advanced;
    //    container traceoptions {
    //      description "Global multicast trace options";
    //      // uses apply-advanced;
    //      container file {
    //        description "Trace file options";
    //        leaf filename {
    //          description "Name of file in which to write trace information";
    //          type string {
    //            length "1 .. 1024";
    //          }
    //        }
    //        leaf replace {
    //          description "Replace trace file rather than appending to it";
    //          status deprecated;
    //          type empty;
    //        }
    //        leaf size {
    //          description "Maximum trace file size";
    //          type string;
    //        }
    //        leaf files {
    //          description "Maximum number of trace files";
    //          default "10";
    //          type union {
    //            type string {
    //              pattern "<.*>|$.*";
    //            }
    //            type uint32 {
    //              range "2 .. 1000";
    //            }
    //          }
    //        }
    //        leaf no-stamp {
    //          description "Do not timestamp trace file";
    //          status deprecated;
    //          type empty;
    //        }
    //        choice world-readable-choice {
    //          leaf world-readable {
    //            description "Allow any user to read the log file";
    //            type empty;
    //          }
    //          leaf no-world-readable {
    //            description "Don't allow any user to read the log file";
    //            type empty;
    //          }
    //        }
    //      }
    //      list flag {
    //        key name;
    //        ordered-by user;
    //        description "Tracing parameters";
    //        leaf name {
    //          type enumeration {
    //            enum "parse" {
    //              description "Trace configuration parsing";
    //            }
    //            enum "config-internal" {
    //              description "Trace configuration internals";
    //            }
    //            enum "route" {
    //              description "Trace routing information";
    //            }
    //            enum "normal" {
    //              description "Trace normal events";
    //            }
    //            enum "general" {
    //              description "Trace general events";
    //            }
    //            enum "state" {
    //              description "Trace state transitions";
    //            }
    //            enum "policy" {
    //              description "Trace policy processing";
    //            }
    //            enum "task" {
    //              description "Trace routing protocol task processing";
    //            }
    //            enum "timer" {
    //              description "Trace routing protocol timer processing";
    //            }
    //            enum "all" {
    //              description "Trace everything";
    //            }
    //          }
    //        }
    //        leaf disable {
    //          description "Disable this trace flag";
    //          type empty;
    //        }
    //      }
    //    }
    //    leaf rpf {
    //      status deprecated;
    //      type string;
    //    }
    //    list scope {
    //      key name;
    //      ordered-by user;
    //      description "Multicast address scope";
    //      leaf name {
    //        description "Name to identify multicast address scope";
    //        type string;
    //      }
    //      // uses apply-advanced;
    //      leaf prefix {
    //        description "Administratively scoped address";
    //        type jt:ipprefix;
    //      }
    //      leaf-list interface {
    //        ordered-by user;
    //        description "Interface on which to configure scoping";
    //        type union {
    //          type jt:interface-name;
    //          type string {
    //            pattern "<.*>|$.*";
    //          }
    //        }
    //      }
    //    }
    //    leaf-list scope-policy {
    //      ordered-by user;
    //      description "Scoping policy";
    //      type jt:policy-algebra;
    //    }
    //    list flow-map {
    //      key name;
    //      ordered-by user;
    //      description "Multicast flow map configuration";
    //      leaf name {
    //        description "Name of the flow map";
    //        type string;
    //      }
    //      // uses apply-advanced;
    //      leaf-list policy {
    //        ordered-by user;
    //        description "Policy for matched flows";
    //        type jt:policy-algebra;
    //      }
    //      container bandwidth {
    //        presence "enable bandwidth";
    //        description "Bandwidth properties for matched flows";
    //        leaf bandwidth-value {
    //          description "Static or default bandwidth for the matched flows";
    //          units "bps";
    //          type string;
    //        }
    //        leaf adaptive {
    //          description "Auto-sense bandwidth for matched flows";
    //          type empty;
    //        }
    //      }
    //      leaf-list redundant-sources {
    //        ordered-by user;
    //        description "Redundant source addresses";
    //        type jt:ipaddr;
    //      }
    //      container forwarding-cache {
    //        description "Forwarding cache properties for matched flows";
    //        // uses apply-advanced;
    //        container timeout {
    //          description "Timeout properties for matched flows";
    //          choice timeout_choice {
    //            case case_1 {
    //              leaf timeout-value {
    //                description "Timeout for forwarding cache entry";
    //                units "minutes";
    //                type union {
    //                  type string {
    //                    pattern "<.*>|$.*";
    //                  }
    //                  type uint32 {
    //                    range "1 .. 720";
    //                  }
    //                }
    //              }
    //            }
    //            case case_2 {
    //              container never {
    //                presence "enable never";
    //                description "Forwarding cache entries never time out";
    //                // uses apply-advanced;
    //                leaf non-discard-entry-only {
    //                  description "Apply only to non-discard entries";
    //                  type empty;
    //                }
    //              }
    //            }
    //          }
    //        }
    //      }
    //    }
    //    leaf-list resolve-filter {
    //      ordered-by user;
    //      description "Multicast resolve policy filter";
    //      status deprecated;
    //      type jt:policy-algebra;
    //    }
    //    leaf-list ssm-groups {
    //      ordered-by user;
    //      description "Source-specific multicast group ranges";
    //      type jt:ipprefix;
    //    }
    //    leaf cont-stats-collection-interval {
    //      description "IGMP/MLD continuous statistics collection interval";
    //      default "300";
    //      type union {
    //        type string {
    //          pattern "<.*>|$.*";
    //        }
    //        type uint16 {
    //          range "60 .. 3600";
    //        }
    //      }
    //    }
    //    leaf asm-override-ssm {
    //      description "Allow ASM state for SSM group ranges";
    //      type empty;
    //    }
    //    leaf-list rpf-check-policy {
    //      ordered-by user;
    //      description "Disable RPF check for a source group pair";
    //      type jt:policy-algebra;
    //    }
    //    container pim-to-igmp-proxy {
    //      description "PIM-to-IGMP proxy";
    //      // uses apply-advanced;
    //      leaf-list upstream-interface {
    //        ordered-by user;
    //        description "Upstream interface list";
    //        type union {
    //          type jt:interface-name;
    //          type string {
    //            pattern "<.*>|$.*";
    //          }
    //        }
    //        max-elements 2;
    //      }
    //    }
    //    container pim-to-mld-proxy {
    //      description "PIM-to-MLD proxy";
    //      // uses apply-advanced;
    //      leaf-list upstream-interface {
    //        ordered-by user;
    //        description "Upstream interface list";
    //        type union {
    //          type jt:interface-name;
    //          type string {
    //            pattern "<.*>|$.*";
    //          }
    //        }
    //        max-elements 2;
    //      }
    //    }
    //    container forwarding-cache {
    //      description "Multicast forwarding cache";
    //      // uses apply-advanced;
    //      leaf allow-maximum {
    //        description "Allow maximum of global and family level threshold values for suppress and reuse";
    //        type empty;
    //      }
    //      list family {
    //        key name;
    //        ordered-by user;
    //        description "Protocol family";
    //        leaf name {
    //          description "Protocol family";
    //          type enumeration {
    //            enum "inet" {
    //              description "IPv4 family";
    //            }
    //            enum "inet6" {
    //              description "IPv6 family";
    //            }
    //          }
    //        }
    //        // uses apply-advanced;
    //        container threshold {
    //          presence "enable threshold";
    //          description "Multicast forwarding cache suppress threshold";
    //          // uses apply-advanced;
    //          leaf suppress {
    //            description "Suppress threshold";
    //            type union {
    //              type string {
    //                pattern "<.*>|$.*";
    //              }
    //              type uint32 {
    //                range "1 .. 200000";
    //              }
    //            }
    //          }
    //          leaf reuse {
    //            description "Reuse threshold";
    //            type union {
    //              type string {
    //                pattern "<.*>|$.*";
    //              }
    //              type uint32 {
    //                range "1 .. 200000";
    //              }
    //            }
    //          }
    //          leaf mvpn-rpt-suppress {
    //            description "MVPN RP tree entry suppress threshold";
    //            type union {
    //              type string {
    //                pattern "<.*>|$.*";
    //              }
    //              type uint32 {
    //                range "1 .. 200000";
    //              }
    //            }
    //          }
    //          leaf mvpn-rpt-reuse {
    //            description "MVPN RP tree entry reuse threshold";
    //            type union {
    //              type string {
    //                pattern "<.*>|$.*";
    //              }
    //              type uint32 {
    //                range "1 .. 200000";
    //              }
    //            }
    //          }
    //          leaf log-warning {
    //            description "Percentage at which to start generating warnings";
    //            type union {
    //              type string {
    //                pattern "<.*>|$.*";
    //              }
    //              type uint32 {
    //                range "1 .. 100";
    //              }
    //            }
    //          }
    //        }
    //      }
    //      container threshold {
    //        description "Threshold";
    //        // uses apply-advanced;
    //        leaf suppress {
    //          description "Suppress threshold";
    //          type union {
    //            type string {
    //              pattern "<.*>|$.*";
    //            }
    //            type uint32 {
    //              range "1 .. 200000";
    //            }
    //          }
    //        }
    //        leaf reuse {
    //          description "Reuse threshold";
    //          type union {
    //            type string {
    //              pattern "<.*>|$.*";
    //            }
    //            type uint32 {
    //              range "1 .. 200000";
    //            }
    //          }
    //        }
    //        leaf mvpn-rpt-suppress {
    //          description "MVPN RP tree entry suppress threshold";
    //          type union {
    //            type string {
    //              pattern "<.*>|$.*";
    //            }
    //            type uint32 {
    //              range "1 .. 200000";
    //            }
    //          }
    //        }
    //        leaf mvpn-rpt-reuse {
    //          description "MVPN RP tree entry reuse threshold";
    //          type union {
    //            type string {
    //              pattern "<.*>|$.*";
    //            }
    //            type uint32 {
    //              range "1 .. 200000";
    //            }
    //          }
    //        }
    //        leaf log-warning {
    //          description "Percentage at which to start generating warnings";
    //          type union {
    //            type string {
    //              pattern "<.*>|$.*";
    //            }
    //            type uint32 {
    //              range "1 .. 100";
    //            }
    //          }
    //        }
    //      }
    //      leaf timeout {
    //        description "Forwarding cache entry timeout in minutes";
    //        type union {
    //          type string {
    //            pattern "<.*>|$.*";
    //          }
    //          type uint32 {
    //            range "1 .. 720";
    //          }
    //        }
    //      }
    //    }
    //    list interface {
    //      key name;
    //      ordered-by user;
    //      description "Multicast interface options";
    //      uses multicast_interface_options_type;
    //    }
    //    list ssm-map {
    //      key name;
    //      ordered-by user;
    //      description "SSM map definitions";
    //      leaf name {
    //        description "SSM map name";
    //        type string;
    //      }
    //      // uses apply-advanced;
    //      leaf-list policy {
    //        ordered-by user;
    //        description "Policy for matching group";
    //        type jt:policy-algebra;
    //      }
    //      leaf-list source {
    //        ordered-by user;
    //        description "One or more source addresses";
    //        type jt:ipaddr;
    //      }
    //    }
    //    container stream-protection {
    //      presence "enable stream-protection";
    //      description "Multicast only Fast Re-Route";
    //      // uses apply-advanced;
    //      leaf mofrr-primary-path-selection-by-routing {
    //        description "Multicast only Fast Re-Route primary path by Routing";
    //        type empty;
    //      }
    //      leaf mofrr-disjoint-upstream-only {
    //        description "Multicast only Fast Re-Route disjoint upstream only";
    //        type empty;
    //      }
    //      leaf mofrr-no-backup-join {
    //        description "Multicast only Fast Re-Route no backup join";
    //        type empty;
    //      }
    //      leaf mofrr-asm-starg {
    //        description "Multicast only Fast Re-Route asm (*,G)";
    //        type empty;
    //      }
    //      leaf-list policy {
    //        ordered-by user;
    //        description "MoFRR Policy";
    //        type jt:policy-algebra;
    //      }
    //    }
    //    list backup-pe-group {
    //      key name;
    //      ordered-by user;
    //      description "Backup PE group definitions";
    //      leaf name {
    //        description "PE group name";
    //        type string;
    //      }
    //      // uses apply-advanced;
    //      leaf-list backups {
    //        ordered-by user;
    //        description "One or more IP addresses";
    //        type jt:ipaddr;
    //        max-elements 8;
    //      }
    //      leaf local-address {
    //        description "Address to be used as local-address for this group";
    //        type jt:ipaddr;
    //      }
    //    }
    //    leaf omit-wildcard-address {
    //      description "Omit wildcard source/group fields in SPMSI AD NLRI";
    //      type empty;
    //    }
    //    leaf local-address {
    //      description "Local address for PIM and MVPN sessions";
    //      type jt:ipv4addr;
    //    }
    //  }
    //  container programmable-rpd {
    //    description "RPD Server module management options";
    //    uses programmable-rpd-type;
    //  }
    //  container validation {
    //    description "Define Route validation";
    //    // uses apply-advanced;
    //    container traceoptions {
    //      description "Trace options for route validation";
    //      // uses apply-advanced;
    //      container file {
    //        description "Trace file options";
    //        leaf filename {
    //          description "Name of file in which to write trace information";
    //          type string {
    //            length "1 .. 1024";
    //          }
    //        }
    //        leaf replace {
    //          description "Replace trace file rather than appending to it";
    //          status deprecated;
    //          type empty;
    //        }
    //        leaf size {
    //          description "Maximum trace file size";
    //          type string;
    //        }
    //        leaf files {
    //          description "Maximum number of trace files";
    //          default "10";
    //          type union {
    //            type string {
    //              pattern "<.*>|$.*";
    //            }
    //            type uint32 {
    //              range "2 .. 1000";
    //            }
    //          }
    //        }
    //        leaf no-stamp {
    //          description "Do not timestamp trace file";
    //          status deprecated;
    //          type empty;
    //        }
    //        choice world-readable-choice {
    //          leaf world-readable {
    //            description "Allow any user to read the log file";
    //            type empty;
    //          }
    //          leaf no-world-readable {
    //            description "Don't allow any user to read the log file";
    //            type empty;
    //          }
    //        }
    //      }
    //      list flag {
    //        key name;
    //        ordered-by user;
    //        description "Tracing parameters";
    //        leaf name {
    //          type enumeration {
    //            enum "error" {
    //              description "Trace errored packets";
    //            }
    //            enum "packets" {
    //              description "Trace all I/O packets";
    //            }
    //            enum "keepalive" {
    //              description "Trace keepalive packets";
    //            }
    //            enum "update" {
    //              description "Trace update packets";
    //            }
    //            enum "nsr-synchronization" {
    //              description "Trace NSR synchronization events";
    //            }
    //            enum "state" {
    //              description "Trace state transitions";
    //            }
    //            enum "policy" {
    //              description "Trace policy processing";
    //            }
    //            enum "task" {
    //              description "Trace routing protocol task processing";
    //            }
    //            enum "timer" {
    //              description "Trace routing protocol timer processing";
    //            }
    //            enum "client" {
    //              description "Trace route validation client events";
    //            }
    //            enum "all" {
    //              description "Trace everything";
    //            }
    //          }
    //        }
    //        leaf send {
    //          description "Trace transmitted packets";
    //          type empty;
    //        }
    //        leaf receive {
    //          description "Trace received packets";
    //          type empty;
    //        }
    //        leaf detail {
    //          description "Trace detailed information";
    //          type empty;
    //        }
    //        leaf disable {
    //          description "Disable this trace flag";
    //          type empty;
    //        }
    //      }
    //    }
    //    leaf source-file {
    //      description "Specify a local file to read data set";
    //      type string;
    //    }
    //    leaf-list notification-rib {
    //      ordered-by user;
    //      description "Define routing tables that get notified upon validation state change";
    //      type string;
    //    }
    //    list group {
    //      key name;
    //      description "Define a group of sessions";
    //      leaf name {
    //        description "Group name";
    //        type string;
    //      }
    //      // uses apply-advanced;
    //      leaf authentication-algorithm {
    //        description "Authentication algorithm name";
    //        type enumeration {
    //          enum "ao" {
    //            description "TCP authentication option";
    //          }
    //        }
    //      }
    //      leaf tcpao-auth-mismatch {
    //        description "Continue without TCP-AO if any one TCP endpoint does not have TCP-AO configured";
    //        type enumeration {
    //          enum "allow-without-tcpao" {
    //            description "Allow the connection establishment without TCP-AO";
    //          }
    //        }
    //      }
    //      leaf authentication-key-chain {
    //        description "Key chain name";
    //        type string {
    //          length "1 .. 128";
    //        }
    //      }
    //      leaf max-sessions {
    //        description "Maximum connected session in this group";
    //        type union {
    //          type string {
    //            pattern "<.*>|$.*";
    //          }
    //          type uint32 {
    //            range "1 .. 63";
    //          }
    //        }
    //      }
    //      list session {
    //        key name;
    //        description "Configure a session";
    //        leaf name {
    //          type jt:ipaddr;
    //        }
    //        // uses apply-advanced;
    //        container traceoptions {
    //          description "Trace options for route validation";
    //          // uses apply-advanced;
    //          container file {
    //            description "Trace file options";
    //            leaf filename {
    //              description "Name of file in which to write trace information";
    //              type string {
    //                length "1 .. 1024";
    //              }
    //            }
    //            leaf replace {
    //              description "Replace trace file rather than appending to it";
    //              status deprecated;
    //              type empty;
    //            }
    //            leaf size {
    //              description "Maximum trace file size";
    //              type string;
    //            }
    //            leaf files {
    //              description "Maximum number of trace files";
    //              default "10";
    //              type union {
    //                type string {
    //                  pattern "<.*>|$.*";
    //                }
    //                type uint32 {
    //                  range "2 .. 1000";
    //                }
    //              }
    //            }
    //            leaf no-stamp {
    //              description "Do not timestamp trace file";
    //              status deprecated;
    //              type empty;
    //            }
    //            choice world-readable-choice {
    //              leaf world-readable {
    //                description "Allow any user to read the log file";
    //                type empty;
    //              }
    //              leaf no-world-readable {
    //                description "Don't allow any user to read the log file";
    //                type empty;
    //              }
    //            }
    //          }
    //          list flag {
    //            key name;
    //            ordered-by user;
    //            description "Tracing parameters";
    //            leaf name {
    //              type enumeration {
    //                enum "error" {
    //                  description "Trace errored packets";
    //                }
    //                enum "packets" {
    //                  description "Trace all I/O packets";
    //                }
    //                enum "keepalive" {
    //                  description "Trace keepalive packets";
    //                }
    //                enum "update" {
    //                  description "Trace update packets";
    //                }
    //                enum "state" {
    //                  description "Trace state transitions";
    //                }
    //                enum "task" {
    //                  description "Trace routing protocol task processing";
    //                }
    //                enum "timer" {
    //                  description "Trace routing protocol timer processing";
    //                }
    //                enum "all" {
    //                  description "Trace everything";
    //                }
    //              }
    //            }
    //            leaf send {
    //              description "Trace transmitted packets";
    //              type empty;
    //            }
    //            leaf receive {
    //              description "Trace received packets";
    //              type empty;
    //            }
    //            leaf detail {
    //              description "Trace detailed information";
    //              type empty;
    //            }
    //            leaf disable {
    //              description "Disable this trace flag";
    //              type empty;
    //            }
    //          }
    //        }
    //        leaf authentication-algorithm {
    //          description "Authentication algorithm name";
    //          type enumeration {
    //            enum "ao" {
    //              description "TCP authentication option";
    //            }
    //          }
    //        }
    //        leaf tcpao-auth-mismatch {
    //          description "Continue without TCP-AO if any one TCP endpoint does not have TCP-AO configured";
    //          type enumeration {
    //            enum "allow-without-tcpao" {
    //              description "Allow the connection establishment without TCP-AO";
    //            }
    //          }
    //        }
    //        leaf authentication-key-chain {
    //          description "Key chain name";
    //          type string {
    //            length "1 .. 128";
    //          }
    //        }
    //        leaf database {
    //          description "Named database in this instance to install validation entries";
    //          type string;
    //        }
    //        leaf refresh-time {
    //          description "Interval between keepalive packet transmissions";
    //          units "seconds";
    //          type union {
    //            type string {
    //              pattern "<.*>|$.*";
    //            }
    //            type uint32 {
    //              range "1 .. 1800";
    //            }
    //          }
    //        }
    //        leaf hold-time {
    //          description "Time after which the session is declared down.";
    //          units "seconds";
    //          type union {
    //            type string {
    //              pattern "<.*>|$.*";
    //            }
    //            type uint32 {
    //              range "10 .. 3600";
    //            }
    //          }
    //        }
    //        leaf record-lifetime {
    //          description "Lifetime of route validation records";
    //          units "seconds";
    //          type union {
    //            type string {
    //              pattern "<.*>|$.*";
    //            }
    //            type uint32 {
    //              range "60 .. 604800";
    //            }
    //          }
    //        }
    //        leaf preference {
    //          description "Preference for session establishment";
    //          type union {
    //            type string {
    //              pattern "<.*>|$.*";
    //            }
    //            type uint32 {
    //              range "1 .. 255";
    //            }
    //          }
    //        }
    //        leaf port {
    //          description "Portnumber to connect";
    //          type union {
    //            type string {
    //              pattern "<.*>|$.*";
    //            }
    //            type uint16 {
    //              range "1 .. 65535";
    //            }
    //          }
    //        }
    //        leaf local-address {
    //          type jt:ipaddr;
    //        }
    //      }
    //    }
    //    container static {
    //      description "Define static route validation record";
    //      // uses apply-advanced;
    //      list record {
    //        key name;
    //        description "Static route validation record";
    //        leaf name {
    //          type jt:ipprefix;
    //        }
    //        // uses apply-advanced;
    //        list maximum-length {
    //          key name;
    //          ordered-by user;
    //          leaf name {
    //            description "Maximum prefix-length for route validation record";
    //            type union {
    //              type string {
    //                pattern "<.*>|$.*";
    //              }
    //              type uint32 {
    //                range "1 .. 128";
    //              }
    //            }
    //          }
    //          // uses apply-advanced;
    //          list origin-autonomous-system {
    //            key name;
    //            ordered-by user;
    //            leaf name {
    //              description "Legitimate Origin Autonomous System";
    //              type union {
    //                type uint32;
    //                type string {
    //                  pattern "<.*>|$.*";
    //                }
    //              }
    //            }
    //            // uses apply-advanced;
    //            leaf validation-state {
    //              description "Validation state for route validation record";
    //              type enumeration {
    //                enum "invalid" {
    //                  description "Invalid route validation state";
    //                }
    //                enum "valid" {
    //                  description "Valid route validation state";
    //                }
    //              }
    //            }
    //          }
    //        }
    //      }
    //    }
    //    list database {
    //      key name;
    //      description "Specify a named validation database";
    //      leaf name {
    //        description "Name of validation database";
    //        type string;
    //      }
    //      // uses apply-advanced;
    //      container static {
    //        description "Define static route validation record";
    //        // uses apply-advanced;
    //        list record {
    //          key name;
    //          description "Static route validation record";
    //          leaf name {
    //            type jt:ipprefix;
    //          }
    //          // uses apply-advanced;
    //          list maximum-length {
    //            key name;
    //            ordered-by user;
    //            leaf name {
    //              description "Maximum prefix-length for route validation record";
    //              type union {
    //                type string {
    //                  pattern "<.*>|$.*";
    //                }
    //                type uint32 {
    //                  range "1 .. 128";
    //                }
    //              }
    //            }
    //            // uses apply-advanced;
    //            list origin-autonomous-system {
    //              key name;
    //              ordered-by user;
    //              leaf name {
    //                description "Legitimate Origin Autonomous System";
    //                type union {
    //                  type uint32;
    //                  type string {
    //                    pattern "<.*>|$.*";
    //                  }
    //                }
    //              }
    //              // uses apply-advanced;
    //              leaf validation-state {
    //                description "Validation state for route validation record";
    //                type enumeration {
    //                  enum "invalid" {
    //                    description "Invalid route validation state";
    //                  }
    //                  enum "valid" {
    //                    description "Valid route validation state";
    //                  }
    //                }
    //              }
    //            }
    //          }
    //        }
    //      }
    //    }
    //  }
    //  container congestion-protection {
    //    description "Configuration for Tactical Traffic Engineering";
    //    // uses apply-advanced;
    //    list template {
    //      key name;
    //      ordered-by user;
    //      description "Network slice policy";
    //      max-elements 15;
    //      leaf name {
    //        description "Express Segment Template Name";
    //        type string;
    //      }
    //      // uses apply-advanced;
    //      leaf statistics-collection-interval {
    //        description "Statistics collection interval.";
    //        type union {
    //          type uint32;
    //          type string {
    //            pattern "<.*>|$.*";
    //          }
    //        }
    //      }
    //      leaf-list policy {
    //        ordered-by user;
    //        description "Policy for matching specific prefixes for TTE";
    //        type jt:policy-algebra;
    //      }
    //      container high-threshold {
    //        description "High-threshold.";
    //        // uses apply-advanced;
    //        leaf bandwidth {
    //          description "Percentage Maximum bandwidth";
    //          units "percent";
    //          type decimal64 {
    //            fraction-digits 9;
    //            range "0 .. 100";
    //          }
    //        }
    //        leaf consecutive-events {
    //          description "Number of consecutive threshold events before action is taken.";
    //          type union {
    //            type uint32;
    //            type string {
    //              pattern "<.*>|$.*";
    //            }
    //          }
    //        }
    //      }
    //      container low-threshold {
    //        description "Low-threshold.";
    //        // uses apply-advanced;
    //        leaf bandwidth {
    //          description "Percentage Minimum bandwidth";
    //          units "percent";
    //          type decimal64 {
    //            fraction-digits 9;
    //            range "0 .. 100";
    //          }
    //        }
    //        leaf consecutive-events {
    //          description "Number of consecutive threshold events before action is taken.";
    //          type union {
    //            type uint32;
    //            type string {
    //              pattern "<.*>|$.*";
    //            }
    //          }
    //        }
    //        leaf tte-path {
    //          description "TTE alternate paths.";
    //          type enumeration {
    //            enum "ti-lfa" {
    //              description "IGP computed TI-LFA alternate paths.";
    //            }
    //            enum "compute-service" {
    //              description "TE computed alternate paths.";
    //            }
    //          }
    //        }
    //      }
    //    }
    //    list interface {
    //      key name;
    //      description "TTE interface options";
    //      leaf name {
    //        description "Interface name";
    //        type union {
    //          type jt:interface-name;
    //          type string {
    //            pattern "<.*>|$.*";
    //          }
    //        }
    //      }
    //      // uses apply-advanced;
    //      leaf template {
    //        description "Template name.";
    //        type string;
    //      }
    //    }
    //    container traceoptions {
    //      description "Trace options for congestion protection";
    //      // uses apply-advanced;
    //      leaf no-remote-trace {
    //        description "Disable remote tracing";
    //        type empty;
    //      }
    //      container file {
    //        description "Trace file information";
    //        leaf filename {
    //          description "Name of file in which to write trace information";
    //          type string {
    //            length "1 .. 1024";
    //          }
    //        }
    //        leaf size {
    //          description "Maximum trace file size";
    //          type string;
    //        }
    //        leaf files {
    //          description "Maximum number of trace files";
    //          default "3";
    //          type union {
    //            type string {
    //              pattern "<.*>|$.*";
    //            }
    //            type uint32 {
    //              range "2 .. 1000";
    //            }
    //          }
    //        }
    //        choice world-readable-choice {
    //          leaf world-readable {
    //            description "Allow any user to read the log file";
    //            type empty;
    //          }
    //          leaf no-world-readable {
    //            description "Don't allow any user to read the log file";
    //            type empty;
    //          }
    //        }
    //        leaf match {
    //          description "Regular expression for lines to be logged";
    //          type jt:regular-expression;
    //        }
    //      }
    //      list flag {
    //        key name;
    //        ordered-by user;
    //        description "Tracing parameters";
    //        leaf name {
    //          type enumeration {
    //            enum "all" {
    //              description "Trace everything";
    //            }
    //            enum "error" {
    //              description "Trace errors";
    //            }
    //            enum "route" {
    //              description "Trace route-related changes";
    //            }
    //            enum "state" {
    //              description "Trace state transitions";
    //            }
    //          }
    //        }
    //        leaf send {
    //          description "Trace transmitted packets";
    //          type empty;
    //        }
    //        leaf receive {
    //          description "Trace received packets";
    //          type empty;
    //        }
    //        leaf detail {
    //          description "Trace detailed information";
    //          type empty;
    //        }
    //        leaf disable {
    //          description "Disable this trace flag";
    //          type empty;
    //        }
    //      }
    //    }
    //    container server {
    //      description "Configuration for the TTE server";
    //      // uses apply-advanced;
    //      container traceoptions {
    //        description "Trace options for congestion protection";
    //        // uses apply-advanced;
    //        leaf no-remote-trace {
    //          description "Disable remote tracing";
    //          type empty;
    //        }
    //        container file {
    //          description "Trace file information";
    //          leaf filename {
    //            description "Name of file in which to write trace information";
    //            type string {
    //              length "1 .. 1024";
    //            }
    //          }
    //          leaf size {
    //            description "Maximum trace file size";
    //            type string;
    //          }
    //          leaf files {
    //            description "Maximum number of trace files";
    //            default "3";
    //            type union {
    //              type string {
    //                pattern "<.*>|$.*";
    //              }
    //              type uint32 {
    //                range "2 .. 1000";
    //              }
    //            }
    //          }
    //          choice world-readable-choice {
    //            leaf world-readable {
    //              description "Allow any user to read the log file";
    //              type empty;
    //            }
    //            leaf no-world-readable {
    //              description "Don't allow any user to read the log file";
    //              type empty;
    //            }
    //          }
    //          leaf match {
    //            description "Regular expression for lines to be logged";
    //            type jt:regular-expression;
    //          }
    //        }
    //        list flag {
    //          key name;
    //          ordered-by user;
    //          description "Tracing parameters";
    //          leaf name {
    //            type enumeration {
    //              enum "all" {
    //                description "Trace everything";
    //              }
    //              enum "error" {
    //                description "Trace errors";
    //              }
    //              enum "state" {
    //                description "Trace state transitions";
    //              }
    //              enum "database" {
    //                description "Trace database operations";
    //              }
    //              enum "flash" {
    //                description "Trace route monitor transactions";
    //              }
    //              enum "japi" {
    //                description "Trace JAPI transactions";
    //              }
    //              enum "event" {
    //                description "Trace events";
    //              }
    //              enum "samples" {
    //                description "Trace bandwidth samples";
    //              }
    //              enum "activation" {
    //                description "Trace activation and deactivation decisions";
    //              }
    //            }
    //          }
    //          leaf send {
    //            description "Trace transmitted packets";
    //            type empty;
    //          }
    //          leaf receive {
    //            description "Trace received packets";
    //            type empty;
    //          }
    //          leaf detail {
    //            description "Trace detailed information";
    //            type empty;
    //          }
    //          leaf disable {
    //            description "Disable this trace flag";
    //            type empty;
    //          }
    //        }
    //      }
    //    }
    //  }
   }
  //  grouping bmp-loc-rib-apath-options {
  //    description "Number of paths to advertise";
  //    // uses apply-advanced;
  //    container path-selection-mode {
  //      description "Configure how to select add-path routes";
  //      // uses apply-advanced;
  //      choice mode {
  //        case case_1 {
  //          leaf all-paths {
  //            description "Advertise all paths allowed by path count";
  //            type empty;
  //          }
  //        }
  //        case case_2 {
  //          leaf equal-cost-paths {
  //            description "Advertise equal cost paths";
  //            type empty;
  //          }
  //        }
  //      }
  //    }
  //    leaf path-count {
  //      description "Number of paths to advertise";
  //      type union {
  //        type string {
  //          pattern "<.*>|$.*";
  //        }
  //        type int32 {
  //          range "2 .. 64";
  //        }
  //      }
  //    }
  //    leaf multipath {
  //      description "Include multipath contributor routes";
  //      type empty;
  //    }
  //  }
  //  grouping dynamic_tunnel_type {
  //    description "Dynamic tunnel definition";
  //    leaf name {
  //      description "Tunnel name";
  //      type string {
  //      }
  //    }
  //    // uses apply-advanced;
  //    leaf source-address {
  //      description "Tunnel source address";
  //      type jt:ipaddr;
  //    }
  //    choice tunnel-type {
  //      case case_1 {
  //        list rsvp-te {
  //          key name;
  //          ordered-by user;
  //          description "RSVP-TE point-to-point LSP";
  //          leaf name {
  //            description "Configure multiple entries for RSVP tunnel";
  //            type string;
  //          }
  //          // uses apply-advanced;
  //          container label-switched-path-template {
  //            description "Template for dynamic point-to-point LSP parameters";
  //            // uses apply-advanced;
  //            choice dynamic-template {
  //              case case_1 {
  //                leaf template-name {
  //                  description "Name of point-to-point LSP template";
  //                  type string {
  //                  }
  //                }
  //              }
  //              case case_2 {
  //                leaf default-template {
  //                  description "Use default parameters";
  //                  type empty;
  //                }
  //              }
  //            }
  //          }
  //          list destination-networks {
  //            key name;
  //            ordered-by user;
  //            description "Create tunnels for routes in these destination networks";
  //            uses app_network_type;
  //          }
  //        }
  //      }
  //      case case_2 {
  //        container spring-te {
  //          description "SPRING-TE LSP's";
  //          // uses apply-advanced;
  //          leaf use-transport-class {
  //            description "Install dynamic-tunnel routes via transport class RIBs";
  //            type empty;
  //          }
  //          list source-routing-path-template {
  //            key name;
  //            ordered-by user;
  //            description "Template color mapping for SPRING-TE dynamic LSP parameters";
  //            uses spring-te-template-map;
  //          }
  //          list destination-networks {
  //            key name;
  //            ordered-by user;
  //            description "Create tunnels for routes in these destination networks";
  //            uses app_network_type;
  //          }
  //        }
  //      }
  //      case case_3 {
  //        leaf gre {
  //          description "Generic routing encapsulation type for IPv4";
  //          type empty;
  //        }
  //      }
  //      case case_4 {
  //        leaf udp {
  //          description "UDP encapsulation type for IPv4";
  //          type empty;
  //        }
  //      }
  //      case case_5 {
  //        leaf bgp-signal {
  //          description "BGP signals the encapsulation type for IPv4";
  //          type empty;
  //        }
  //      }
  //      case case_6 {
  //        leaf ipip {
  //          description "IPIP encapsulation type for IPv4";
  //          type empty;
  //        }
  //      }
  //      case case_7 {
  //        leaf srv6 {
  //          description "SRv6 encapsulation type for IPv6";
  //          type empty;
  //        }
  //      }
  //    }
  //    list destination-networks {
  //      key name;
  //      ordered-by user;
  //      description "Create tunnels for routes in these destination networks";
  //      uses network_type;
  //    }
  //  }
  //  grouping app_network_type {
  //    leaf name {
  //      description "Network prefix";
  //      type jt:ipprefix;
  //    }
  //    // uses apply-advanced;
  //  }
  //  grouping export-af-obj {
  //    // uses apply-advanced;
  //    choice enable-disable {
  //      case case_1 {
  //        leaf disable {
  //          description "Disable auto-export for address family";
  //          type empty;
  //        }
  //      }
  //    }
  //    container unicast {
  //      description "Unicast routing information";
  //      presence "enable unicast";
  //      uses export-subaf-obj;
  //    }
  //    container multicast {
  //      description "Multicast routing information";
  //      presence "enable multicast";
  //      uses export-subaf-obj;
  //    }
  //    container flow {
  //      description "Flow routing information";
  //      presence "enable flow";
  //      uses export-subaf-obj;
  //    }
  //  }
  //  grouping export-subaf-obj {
  //    // uses apply-advanced;
  //    choice enable-disable {
  //      case case_1 {
  //        leaf disable {
  //          description "Disable instance export";
  //          type empty;
  //        }
  //      }
  //    }
  //    leaf rib-group {
  //      description "Auxiliary rib-group of additional RIBs to consider";
  //      type string;
  //    }
  //  }
  //  grouping fate_sharing_links {
  //    leaf name {
  //      description "Router ID or LAN interface address";
  //      type jt:ipv4addr;
  //    }
  //    leaf to {
  //      description "Point-to-point links";
  //      type jt:ipv4addr;
  //    }
  //  }
  //  grouping flow-interface-group {
  //    leaf group {
  //      description "Interface group ID to match traffic";
  //      type union {
  //        type string {
  //          pattern "<.*>|$.*";
  //        }
  //        type uint32;
  //      }
  //    }
  //    leaf exclude {
  //      description "Don't apply flow-spec filter to traffic on this group";
  //      type empty;
  //    }
  //  }
  //  grouping flow-route-inet {
  //    leaf name {
  //      type string;
  //    }
  //    // uses apply-advanced;
  //    leaf no-install {
  //      description "Don't install firewall filter in forwarding";
  //      type empty;
  //    }
  //    container match {
  //      description "Flow definition";
  //      uses flow-route-qualifier-inet;
  //    }
  //    container then {
  //      description "Actions to take for this flow";
  //      uses flow-route-op;
  //    }
  //  }
  //  grouping flow-route-inet6 {
  //    leaf name {
  //      type string;
  //    }
  //    // uses apply-advanced;
  //    leaf no-install {
  //      description "Don't install firewall filter in forwarding";
  //      type empty;
  //    }
  //    container match {
  //      description "Flow definition";
  //      uses flow-route-qualifier-inet6;
  //    }
  //    container then {
  //      description "Actions to take for this flow";
  //      uses flow-route-op;
  //    }
  //  }
  //  grouping flow-route-op {
  //    // uses apply-advanced;
  //    leaf community {
  //      description "Name of BGP community";
  //      type string;
  //    }
  //    choice flow_op_action {
  //      case case_1 {
  //        leaf accept {
  //          description "Allow traffic through";
  //          type empty;
  //        }
  //      }
  //      case case_2 {
  //        leaf discard {
  //          description "Discard all traffic for this flow";
  //          type empty;
  //        }
  //      }
  //      case case_3 {
  //        leaf rate-limit {
  //          description "Rate in bits/sec to limit the flow traffic";
  //          type string;
  //        }
  //      }
  //    }
  //    leaf routing-instance {
  //      description "Redirect to instance identified via Route Target community";
  //      type string {
  //      }
  //    }
  //    leaf sample {
  //      description "Sample traffic that matches this flow";
  //      type empty;
  //    }
  //    leaf mark {
  //      description "Set DSCP value for traffic that matches this flow";
  //      type union {
  //        type string {
  //          pattern "<.*>|$.*";
  //        }
  //        type uint32 {
  //          range "0 .. 63";
  //        }
  //      }
  //    }
  //    leaf next-term {
  //      description "Continue the filter evaluation after matching this flow";
  //      type empty;
  //    }
  //    choice redirect_op_action {
  //      case case_1 {
  //        leaf-list redirect {
  //          ordered-by user;
  //          description "Redirect(Tunnel) this flow's traffic to given next-hop address";
  //          type jt:ipaddr;
  //        }
  //      }
  //    }
  //  }
  //  grouping flow-route-qualifier-inet {
  //    // uses apply-advanced;
  //    leaf-list protocol {
  //      ordered-by user;
  //      description "IP protocol value";
  //      type string;
  //    }
  //    leaf-list port {
  //      ordered-by user;
  //      type string;
  //    }
  //    leaf-list destination-port {
  //      ordered-by user;
  //      type string;
  //    }
  //    leaf-list source-port {
  //      ordered-by user;
  //      type string;
  //    }
  //    leaf-list tcp-flags {
  //      ordered-by user;
  //      description "TCP flags";
  //      type string;
  //    }
  //    leaf-list packet-length {
  //      ordered-by user;
  //      description "Packet length (0-65535)";
  //      type jt:policy-algebra;
  //    }
  //    leaf-list dscp {
  //      ordered-by user;
  //      description "Differentiated Services (DiffServ) code point (DSCP) (0-63)";
  //      type jt:policy-algebra;
  //    }
  //    leaf-list fragment {
  //      ordered-by user;
  //      type enumeration {
  //        enum "dont-fragment" {
  //          description "Don't Fragment flag is set";
  //        }
  //        enum "not-a-fragment" {
  //          description "Not a fragment";
  //        }
  //        enum "is-fragment" {
  //          description "Fragmented packet";
  //        }
  //        enum "first-fragment" {
  //          description "First fragment";
  //        }
  //        enum "last-fragment" {
  //          description "Last fragment";
  //        }
  //      }
  //    }
  //    leaf destination {
  //      description "Destination prefix for this traffic flow";
  //      type jt:ipv4prefix;
  //    }
  //    leaf source {
  //      description "Source prefix for this traffic flow";
  //      type jt:ipv4prefix;
  //    }
  //    leaf-list icmp-code {
  //      ordered-by user;
  //      description "ICMP message code";
  //      type string;
  //    }
  //    leaf-list icmp-type {
  //      ordered-by user;
  //      description "ICMP message type";
  //      type string;
  //    }
  //  }
  //  grouping flow-route-qualifier-inet6 {
  //    // uses apply-advanced;
  //    leaf-list protocol {
  //      ordered-by user;
  //      description "IP protocol value";
  //      type string;
  //    }
  //    leaf-list port {
  //      ordered-by user;
  //      type string;
  //    }
  //    leaf-list destination-port {
  //      ordered-by user;
  //      type string;
  //    }
  //    leaf-list source-port {
  //      ordered-by user;
  //      type string;
  //    }
  //    leaf-list tcp-flags {
  //      ordered-by user;
  //      description "TCP flags";
  //      type string;
  //    }
  //    leaf-list packet-length {
  //      ordered-by user;
  //      description "Packet length (0-65535)";
  //      type jt:policy-algebra;
  //    }
  //    leaf-list dscp {
  //      ordered-by user;
  //      description "Differentiated Services (DiffServ) code point (DSCP) (0-63)";
  //      type jt:policy-algebra;
  //    }
  //    leaf-list fragment {
  //      ordered-by user;
  //      type enumeration {
  //        enum "dont-fragment" {
  //          description "Don't Fragment flag is set";
  //        }
  //        enum "not-a-fragment" {
  //          description "Not a fragment";
  //        }
  //        enum "is-fragment" {
  //          description "Fragmented packet";
  //        }
  //        enum "first-fragment" {
  //          description "First fragment";
  //        }
  //        enum "last-fragment" {
  //          description "Last fragment";
  //        }
  //      }
  //    }
  //    container destination {
  //      description "Destination prefix for this traffic flow";
  //      presence "enable destination";
  //      uses flow-prefix-with-offset;
  //    }
  //    container source {
  //      description "Source prefix for this traffic flow";
  //      presence "enable source";
  //      uses flow-prefix-with-offset;
  //    }
  //    leaf-list icmp6-type {
  //      ordered-by user;
  //      description "ICMP message type";
  //      type string;
  //    }
  //    leaf-list icmp6-code {
  //      ordered-by user;
  //      description "ICMP message code";
  //      type string;
  //    }
  //    leaf-list flow-label {
  //      ordered-by user;
  //      description "Flow-label (0-1048575)";
  //      type jt:policy-algebra;
  //    }
  //  }
  //  grouping flow-prefix-with-offset {
  //    leaf prefix {
  //      type jt:ipv6prefix;
  //    }
  //    leaf prefix-offset {
  //      description "Offset from where prefix match will start";
  //      type union {
  //        type uint32;
  //        type string {
  //          pattern "<.*>|$.*";
  //        }
  //      }
  //    }
  //  }
  //  grouping flow-rule-inet {
  //    leaf name {
  //      type string;
  //    }
  //    // uses apply-advanced;
  //    leaf no-install {
  //      description "Don't install firewall filter in forwarding";
  //      type empty;
  //    }
  //    container match {
  //      description "Flow definition";
  //      uses flow-rule-qualifier-inet;
  //    }
  //    container then {
  //      description "Actions to take for this flow";
  //      uses flow-rule-op;
  //    }
  //  }
  //  grouping flow-rule-inet6 {
  //    leaf name {
  //      type string;
  //    }
  //    // uses apply-advanced;
  //    leaf no-install {
  //      description "Don't install firewall filter in forwarding";
  //      type empty;
  //    }
  //    container match {
  //      description "Flow definition";
  //      uses flow-rule-qualifier-inet6;
  //    }
  //    container then {
  //      description "Actions to take for this flow";
  //      uses flow-rule-op;
  //    }
  //  }
  //  grouping flow-rule-op {
  //    // uses apply-advanced;
  //    choice flow_op_action {
  //      case case_1 {
  //        leaf accept {
  //          description "Allow traffic through";
  //          type empty;
  //        }
  //      }
  //      case case_2 {
  //        leaf discard {
  //          description "Discard all traffic for this flow";
  //          type empty;
  //        }
  //      }
  //      case case_3 {
  //        leaf rate-limit {
  //          description "Rate in bits/sec to limit the flow traffic";
  //          type string;
  //        }
  //      }
  //    }
  //  }
  //  grouping flow-rule-qualifier-inet {
  //    // uses apply-advanced;
  //    leaf-list protocol {
  //      ordered-by user;
  //      description "IP protocol value";
  //      type string;
  //    }
  //    leaf-list port {
  //      ordered-by user;
  //      type string;
  //    }
  //    leaf-list destination-port {
  //      ordered-by user;
  //      type string;
  //    }
  //    leaf-list source-port {
  //      ordered-by user;
  //      type string;
  //    }
  //    leaf destination {
  //      description "Destination prefix for this traffic flow";
  //      type jt:ipv4prefix;
  //    }
  //    leaf source {
  //      description "Source prefix for this traffic flow";
  //      type jt:ipv4prefix;
  //    }
  //  }
  //  grouping flow-rule-qualifier-inet6 {
  //    // uses apply-advanced;
  //    leaf-list protocol {
  //      ordered-by user;
  //      description "IP protocol value";
  //      type string;
  //    }
  //    leaf-list port {
  //      ordered-by user;
  //      type string;
  //    }
  //    leaf-list destination-port {
  //      ordered-by user;
  //      type string;
  //    }
  //    leaf-list source-port {
  //      ordered-by user;
  //      type string;
  //    }
  //    container destination {
  //      description "Destination prefix for this traffic flow";
  //      presence "enable destination";
  //      uses flow-prefix-with-offset;
  //    }
  //    container source {
  //      description "Source prefix for this traffic flow";
  //      presence "enable source";
  //      uses flow-prefix-with-offset;
  //    }
  //  }
  //  grouping flow-validation {
  //    // uses apply-advanced;
  //    container traceoptions {
  //      description "Trace options";
  //      uses flow-dep-traceoptions;
  //    }
  //  }
  //  grouping flow-dep-traceoptions {
  //    // uses apply-advanced;
  //    container file {
  //      description "Trace file options";
  //      leaf filename {
  //        description "Name of file in which to write trace information";
  //        type string {
  //          length "1 .. 1024";
  //        }
  //      }
  //      leaf replace {
  //        description "Replace trace file rather than appending to it";
  //        status deprecated;
  //        type empty;
  //      }
  //      leaf size {
  //        description "Maximum trace file size";
  //        type string;
  //      }
  //      leaf files {
  //        description "Maximum number of trace files";
  //        default "10";
  //        type union {
  //          type string {
  //            pattern "<.*>|$.*";
  //          }
  //          type uint32 {
  //            range "2 .. 1000";
  //          }
  //        }
  //      }
  //      leaf no-stamp {
  //        description "Do not timestamp trace file";
  //        status deprecated;
  //        type empty;
  //      }
  //      choice world-readable-choice {
  //        leaf world-readable {
  //          description "Allow any user to read the log file";
  //          type empty;
  //        }
  //        leaf no-world-readable {
  //          description "Don't allow any user to read the log file";
  //          type empty;
  //        }
  //      }
  //    }
  //    list flag {
  //      key name;
  //      ordered-by user;
  //      description "Tracing parameters";
  //      leaf name {
  //        type enumeration {
  //          enum "resolution" {
  //            description "Trace flow to unicast route resolution";
  //          }
  //          enum "flash" {
  //            description "Trace flash processing";
  //          }
  //          enum "route" {
  //            description "Trace routing information";
  //          }
  //          enum "normal" {
  //            description "Trace normal events";
  //          }
  //          enum "general" {
  //            description "Trace general events";
  //          }
  //          enum "state" {
  //            description "Trace state transitions";
  //          }
  //          enum "policy" {
  //            description "Trace policy processing";
  //          }
  //          enum "task" {
  //            description "Trace routing protocol task processing";
  //          }
  //          enum "timer" {
  //            description "Trace routing protocol timer processing";
  //          }
  //          enum "all" {
  //            description "Trace everything";
  //          }
  //        }
  //      }
  //      leaf send {
  //        description "Trace transmitted packets";
  //        type empty;
  //      }
  //      leaf receive {
  //        description "Trace received packets";
  //        type empty;
  //      }
  //      leaf detail {
  //        description "Trace detailed information";
  //        type empty;
  //      }
  //      leaf disable {
  //        description "Disable this trace flag";
  //        type empty;
  //      }
  //      container filter {
  //        presence "enable filter";
  //        description "Filter to apply to tracing";
  //        leaf match-on {
  //          description "Argument on which to match";
  //          type enumeration {
  //            enum "prefix" {
  //              description "Filter based on prefix";
  //            }
  //            enum "route-attribute" {
  //              description "Filter based on route attributes";
  //            }
  //          }
  //        }
  //        leaf-list policy {
  //          ordered-by user;
  //          description "Filter policy";
  //          type jt:policy-algebra;
  //        }
  //      }
  //    }
  //  }
  //  grouping forwarding-table-type {
  //    description "Forwarding table management options";
  //    // uses apply-advanced;
  //    leaf oc-tlv-support {
  //      description "Send origin protocol and network-instance for route and stream next-hop origin protocol";
  //      type empty;
  //    }
  //    leaf remnant-holdtime {
  //      description "Time to hold inherited routes from FIB";
  //      type union {
  //        type string {
  //          pattern "<.*>|$.*";
  //        }
  //        type uint32 {
  //          range "0 .. 10000";
  //        }
  //      }
  //    }
  //    leaf send-gr-issu-message {
  //      description "Simulate gr-issu message reception from rpd-agent";
  //      type union {
  //        type string {
  //          pattern "<.*>|$.*";
  //        }
  //        type uint32 {
  //          range "1 .. 65535";
  //        }
  //      }
  //    }
  //    leaf chain-composite-max-label-count {
  //      description "Maximum labels inside chain composite for the platform.";
  //      type union {
  //        type string {
  //          pattern "<.*>|$.*";
  //        }
  //        type uint32 {
  //          range "1 .. 16";
  //        }
  //      }
  //    }
  //    leaf krt-nexthop-ack {
  //      description "Enable kernel nexthop ack";
  //      type empty;
  //    }
  //    leaf krt-nexthop-ack-timeout {
  //      description "Kernel nexthop ack timeout interval";
  //      type union {
  //        type string {
  //          pattern "<.*>|$.*";
  //        }
  //        type uint32 {
  //          range "1 .. 400";
  //        }
  //      }
  //    }
  //    leaf srv6-chain-merge {
  //      description "Enable merging of srv6 chain nexthops";
  //      type empty;
  //    }
  //    choice session-id-change-limiter-indirect-choice {
  //      leaf session-id-change-limiter-indirect {
  //        description "Enable indirect nexthop to limit session-id change propagation";
  //        type empty;
  //      }
  //      leaf no-session-id-change-limiter-indirect {
  //        description "Don't enable indirect nexthop to limit session-id change propagation";
  //        type empty;
  //      }
  //    }
  //    container consistency-checking {
  //      description "RIB/FIB consistency checking";
  //      status deprecated;
  //      // uses apply-advanced;
  //      choice enable-disable {
  //        case case_1 {
  //          leaf enable {
  //            description "Enable consistency checking";
  //            type empty;
  //          }
  //        }
  //        case case_2 {
  //          leaf disable {
  //            description "Disable consistency checking";
  //            type empty;
  //          }
  //        }
  //      }
  //      leaf period {
  //        description "Periodicity of scan in seconds";
  //        type union {
  //          type string {
  //            pattern "<.*>|$.*";
  //          }
  //          type uint32 {
  //            range "30 .. 4294967295";
  //          }
  //        }
  //      }
  //      leaf threshold {
  //        description "Mismatch threshold until complaint";
  //        type union {
  //          type uint32;
  //          type string {
  //            pattern "<.*>|$.*";
  //          }
  //        }
  //      }
  //    }
  //    leaf-list export {
  //      ordered-by user;
  //      description "Export policy";
  //      type jt:policy-algebra;
  //    }
  //    leaf dynamic-list-next-hop {
  //      description "Dynamic next-hop mode for EVPN";
  //      type empty;
  //    }
  //    container evpn-egress-link-protection {
  //      presence "enable evpn-egress-link-protection";
  //      description "EVPN PE-CE egress link failure protection";
  //      // uses apply-advanced;
  //    }
  //    leaf vpls-hotstandby-convergence {
  //      description "Enable convergence improvements for VPLS hot-standby";
  //      type empty;
  //    }
  //    container egress-chaining {
  //      description "Enable egress-chaining";
  //      // uses apply-advanced;
  //      leaf spring-te {
  //        description "Enable egress-chaining for SPRING-TE routes";
  //        type empty;
  //      }
  //    }
  //    leaf evpn-aliasing-optimize {
  //      description "EVPN Aliasing convergence improvement";
  //      type empty;
  //    }
  //    choice ecmp-fast-reroute-choice {
  //      leaf ecmp-fast-reroute {
  //        description "Enable fast reroute for ECMP next hops";
  //        type empty;
  //      }
  //      leaf no-ecmp-fast-reroute {
  //        description "Don't enable fast reroute for ECMP next hops";
  //        type empty;
  //      }
  //    }
  //    choice indirect-next-hop-choice {
  //      leaf indirect-next-hop {
  //        description "Install indirect next hops in Packet Forwarding Engine";
  //        type empty;
  //      }
  //      leaf no-indirect-next-hop {
  //        description "Don't install indirect next hops in Packet Forwarding Engine";
  //        type empty;
  //      }
  //    }
  //    choice route-ack-converge-choice {
  //      leaf route-ack-converge {
  //        description "Enable the route ack convergence feature";
  //        type empty;
  //      }
  //      leaf no-route-ack-converge {
  //        description "Don't enable the route ack convergence feature";
  //        type empty;
  //      }
  //    }
  //    leaf long-live-ack-timer-val {
  //      description "Set default long live acknowledgement timer value";
  //      type union {
  //        type string {
  //          pattern "<.*>|$.*";
  //        }
  //        type uint32 {
  //          range "1 .. 65535";
  //        }
  //      }
  //    }
  //    list rib {
  //      key name;
  //      ordered-by user;
  //      status deprecated;
  //      leaf name {
  //        type string;
  //      }
  //    }
  //    leaf unicast-reverse-path {
  //      description "Unicast reverse path (RP) verification";
  //      type enumeration {
  //        enum "active-paths" {
  //          description "Consider active paths when performing RP verification";
  //        }
  //        enum "feasible-paths" {
  //          description "Consider all feasible paths for RP verification";
  //        }
  //      }
  //    }
  //    container ip-tunnel-rpf-check {
  //      presence "enable ip-tunnel-rpf-check";
  //      description "IP tunnel Reverse Path Forwarding Check";
  //      // uses apply-advanced;
  //      leaf mode {
  //        default "strict";
  //        type enumeration {
  //          enum "strict" {
  //            description "Strict mode for rpf-check(Default)";
  //          }
  //          enum "loose" {
  //            description "Loose mode for rpf-check";
  //          }
  //        }
  //      }
  //      leaf fail-filter {
  //        description "Fail filter name for RPF check(family inet|inet6|any)";
  //        type string {
  //        }
  //      }
  //    }
  //   //  list source-class {
  //   //    key name;
  //   //    ordered-by user;
  //   //    description "Source class filters";
  //   //    uses source-class-filters;
  //   //  }
  //    list destination-class {
  //      key name;
  //      ordered-by user;
  //      description "Destination class filters";
  //      uses destination-class-filters;
  //    }
  //    leaf transit-lsp-statistics-from-route {
  //      description "Enable LSP statistics collection from the route";
  //      type empty;
  //    }
  //    container chained-composite-next-hop {
  //      description "Next-hop chaining mode";
  //      // uses apply-advanced;
  //      container ingress {
  //        description "Ingress LSP nexthop settings";
  //        // uses apply-advanced;
  //        choice l2vpn-choice {
  //          leaf l2vpn {
  //            description "Create composite-chained nexthops for ingress l2vpn LSPs";
  //            type empty;
  //          }
  //          leaf no-l2vpn {
  //            description "Don't create composite-chained nexthops for ingress l2vpn LSPs";
  //            type empty;
  //          }
  //        }
  //        choice l2ckt-choice {
  //          leaf l2ckt {
  //            description "Create composite-chained nexthops for ingress l2ckt LSPs";
  //            type empty;
  //          }
  //          leaf no-l2ckt {
  //            description "Don't create composite-chained nexthops for ingress l2ckt LSPs";
  //            type empty;
  //          }
  //        }
  //        choice fec129-vpws-choice {
  //          leaf fec129-vpws {
  //            description "Create composite-chained nexthops for ingress fec129-vpws LSPs";
  //            type empty;
  //          }
  //          leaf no-fec129-vpws {
  //            description "Don't create composite-chained nexthops for ingress fec129-vpws LSPs";
  //            type empty;
  //          }
  //        }
  //        choice evpn-choice {
  //          leaf evpn {
  //            description "Create composite-chained nexthops for ingress EVPN LSPs";
  //            type empty;
  //          }
  //          leaf no-evpn {
  //            description "Don't create composite-chained nexthops for ingress EVPN LSPs";
  //            type empty;
  //          }
  //        }
  //        container labeled-bgp {
  //          description "Create composite-chained nexthops for ingress labeled-bgp LSPs";
  //          // uses apply-advanced;
  //          choice inet-choice {
  //            leaf inet {
  //              description "Enable inet labeled-bgp composite nexthop creation";
  //              type empty;
  //            }
  //            leaf no-inet {
  //              description "Don't enable inet labeled-bgp composite nexthop creation";
  //              type empty;
  //            }
  //          }
  //          choice inet6-choice {
  //            leaf inet6 {
  //              description "Enable inet6 labeled-bgp composite nexthop creation";
  //              type empty;
  //            }
  //            leaf no-inet6 {
  //              description "Don't enable inet6 labeled-bgp composite nexthop creation";
  //              type empty;
  //            }
  //          }
  //        }
  //        container l3vpn {
  //          presence "enable l3vpn";
  //          description "Create composite-chained nexthops for ingress l3vpn LSPs";
  //          leaf extended-space {
  //            description "Allocate in extended-space for scalability";
  //            type empty;
  //          }
  //        }
  //        choice ldp-choice {
  //          leaf ldp {
  //            description "Create chained-composite nexthops to support segmentation LDP tunnels";
  //            type empty;
  //          }
  //          leaf no-ldp {
  //            description "Don't create chained-composite nexthops to support segmentation LDP tunnels";
  //            type empty;
  //          }
  //        }
  //        leaf static {
  //          description "Create composite-chained nexthops for static LSPs";
  //          type empty;
  //        }
  //      }
  //      container transit {
  //        description "Transit LSP nexthops settings";
  //        // uses apply-advanced;
  //        choice l2vpn-choice {
  //          leaf l2vpn {
  //            description "Create composite-chained nexthops for transit l2vpn LSPs";
  //            type empty;
  //          }
  //          leaf no-l2vpn {
  //            description "Don't create composite-chained nexthops for transit l2vpn LSPs";
  //            type empty;
  //          }
  //        }
  //        choice l3vpn-choice {
  //          leaf l3vpn {
  //            description "Create composite-chained nexthops for transit l3vpn LSPs";
  //            type empty;
  //          }
  //          leaf no-l3vpn {
  //            description "Don't create composite-chained nexthops for transit l3vpn LSPs";
  //            type empty;
  //          }
  //        }
  //        choice labeled-bgp-choice {
  //          leaf labeled-bgp {
  //            description "Create composite-chained nexthops for transit labeled BGP routes";
  //            type empty;
  //          }
  //          leaf no-labeled-bgp {
  //            description "Don't create composite-chained nexthops for transit labeled BGP routes";
  //            type empty;
  //          }
  //        }
  //        choice static-choice {
  //          leaf static {
  //            description "Create composite-chained nexthops for static LSPs";
  //            type empty;
  //          }
  //          leaf no-static {
  //            description "Don't create composite-chained nexthops for static LSPs";
  //            type empty;
  //          }
  //        }
  //        choice rsvp-choice {
  //          leaf rsvp {
  //            description "Create composite-chained nexthops for RSVP LSPs";
  //            type empty;
  //          }
  //          leaf no-rsvp {
  //            description "Don't create composite-chained nexthops for RSVP LSPs";
  //            type empty;
  //          }
  //        }
  //        choice rsvp-p2mp-choice {
  //          leaf rsvp-p2mp {
  //            description "Create composite-chained nexthops for RSVP p2mp LSPs";
  //            type empty;
  //          }
  //          leaf no-rsvp-p2mp {
  //            description "Don't create composite-chained nexthops for RSVP p2mp LSPs";
  //            type empty;
  //          }
  //        }
  //        choice express-segments-choice {
  //          leaf express-segments {
  //            description "Create composite-chained nexthops for Express Segments";
  //            type empty;
  //          }
  //          leaf no-express-segments {
  //            description "Don't create composite-chained nexthops for Express Segments";
  //            type empty;
  //          }
  //        }
  //        choice ldp-choice {
  //          leaf ldp {
  //            description "Create composite-chained nexthops for LDP LSPs";
  //            type empty;
  //          }
  //          leaf no-ldp {
  //            description "Don't create composite-chained nexthops for LDP LSPs";
  //            type empty;
  //          }
  //        }
  //        choice ldp-p2mp-choice {
  //          leaf ldp-p2mp {
  //            description "Create composite-chained nexthops for LDP P2MP LSPs";
  //            type empty;
  //          }
  //          leaf no-ldp-p2mp {
  //            description "Don't create composite-chained nexthops for LDP P2MP LSPs";
  //            type empty;
  //          }
  //        }
  //        choice labeled-isis-choice {
  //          leaf labeled-isis {
  //            description "Create composite-chained nexthops for labeled ISIS routes";
  //            type empty;
  //          }
  //          leaf no-labeled-isis {
  //            description "Don't create composite-chained nexthops for labeled ISIS routes";
  //            type empty;
  //          }
  //        }
  //      }
  //    }
  //    container fib-next-hop-split {
  //      description "Split nexthop to chain nexthop when installing fom rib to fib";
  //      // uses apply-advanced;
  //      leaf labeled-isis {
  //        description "Create composite-chained nexthops for labeled ISIS routes";
  //        type empty;
  //      }
  //    }
  //    container fib-agent {
  //      presence "enable fib-agent";
  //      description "Configure fib-agent parameters";
  //      // uses apply-advanced;
  //      leaf address {
  //        description "IP address of the FIB agent";
  //        default "127.0.0.1";
  //        type jt:ipaddr;
  //      }
  //      leaf port {
  //        description "TCP port of the FIB agent";
  //        default "2620";
  //        type union {
  //          type string {
  //            pattern "<.*>|$.*";
  //          }
  //          type uint32 {
  //            range "1 .. 65535";
  //          }
  //        }
  //      }
  //      leaf protocol-id {
  //        description "Protocol ID to be used for programming routes";
  //        default "22";
  //        type union {
  //          type string {
  //            pattern "<.*>|$.*";
  //          }
  //          type uint32 {
  //            range "0 .. 255";
  //          }
  //        }
  //      }
  //    }
  //    list channel {
  //      key name;
  //      ordered-by user;
  //      description "Configure fib-channel parameters";
  //      leaf name {
  //        description "FIB Channel Name";
  //        type string;
  //      }
  //      // uses apply-advanced;
  //      container protocol {
  //        presence "enable protocol";
  //        description "Configure fib-channel protocol";
  //        // uses apply-advanced;
  //        leaf protocol-type {
  //          type enumeration {
  //            enum "netlink-fpm" {
  //              description "Configure SONiC FIB Channel";
  //            }
  //            enum "gRPC" {
  //              description "Configure vRouter FIB channel.";
  //            }
  //          }
  //        }
  //        leaf destination {
  //          description "Destination of the FIB";
  //          type string;
  //        }
  //        leaf source-id {
  //          description "Source ID to be used for programming routes";
  //          default "22";
  //          type union {
  //            type string {
  //              pattern "<.*>|$.*";
  //            }
  //            type uint32 {
  //              range "0 .. 255";
  //            }
  //          }
  //        }
  //      }
  //      leaf-list export {
  //        ordered-by user;
  //        description "Export policy";
  //        type jt:policy-algebra;
  //      }
  //    }
  //    leaf multicast-composite-delete-defer-timeout {
  //      description "Time to defer multicast composite NH delete operation into FIB";
  //      type union {
  //        type string {
  //          pattern "<.*>|$.*";
  //        }
  //        type uint32 {
  //          range "1 .. 3600";
  //        }
  //      }
  //    }
  //  }
   grouping destination-class-filters {
     leaf name {
       description "Destination class name";
       type string;
     }
     // uses apply-advanced;
     container family {
       description "Protocol family";
       container inet {
         description "Protocol family IPv4 for firewall filter";
         // uses apply-advanced;
         container filter {
           description "Packet filtering";
           // uses apply-advanced;
           leaf filter-name {
             description "Inet Filter name";
             type string;
           }
         }
       }
       container inet6 {
         description "Protocol family IPv6 for firewall filter";
         // uses apply-advanced;
         container filter {
           description "Packet filtering";
           // uses apply-advanced;
           leaf filter-name {
             description "Inet6 Filter name";
             type string;
           }
         }
       }
     }
   }
  //  grouping juniper-sampling-options {
  //    // uses apply-advanced;
  //    choice enable-disable {
  //      case case_1 {
  //        leaf disable {
  //          description "Disable global sampling instance";
  //          type empty;
  //        }
  //      }
  //    }
  //    container traceoptions {
  //      description "Traffic sampling trace options";
  //      uses sampling_traceoptions_type;
  //    }
  //    leaf sample-once {
  //      description "Sample the packet for active-monitoring only once";
  //      type empty;
  //    }
  //    leaf pre-rewrite-tos {
  //      description "Sample the packet retaining tos value before normalization";
  //      type empty;
  //    }
  //    container input {
  //      description "Traffic Sampling data acquisition";
  //      uses sampling_input_type;
  //    }
  //    container output {
  //      description "Traffic sampling data disposition";
  //      status deprecated;
  //      uses sampling_output_type;
  //    }
  //    container family {
  //      description "Address family of packets to sample";
  //      container inet {
  //        description "Sample IPv4 packets";
  //        // uses apply-advanced;
  //        choice enable-disable {
  //          case case_1 {
  //            leaf disable {
  //              description "Disable sampling family inet";
  //              type empty;
  //            }
  //          }
  //        }
  //        container input {
  //          description "Settings for sampling of input packets";
  //          uses sampling_family_input_type;
  //        }
  //        container output {
  //          description "Traffic sampling data disposition";
  //          uses sampling_instance_inet_global_output_type;
  //        }
  //      }
  //      container inet6 {
  //        description "Sample IPv6 packets";
  //        // uses apply-advanced;
  //        choice enable-disable {
  //          case case_1 {
  //            leaf disable {
  //              description "Disable sampling family inet6";
  //              type empty;
  //            }
  //          }
  //        }
  //        container input {
  //          description "Settings for sampling of input packets";
  //          uses sampling_family_input_type;
  //        }
  //        container output {
  //          description "Traffic sampling data disposition";
  //          uses sampling_family_inet6_output_type;
  //        }
  //      }
  //      container mpls {
  //        description "Sample mpls packets";
  //        // uses apply-advanced;
  //        choice enable-disable {
  //          case case_1 {
  //            leaf disable {
  //              description "Disable sampling family mpls";
  //              type empty;
  //            }
  //          }
  //        }
  //        container input {
  //          description "Settings for sampling of input packets";
  //          uses sampling_family_input_type;
  //        }
  //        container output {
  //          description "Traffic sampling data disposition";
  //          uses sampling_global_mpls_output_type;
  //        }
  //      }
  //    }
  //    list instance {
  //      key name;
  //      ordered-by user;
  //      description "Instance of sampling parameters";
  //      leaf name {
  //        description "Name for sampling instance";
  //        type string;
  //      }
  //      // uses apply-advanced;
  //      choice enable-disable {
  //        case case_1 {
  //          leaf disable {
  //            description "Disable sampling instance";
  //            type empty;
  //          }
  //        }
  //      }
  //      container input {
  //        description "Traffic Sampling data acquisition";
  //        uses sampling_instance_input_type;
  //      }
  //      container family {
  //        description "Address family of packets to sample";
  //        container inet {
  //          description "Sample IPv4 packets";
  //          // uses apply-advanced;
  //          choice enable-disable {
  //            case case_1 {
  //              leaf disable {
  //                description "Disable instance family inet";
  //                status deprecated;
  //                type empty;
  //              }
  //            }
  //          }
  //          container input {
  //            description "Settings for sampling of input packets";
  //            uses sampling_family_input_type;
  //          }
  //          container output {
  //            description "Traffic sampling data disposition";
  //            uses sampling_instance_inet_output_type;
  //          }
  //        }
  //        container inet6 {
  //          description "Sample IPv6 packets";
  //          // uses apply-advanced;
  //          choice enable-disable {
  //            case case_1 {
  //              leaf disable {
  //                description "Disable instance family inet6";
  //                status deprecated;
  //                type empty;
  //              }
  //            }
  //          }
  //          container input {
  //            description "Settings for sampling of input packets";
  //            uses sampling_family_input_type;
  //          }
  //          container output {
  //            description "Traffic sampling data disposition";
  //            uses sampling_instance_inet6_output_type;
  //          }
  //        }
  //        container mpls {
  //          description "Sample mpls packets";
  //          // uses apply-advanced;
  //          choice enable-disable {
  //            case case_1 {
  //              leaf disable {
  //                description "Disable instance family mpls";
  //                status deprecated;
  //                type empty;
  //              }
  //            }
  //          }
  //          container input {
  //            description "Settings for sampling of input packets";
  //            uses sampling_family_input_type;
  //          }
  //          container output {
  //            description "Traffic sampling data disposition";
  //            uses sampling_instance_mpls_output_type;
  //          }
  //        }
  //        container vpls {
  //          description "Sample vpls packets";
  //          status deprecated;
  //          // uses apply-advanced;
  //          choice enable-disable {
  //            case case_1 {
  //              leaf disable {
  //                description "Disable instance family vpls";
  //                type empty;
  //              }
  //            }
  //          }
  //          container input {
  //            description "Settings for sampling of input packets";
  //            uses sampling_family_input_type;
  //          }
  //          container output {
  //            description "Traffic sampling data disposition";
  //            uses sampling_instance_vpls_output_type;
  //          }
  //        }
  //        container bridge {
  //          description "Sample bridge packets";
  //          // uses apply-advanced;
  //          choice enable-disable {
  //            case case_1 {
  //              leaf disable {
  //                description "Disable instance family bridge";
  //                type empty;
  //              }
  //            }
  //          }
  //          container input {
  //            description "Settings for sampling of input packets";
  //            uses sampling_family_input_type;
  //          }
  //          container output {
  //            description "Traffic sampling data disposition";
  //            uses sampling_instance_bridge_output_type;
  //          }
  //        }
  //      }
  //    }
  //    container jflow-service {
  //      description "Jflow service configuration";
  //      // uses apply-advanced;
  //      container traceoptions {
  //        description "Jflow service trace options";
  //        uses jflow_service_traceoptions;
  //      }
  //    }
  //    container route-record {
  //      description "Sampling route record configuration";
  //      // uses apply-advanced;
  //      container traceoptions {
  //        description "Sampling route record trace options";
  //        uses route_record_traceoptions;
  //      }
  //    }
  //  }
  //  grouping jflow_service_traceoptions {
  //    description "Traceoptions for jflow-service";
  //    // uses apply-advanced;
  //    leaf no-remote-trace {
  //      description "Disable remote tracing";
  //      type empty;
  //    }
  //    container file {
  //      description "Trace file information";
  //      leaf filename {
  //        description "Name of file in which to write trace information";
  //        type string {
  //          length "1 .. 1024";
  //        }
  //      }
  //      leaf size {
  //        description "Maximum trace file size";
  //        type string;
  //      }
  //      leaf files {
  //        description "Maximum number of trace files";
  //        default "3";
  //        type union {
  //          type string {
  //            pattern "<.*>|$.*";
  //          }
  //          type uint32 {
  //            range "2 .. 1000";
  //          }
  //        }
  //      }
  //      choice world-readable-choice {
  //        leaf world-readable {
  //          description "Allow any user to read the log file";
  //          type empty;
  //        }
  //        leaf no-world-readable {
  //          description "Don't allow any user to read the log file";
  //          type empty;
  //        }
  //      }
  //      leaf match {
  //        description "Regular expression for lines to be logged";
  //        type jt:regular-expression;
  //      }
  //    }
  //    leaf level {
  //      description "Level of debugging output";
  //      default "error";
  //      type enumeration {
  //        enum "error" {
  //          description "Match error conditions";
  //        }
  //        enum "warning" {
  //          description "Match warning messages";
  //        }
  //        enum "notice" {
  //          description "Match conditions that should be handled specially";
  //        }
  //        enum "info" {
  //          description "Match informational messages";
  //        }
  //        enum "verbose" {
  //          description "Match verbose messages";
  //        }
  //        enum "all" {
  //          description "Match all levels";
  //        }
  //      }
  //    }
  //    list flag {
  //      key name;
  //      ordered-by user;
  //      description "Area of jflow-service to enable debuging output";
  //      leaf name {
  //        type enumeration {
  //          enum "parse" {
  //            description "Trace parsing code";
  //          }
  //          enum "rtsock" {
  //            description "Trace rtsock code";
  //          }
  //          enum "sm" {
  //            description "Trace State machine code";
  //          }
  //          enum "all" {
  //            description "Trace all area of jflow-service code";
  //          }
  //        }
  //      }
  //    }
  //  }
  //  grouping junos_hash_key {
  //    description "Select data used in the hash key";
  //    // uses apply-advanced;
  //    container hash-seed {
  //      presence "enable hash-seed";
  //      description "Hash seed";
  //      // uses apply-advanced;
  //      leaf seed-value {
  //        description "Hash seed value";
  //        type union {
  //          type string {
  //            pattern "<.*>|$.*";
  //          }
  //          type uint32 {
  //            range "0 .. 4294967295";
  //          }
  //        }
  //      }
  //    }
  //    container family {
  //      description "Protocol family";
  //      container fcoe {
  //        description "FCoE protocol family";
  //        // uses apply-advanced;
  //        container ethernet-interfaces {
  //          description "FCoE hash-key configuration on ethernet interfaces";
  //          // uses apply-advanced;
  //          leaf oxid {
  //            description "Originator Exchange ID";
  //            type enumeration {
  //              enum "enable" {
  //                description "Include Originator Exchange ID in the hash key";
  //              }
  //              enum "disable" {
  //                description "Do not include Originator Exchange ID in the hash key";
  //              }
  //            }
  //          }
  //        }
  //        container fabric-interfaces {
  //          description "FCoE hash-key configuration on fabric interfaces";
  //          // uses apply-advanced;
  //          leaf oxid {
  //            description "Originator Exchange ID";
  //            type enumeration {
  //              enum "enable" {
  //                description "Include Originator Exchange ID in the hash key";
  //              }
  //              enum "disable" {
  //                description "Do not include Originator Exchange ID in the hash key";
  //              }
  //            }
  //          }
  //        }
  //      }
  //      container inet {
  //        description "IPv4 protocol family";
  //        // uses apply-advanced;
  //        container layer-3 {
  //          presence "enable layer-3";
  //          description "Include Layer 3 (IP) data in the hash key";
  //          // uses apply-advanced;
  //          leaf destination-address {
  //            description "Include IP destination address in the hash key";
  //            type empty;
  //          }
  //        }
  //        container layer-4 {
  //          presence "enable layer-4";
  //          description "Include Layer 4 (TCP or UDP) data in the hash key";
  //          // uses apply-advanced;
  //          leaf gtp-tunnel-endpoint-identifier {
  //            description "Include GTP TEID in the hash key";
  //            type empty;
  //          }
  //        }
  //        container symmetric-hash {
  //          presence "enable symmetric-hash";
  //          description "Create symmetric hash-key with source & destination ports";
  //          // uses apply-advanced;
  //          leaf complement {
  //            description "Create complement of symmetric hash-key";
  //            type empty;
  //          }
  //        }
  //        leaf no-incoming-port {
  //          description "Exclude incoming port from the hash key";
  //          type empty;
  //        }
  //      }
  //      container inet6 {
  //        description "IPv6 protocol family";
  //        // uses apply-advanced;
  //        container layer-3 {
  //          presence "enable layer-3";
  //          description "Include Layer 3 (IP) data in the hash key";
  //          // uses apply-advanced;
  //          leaf destination-address {
  //            description "Include IP destination address in the hash key";
  //            type empty;
  //          }
  //          leaf incoming-interface-index {
  //            description "Include incoming interface index in the hash key";
  //            type empty;
  //          }
  //          leaf next-header {
  //            description "Include IP Next Header field in the hash key";
  //            type empty;
  //          }
  //          leaf source-address {
  //            description "Include IP source address in the hash key";
  //            type empty;
  //          }
  //          leaf traffic-class {
  //            description "Include Traffic Class field in the hash key";
  //            type empty;
  //          }
  //          leaf ipv6-flow-label {
  //            description "Include IPV6 flow label field in the hash key";
  //            type empty;
  //          }
  //        }
  //        container layer-4 {
  //          presence "enable layer-4";
  //          description "Include Layer 4 (TCP or UDP) data in the hash key";
  //          // uses apply-advanced;
  //          leaf destination-port {
  //            description "Include IP destination port in the hash key";
  //            type empty;
  //          }
  //          leaf source-port {
  //            description "Include IP source port in the hash key";
  //            type empty;
  //          }
  //          leaf gtp-tunnel-endpoint-identifier {
  //            description "Include GTP TEID in the hash key";
  //            type empty;
  //          }
  //        }
  //        leaf no-incoming-port {
  //          description "Exclude incoming port from the hash key";
  //          type empty;
  //        }
  //      }
  //      container mpls {
  //        description "MPLS protocol family";
  //        // uses apply-advanced;
  //        choice label {
  //          case case_1 {
  //            leaf label-1 {
  //              description "Include the first MPLS label in the hash key";
  //              type empty;
  //            }
  //          }
  //          case case_2 {
  //            leaf all-labels {
  //              description "Include all MPLS labels in hash key";
  //              type empty;
  //            }
  //          }
  //          case case_3 {
  //            leaf no-labels {
  //              description "Exclude all MPLS labels from hash key";
  //              type empty;
  //            }
  //          }
  //          case case_4 {
  //            leaf bottom-label-1 {
  //              description "Include the first MPLS label from bottom-of-stack in the hash key";
  //              type empty;
  //            }
  //          }
  //        }
  //        leaf label-2 {
  //          description "Include the second MPLS label in the hash key";
  //          type empty;
  //        }
  //        leaf label-3 {
  //          description "Include the third MPLS label in the hash key";
  //          type empty;
  //        }
  //        leaf bottom-label-2 {
  //          description "Include the second MPLS label from bottom-of-stack in the hash key";
  //          type empty;
  //        }
  //        leaf bottom-label-3 {
  //          description "Include the third MPLS label from bottom-of-stack in the hash key";
  //          type empty;
  //        }
  //        leaf no-label-1-exp {
  //          description "Omit EXP bits of first MPLS label from the hash key";
  //          type empty;
  //        }
  //        container payload {
  //          description "Include payload data in the hash key";
  //          // uses apply-advanced;
  //          container ether-pseudowire {
  //            presence "enable ether-pseudowire";
  //            description "Load-balance ethernet over ethernet PW";
  //            // uses apply-advanced;
  //            leaf zero-control-word {
  //              description "MPLS ether-pseudowire payload with zero-control-word preceding ethernet packet";
  //              type empty;
  //            }
  //          }
  //          container ip {
  //            presence "enable ip";
  //            description "Include IPv4 or IPv6 payload data in the hash key";
  //            // uses apply-advanced;
  //            choice layer-4-select {
  //              case case_1 {
  //                choice ip-payload {
  //                  case case_1 {
  //                    leaf layer-3-only {
  //                      description "Include only layer-3 IP information";
  //                      type empty;
  //                    }
  //                  }
  //                  case case_2 {
  //                    leaf enable {
  //                      description "Include layer3/4 IP payload in the hash key";
  //                      type empty;
  //                    }
  //                  }
  //                  case case_3 {
  //                    leaf disable {
  //                      description "Exclude layer3/4 IP payload in the hash key";
  //                      type empty;
  //                    }
  //                  }
  //                }
  //              }
  //              case case_2 {
  //                container port-data {
  //                  presence "enable port-data";
  //                  // uses apply-advanced;
  //                  leaf source-msb {
  //                    description "Include the most significant byte of the source port";
  //                    type empty;
  //                  }
  //                  leaf source-lsb {
  //                    description "Include the least significant byte of the source port";
  //                    type empty;
  //                  }
  //                  leaf destination-msb {
  //                    description "Include the most significant byte of the destination port";
  //                    type empty;
  //                  }
  //                  leaf destination-lsb {
  //                    description "Include the least significant byte of the destination port";
  //                    type empty;
  //                  }
  //                }
  //              }
  //            }
  //          }
  //        }
  //      }
  //      container multiservice {
  //        description "Multiservice protocol family";
  //        // uses apply-advanced;
  //        leaf source-mac {
  //          description "Include source MAC address in hash key";
  //          type empty;
  //        }
  //        leaf destination-mac {
  //          description "Include destination MAC address in hash key";
  //          type empty;
  //        }
  //        leaf no-destination-mac-address {
  //          description "Exclude destination MAC address in hash key";
  //          type empty;
  //        }
  //        leaf label-1 {
  //          description "Include the first MPLS label in the hash key";
  //          type empty;
  //        }
  //        leaf label-2 {
  //          description "Include the second MPLS label in the hash key";
  //          type empty;
  //        }
  //        container payload {
  //          description "Include payload data in the hash key";
  //          // uses apply-advanced;
  //          container ip {
  //            description "Include IPv4 payload data in the hash key";
  //            // uses apply-advanced;
  //            container layer-3 {
  //              presence "enable layer-3";
  //              description "Include layer-3 ip info for VPLS/Bridge";
  //              // uses apply-advanced;
  //              choice layer-3-options {
  //                case case_1 {
  //                  leaf source-ip-only {
  //                    description "Include source IP only in hash-key";
  //                    type empty;
  //                  }
  //                }
  //                case case_2 {
  //                  leaf destination-ip-only {
  //                    description "Include desintation IP only in hash-key";
  //                    type empty;
  //                  }
  //                }
  //              }
  //            }
  //            leaf layer-4 {
  //              description "Include layer-4 IP information for VPLS/Bridge";
  //              type empty;
  //            }
  //            leaf layer-3-only {
  //              description "Include only layer-3 IP information";
  //              type empty;
  //            }
  //          }
  //        }
  //        container symmetric-hash {
  //          presence "enable symmetric-hash";
  //          description "Create a/symmetric hash-key with any attributes";
  //          // uses apply-advanced;
  //          leaf complement {
  //            description "Create complement of symmetric hash-key";
  //            type empty;
  //          }
  //        }
  //      }
  //    }
  //    container resilient-hash-seed {
  //      presence "enable resilient-hash-seed";
  //      description "Resilient hash seed";
  //      // uses apply-advanced;
  //      leaf resilient-seed-value {
  //        description "Hash seed value for resilient ECMP and LAG";
  //        type union {
  //          type string {
  //            pattern "<.*>|$.*";
  //          }
  //          type uint32 {
  //            range "0 .. 4294967295";
  //          }
  //        }
  //      }
  //    }
  //  }
  //  grouping layer2_pm_family_output_type {
  //    // uses apply-advanced;
  //    choice interface-or-next-hop-index {
  //      case case_1 {
  //        leaf interface {
  //          description "Interface through which to send sampled traffic";
  //          type union {
  //            type jt:interface-name;
  //            type string {
  //              pattern "<.*>|$.*";
  //            }
  //          }
  //        }
  //      }
  //      case case_2 {
  //        leaf next-hop-group {
  //          description "Next-hop-group through which to send port-mirror traffic";
  //          type string;
  //        }
  //      }
  //      case case_3 {
  //        list routing-instance {
  //          key name;
  //          description "Routing instances";
  //          max-elements 1;
  //          uses layer2_pm_output-routing-instance-type;
  //        }
  //      }
  //      case case_4 {
  //        list vlan {
  //          key name;
  //          description "Outgoing VLAN for mirrored packets";
  //          max-elements 1;
  //          uses pm-rspan-vlan;
  //        }
  //      }
  //      case case_5 {
  //        list bridge-domain {
  //          key name;
  //          description "Outgoing bridge-domain for mirrored packets";
  //          max-elements 1;
  //          uses pm-rspan-bridge-domain;
  //        }
  //      }
  //    }
  //    leaf no-filter-check {
  //      description "Do not check for filters on port-mirroring interface";
  //      type empty;
  //    }
  //  }
  //  grouping layer2_pm_output-routing-instance-type {
  //    leaf name {
  //      description "Routing instance name";
  //      type string {
  //      }
  //    }
  //    // uses apply-advanced;
  //    list vlan {
  //      key name;
  //      description "Outgoing VLAN for mirrored packets";
  //      max-elements 1;
  //      uses pm-rspan-vlan;
  //    }
  //    list bridge-domain {
  //      key name;
  //      description "Outgoing bridge-domain for mirrored packets";
  //      max-elements 1;
  //      uses pm-rspan-bridge-domain;
  //    }
  //  }
   grouping ldp-sync-obj {
     // uses apply-advanced;
     choice enable-disable {
       case case_1 {
         leaf disable {
           description "Disable LDP synchronization";
           type empty;
         }
       }
     }
     leaf hold-time {
       description "Time during which maximum metric is advertised";
       type union {
         type string {
           pattern "<.*>|$.*";
         }
         type uint32 {
           range "1 .. 65535";
         }
       }
     }
   }
   grouping ldp_filter_obj {
     description "Filter to apply to tracing";
     leaf match-on {
       description "Argument on which to match";
       type enumeration {
         enum "fec" {
           description "Filter based on FEC associated to the traced object.";
         }
         enum "address" {
           description "Filter based on packet source and destination addresses.";
         }
       }
     }
     leaf-list policy {
       ordered-by user;
       description "Filter policy";
       type jt:policy-algebra;
     }
   }
   grouping lsp-set-match-type {
     // uses apply-advanced;
     leaf lsp-name {
       description "LSP name that matches this string";
       type string;
     }
     leaf lsp-regex {
       description "All LSPs that match this regular expression pattern";
       type string;
     }
     leaf p2mp-name {
       description "P2MP names that match this string";
       type string;
     }
     leaf p2mp-regex {
       description "P2MP names that match this regular expression pattern";
       type string;
     }
     choice router-type {
       case case_1 {
         leaf egress {
           description "All LSPs for which this router is egress";
           type empty;
         }
       }
       case case_2 {
         leaf ingress {
           description "All LSPs for which this router is ingress";
           type empty;
         }
       }
       case case_3 {
         leaf transit {
           description "All LSPs for which this router is transit";
           type empty;
         }
       }
     }
   }
   grouping lsp_nh_obj {
     leaf name {
       description "LSP to use to reach destination";
       type string;
     }
     // uses apply-advanced;
     leaf preference {
       description "Preference of LSP next hop";
       type union {
         type uint32;
         type string {
           pattern "<.*>|$.*";
         }
       }
     }
     leaf metric {
       description "Metric of LSP next hop";
       type union {
         type uint32;
         type string {
           pattern "<.*>|$.*";
         }
       }
     }
   }
  //  grouping macro-data-type {
  //    leaf name {
  //      description "Keyword part of the keyword-value pair";
  //      type string;
  //    }
  //    leaf value {
  //      description "Value part of the keyword-value pair";
  //      type string;
  //    }
  //  }
   grouping martian_type {
     description "Invalid routes";
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
       }
     }
     leaf choice-value {
       type string;
     }
     leaf allow {
       type empty;
     }
   }
  //  grouping monitoring_input_type {
  //    // uses apply-advanced;
  //    list interface {
  //      key name;
  //      ordered-by user;
  //      leaf name {
  //        description "Interface which will be monitored";
  //        type union {
  //          type jt:interface-name;
  //          type string {
  //            pattern "<.*>|$.*";
  //          }
  //        }
  //      }
  //      // uses apply-advanced;
  //    }
  //  }
  //  grouping monitoring_output_type {
  //    // uses apply-advanced;
  //    leaf export-format {
  //      description "Format for sending monitoring information";
  //      type enumeration {
  //        enum "cflowd-version-5" {
  //          description "Export in cflowd version 5 format";
  //        }
  //      }
  //    }
  //    leaf destination-address {
  //      description "Address to which monitored packets will be sent";
  //      status deprecated;
  //      type jt:ipv4addr;
  //    }
  //    leaf destination-port {
  //      description "Port to which monitored packets will be sent";
  //      status deprecated;
  //      type union {
  //        type uint16;
  //        type string {
  //          pattern "<.*>|$.*";
  //        }
  //      }
  //    }
  //    leaf source-address {
  //      description "Address to use for generating monitored packets";
  //      status deprecated;
  //      type jt:ipv4addr;
  //    }
  //    leaf flow-active-timeout {
  //      description "Interval after which an active flow is exported";
  //      default "1800";
  //      units "seconds";
  //      type union {
  //        type string {
  //          pattern "<.*>|$.*";
  //        }
  //        type uint32 {
  //          range "60 .. 1800";
  //        }
  //      }
  //    }
  //    leaf flow-inactive-timeout {
  //      description "Interval of inactivity that marks a flow inactive";
  //      default "60";
  //      units "seconds";
  //      type union {
  //        type string {
  //          pattern "<.*>|$.*";
  //        }
  //        type uint32 {
  //          range "15 .. 1800";
  //        }
  //      }
  //    }
  //    leaf flow-export-destination {
  //      description "Destination for flow export";
  //      type enumeration {
  //        enum "collector-pic" {
  //          description "Send flow information to collector PIC";
  //        }
  //        enum "cflowd-collector" {
  //          description "Send flow information to cflowd collector";
  //        }
  //      }
  //    }
  //    list cflowd {
  //      key name;
  //      description "Collector destination where flow records are sent";
  //      uses cflowd_monitoring_type;
  //    }
  //    list interface {
  //      key name;
  //      description "Interfaces used to send monitored information";
  //      uses monitor_export_intf_type;
  //    }
  //  }
  //  grouping cflowd_monitoring_type {
  //    leaf name {
  //      description "Name of host collecting cflowd packets";
  //      type jt:ipaddr;
  //    }
  //    // uses apply-advanced;
  //    leaf port {
  //      description "UDP port number on host collecting cflowd packets";
  //      type union {
  //        type uint16;
  //        type string {
  //          pattern "<.*>|$.*";
  //        }
  //      }
  //    }
  //    leaf dscp {
  //      description "Numeric DSCP value in the range 0 to 63";
  //      default "0";
  //      type union {
  //        type string {
  //          pattern "<.*>|$.*";
  //        }
  //        type uint8 {
  //          range "0 .. 63";
  //        }
  //      }
  //    }
  //    leaf forwarding-class {
  //      description "Forwarding-class for exported jflow packets, applicable only for inline-jflow";
  //      type string {
  //        length "1 .. 64";
  //      }
  //    }
  //    leaf routing-instance {
  //      description "Name of routing instance on which flow collector is reachable";
  //      type string;
  //    }
  //  }
  //  grouping monitor_export_intf_type {
  //    leaf name {
  //      description "Interface to be used for sending monitored information";
  //      type union {
  //        type jt:interface-name;
  //        type string {
  //          pattern "<.*>|$.*";
  //        }
  //      }
  //    }
  //    // uses apply-advanced;
  //    leaf engine-id {
  //      description "Identity (number) of this monitoring interface";
  //      type union {
  //        type uint8;
  //        type string {
  //          pattern "<.*>|$.*";
  //        }
  //      }
  //    }
  //    leaf engine-type {
  //      description "Type (number) of this monitoring interface";
  //      type union {
  //        type uint8;
  //        type string {
  //          pattern "<.*>|$.*";
  //        }
  //      }
  //    }
  //    leaf input-interface-index {
  //      description "Input interface index for records from this interface";
  //      default "0";
  //      type union {
  //        type uint32;
  //        type string {
  //          pattern "<.*>|$.*";
  //        }
  //      }
  //    }
  //    leaf output-interface-index {
  //      description "Output interface index for records from this interface";
  //      default "0";
  //      type union {
  //        type uint32;
  //        type string {
  //          pattern "<.*>|$.*";
  //        }
  //      }
  //    }
  //    leaf source-address {
  //      description "Address to use for generating monitored packets";
  //      type jt:ipv4addr;
  //    }
  //  }
  //  grouping mpls_pm_family_output_type {
  //    // uses apply-advanced;
  //    leaf server-profile {
  //      description "Server profile name";
  //      type string {
  //        length "3 .. 32";
  //      }
  //    }
  //  }
  //  grouping mrp-trace-options {
  //    description "Trace options for MMRP Protocol";
  //    // uses apply-advanced;
  //    container file {
  //      description "Trace file options";
  //      leaf filename {
  //        description "Name of file in which to write trace information";
  //        type string {
  //          length "1 .. 1024";
  //        }
  //      }
  //      leaf replace {
  //        description "Replace trace file rather than appending to it";
  //        status deprecated;
  //        type empty;
  //      }
  //      leaf size {
  //        description "Maximum trace file size";
  //        type string;
  //      }
  //      leaf files {
  //        description "Maximum number of trace files";
  //        default "10";
  //        type union {
  //          type string {
  //            pattern "<.*>|$.*";
  //          }
  //          type uint32 {
  //            range "2 .. 1000";
  //          }
  //        }
  //      }
  //      leaf no-stamp {
  //        description "Do not timestamp trace file";
  //        status deprecated;
  //        type empty;
  //      }
  //      choice world-readable-choice {
  //        leaf world-readable {
  //          description "Allow any user to read the log file";
  //          type empty;
  //        }
  //        leaf no-world-readable {
  //          description "Don't allow any user to read the log file";
  //          type empty;
  //        }
  //      }
  //    }
  //    list flag {
  //      key name;
  //      ordered-by user;
  //      description "Tracing parameters";
  //      leaf name {
  //        type enumeration {
  //          enum "events" {
  //            description "Trace events to the protocol state machine";
  //          }
  //          enum "pdu" {
  //            description "Trace RAPS PDU reception and transmission";
  //          }
  //          enum "timers" {
  //            description "Trace protocol timers";
  //          }
  //          enum "state-machine" {
  //            description "Trace information of the state machine";
  //          }
  //          enum "socket" {
  //            description "Trace soccket activity";
  //          }
  //          enum "error" {
  //            description "Trace all failure conditions";
  //          }
  //          enum "all" {
  //            description "Trace all";
  //          }
  //        }
  //      }
  //      leaf disable {
  //        description "Disable this trace flag";
  //        type empty;
  //      }
  //    }
  //  }
  //  grouping mstp-interface {
  //    leaf name {
  //      type string;
  //    }
  //    // uses apply-advanced;
  //    leaf priority {
  //      description "Interface priority (in increments of 16 - 0,16,..240)";
  //      type union {
  //        type string {
  //          pattern "<.*>|$.*";
  //        }
  //        type uint16 {
  //          range "0 .. 255";
  //        }
  //      }
  //    }
  //    leaf cost {
  //      description "Cost of the interface";
  //      type union {
  //        type string {
  //          pattern "<.*>|$.*";
  //        }
  //        type uint32 {
  //          range "1 .. 200000000";
  //        }
  //      }
  //    }
  //    leaf mode {
  //      description "Interface mode (P2P or shared)";
  //      type enumeration {
  //        enum "point-to-point" {
  //          description "Interface mode is point-to-point";
  //        }
  //        enum "shared" {
  //          description "Interface mode is shared";
  //        }
  //      }
  //    }
  //    leaf edge {
  //      description "Port is an edge port";
  //      type empty;
  //    }
  //    leaf access-trunk {
  //      description "Send/Receive untagged RSTP BPDUs on this interface";
  //      type empty;
  //    }
  //    container bpdu-timeout-action {
  //      presence "enable bpdu-timeout-action";
  //      description "Define action on BPDU expiry (Loop Protect)";
  //      // uses apply-advanced;
  //      leaf block {
  //        description "Block the interface";
  //        type empty;
  //      }
  //      leaf alarm {
  //        description "Generate an alarm";
  //        type empty;
  //      }
  //    }
  //    leaf no-root-port {
  //      description "Do not allow the interface to become root (Root Protect)";
  //      type empty;
  //    }
  //    leaf disable {
  //      description "Disable Spanning Tree on port";
  //      type empty;
  //    }
  //  }
  //  grouping multicast_interface_options_type {
  //    description "Multicast interface options";
  //    leaf name {
  //      description "Interface name";
  //      type union {
  //        type jt:interface-unit;
  //        type string {
  //          pattern "<.*>|$.*";
  //        }
  //      }
  //    }
  //    // uses apply-advanced;
  //    container maximum-bandwidth {
  //      presence "enable maximum-bandwidth";
  //      description "Maximum multicast bandwidth for the interface";
  //      leaf bandwidth-limit {
  //        description "Maximum multicast bandwidth on the interface";
  //        units "bps";
  //        type string;
  //      }
  //    }
  //    choice enable-disable {
  //      case case_1 {
  //        leaf enable {
  //          description "Enable Multicast";
  //          status deprecated;
  //          type empty;
  //        }
  //      }
  //      case case_2 {
  //        leaf disable {
  //          description "Disable Multicast";
  //          status deprecated;
  //          type empty;
  //        }
  //      }
  //    }
  //    container reverse-oif-mapping {
  //      presence "enable reverse-oif-mapping";
  //      description "Enable reverse OIF mapping on the multicast interface";
  //      // uses apply-advanced;
  //      leaf no-qos-adjust {
  //        description "Disable reverse OIF mapping QoS adjustment";
  //        type empty;
  //      }
  //    }
  //    leaf subscriber-leave-timer {
  //      description "Timeout in seconds to credit back the bandwidth on the subscriber interface";
  //      units "seconds";
  //      type union {
  //        type string {
  //          pattern "<.*>|$.*";
  //        }
  //        type uint32 {
  //          range "0 .. 30";
  //        }
  //      }
  //    }
  //    leaf no-qos-adjust {
  //      description "Disable QoS adjustment for this interface";
  //      type empty;
  //    }
  //  }
   grouping network_type {
     leaf name {
       description "Network prefix";
       type jt:ipprefix;
     }
     // uses apply-advanced;
     leaf-list dyn-tunnel-attribute-policy {
       ordered-by user;
       description "Import policy for dynamic-tunnel under this destination network";
       type jt:policy-algebra;
     }
     leaf preference {
       description "Preference of tunnel route under this destination network";
       type union {
         type uint32;
         type string {
           pattern "<.*>|$.*";
         }
       }
     }
     leaf-list colors {
       ordered-by user;
       description "Set of color list that will be supported for tunnel creation";
       type union {
         type uint32;
         type string {
           pattern "<.*>|$.*";
         }
       }
     }
   }
  //  grouping next_hop_group_intf_type {
  //    leaf name {
  //      description "Interface through which to send sampled traffic";
  //      type union {
  //        type jt:interface-name;
  //        type string {
  //          pattern "<.*>|$.*";
  //        }
  //      }
  //    }
  //    // uses apply-advanced;
  //    list next-hop {
  //      key name;
  //      ordered-by user;
  //      description "Address of next hop through which to send sampled traffic";
  //      uses next_hop_type;
  //    }
  //  }
  //  grouping next_hop_subgroup_intf_type {
  //    leaf name {
  //      description "Interface through which to send sampled traffic";
  //      type union {
  //        type jt:interface-name;
  //        type string {
  //          pattern "<.*>|$.*";
  //        }
  //      }
  //    }
  //    // uses apply-advanced;
  //    list next-hop {
  //      key name;
  //      ordered-by user;
  //      description "Address of next hop through which to send sampled traffic";
  //      uses next_hop_type;
  //    }
  //  }
   grouping next_hop_type {
     description "Address of next hop through which to send sampled traffic";
     leaf name {
       type jt:ipaddr;
     }
     // uses apply-advanced;
   }
  //  grouping override-local-server-type {
  //    description "DHCP override processing";
  //    // uses apply-advanced;
  //    leaf interface-client-limit {
  //      description "Limit the number of clients allowed on an interface";
  //      type union {
  //        type string {
  //          pattern "<.*>|$.*";
  //        }
  //        type uint32 {
  //          range "1 .. 500000";
  //        }
  //      }
  //    }
  //    leaf no-arp {
  //      description "Disable DHCP ARP table population";
  //      status deprecated;
  //      type empty;
  //    }
  //    leaf bootp-support {
  //      description "Allow processing of bootp requests";
  //      type empty;
  //    }
  //    container client-discover-match {
  //      presence "enable client-discover-match";
  //      description "Use secondary match criteria for DISCOVER PDU";
  //      choice match-with {
  //        case case_1 {
  //          leaf option60-and-option82 {
  //            description "Use option 60 and option 82";
  //            type empty;
  //          }
  //        }
  //        case case_2 {
  //          leaf incoming-interface {
  //            description "Use incoming interface";
  //            type empty;
  //          }
  //        }
  //      }
  //    }
  //    container delay-offer {
  //      description "Filter options for dhcp-server";
  //      uses dhcpv4-filter-option;
  //    }
  //    container process-inform {
  //      presence "enable process-inform";
  //      description "Process INFORM PDUs";
  //      // uses apply-advanced;
  //      leaf pool {
  //        description "Pool name for family inet";
  //        type string {
  //          length "1 .. 64";
  //        }
  //      }
  //    }
  //    container include-option-82 {
  //      description "Include option-82 in reply packets";
  //      // uses apply-advanced;
  //      leaf nak {
  //        description "Include option-82 in NAK";
  //        type empty;
  //      }
  //      leaf forcerenew {
  //        description "Include option-82 in FORCERENEW";
  //        type empty;
  //      }
  //    }
  //    leaf delete-binding-on-renegotiation {
  //      description "Delete binding on renegotiation";
  //      type empty;
  //    }
  //    leaf allow-no-end-option {
  //      description "Allow packets without end-of-option";
  //      type empty;
  //    }
  //    leaf asymmetric-lease-time {
  //      description "Use a reduced lease time for the client. In seconds";
  //      units "seconds";
  //      type union {
  //        type string {
  //          pattern "<.*>|$.*";
  //        }
  //        type uint32 {
  //          range "600 .. 86400";
  //        }
  //      }
  //    }
  //    leaf protocol-attributes {
  //      description "DHCPv4 attributes to use as defined under access protocol-attributes";
  //      type string {
  //        length "1 .. 64";
  //      }
  //    }
  //    leaf dual-stack {
  //      description "Dual stack group to use";
  //      type string {
  //        length "1 .. 64";
  //      }
  //    }
  //  }
  //  grouping dhcpv4-filter-option {
  //    description "Generic DHCPv4 filter processing";
  //    // uses apply-advanced;
  //    leaf delay-time {
  //      description "Time delay between discover and offer";
  //      default "3";
  //      units "seconds";
  //      type union {
  //        type string {
  //          pattern "<.*>|$.*";
  //        }
  //        type uint32 {
  //          range "1 .. 30";
  //        }
  //      }
  //    }
  //    container based-on {
  //      description "Option number";
  //      // uses apply-advanced;
  //      container option-82 {
  //        presence "enable option-82";
  //        description "Option 82";
  //        // uses apply-advanced;
  //        container equals {
  //          description "Generic option equals";
  //          uses server-v6-option-ascii-hex;
  //        }
  //        container not-equals {
  //          description "Generic option not equals";
  //          uses server-v6-option-ascii-hex;
  //        }
  //        container starts-with {
  //          description "Generic option starts-with";
  //          uses server-v6-option-ascii-hex;
  //        }
  //      }
  //      container option-60 {
  //        presence "enable option-60";
  //        description "Option 60";
  //        // uses apply-advanced;
  //        container equals {
  //          description "Generic option equals";
  //          uses server-v6-option-ascii-hex;
  //        }
  //        container not-equals {
  //          description "Generic option not equals";
  //          uses server-v6-option-ascii-hex;
  //        }
  //        container starts-with {
  //          description "Generic option starts-with";
  //          uses server-v6-option-ascii-hex;
  //        }
  //      }
  //      container option-77 {
  //        presence "enable option-77";
  //        description "Option 77";
  //        // uses apply-advanced;
  //        container equals {
  //          description "Generic option equals";
  //          uses server-v6-option-ascii-hex;
  //        }
  //        container not-equals {
  //          description "Generic option not equals";
  //          uses server-v6-option-ascii-hex;
  //        }
  //        container starts-with {
  //          description "Generic option starts-with";
  //          uses server-v6-option-ascii-hex;
  //        }
  //      }
  //    }
  //  }
  //  grouping override-type {
  //    description "DHCP override processing";
  //    // uses apply-advanced;
  //    leaf no-unicast-replies {
  //      description "Overwrite unicast bit in incoming packet, when present";
  //      type empty;
  //    }
  //    choice allow-snooped-clients-choice {
  //      leaf allow-snooped-clients {
  //        description "Allow client creation from snooped PDUs";
  //        type empty;
  //      }
  //      leaf no-allow-snooped-clients {
  //        description "Don't allow client creation from snooped PDUs";
  //        type empty;
  //      }
  //    }
  //    leaf allow-no-end-option {
  //      description "Allow packets without end-of-option";
  //      type empty;
  //    }
  //    leaf always-write-giaddr {
  //      description "Overwrite existing 'giaddr' field, when present";
  //      type empty;
  //    }
  //    container always-write-option-82 {
  //      description "Overwrite existing value of option 82, when present";
  //      presence "enable always-write-option-82";
  //      uses write-option-82-type;
  //    }
  //    leaf user-defined-option-82 {
  //      description "Set user defined description for option-82";
  //      type string {
  //        length "1 .. 252";
  //      }
  //    }
  //    leaf layer2-unicast-replies {
  //      description "Do not broadcast client responses";
  //      type empty;
  //    }
  //    leaf trust-option-82 {
  //      description "Trust options-82 option";
  //      type empty;
  //    }
  //    leaf delay-authentication {
  //      description "Delay subscriber authentication in DHCP protocol processing until request packet";
  //      type empty;
  //    }
  //    leaf disable-relay {
  //      description "Disable DHCP relay processing";
  //      type empty;
  //    }
  //    leaf no-bind-on-request {
  //      description "Do not bind if stray DHCP request is received";
  //      type empty;
  //    }
  //    leaf interface-client-limit {
  //      description "Limit the number of client allowed on an interface";
  //      type union {
  //        type string {
  //          pattern "<.*>|$.*";
  //        }
  //        type uint32 {
  //          range "1 .. 500000";
  //        }
  //      }
  //    }
  //    leaf no-arp {
  //      description "Disable DHCP ARP table population";
  //      status deprecated;
  //      type empty;
  //    }
  //    leaf bootp-support {
  //      description "Allows relay of bootp req and reply";
  //      type empty;
  //    }
  //    leaf dual-stack {
  //      description "Dual stack group to use.";
  //      type string {
  //        length "1 .. 64";
  //      }
  //    }
  //    container client-discover-match {
  //      presence "enable client-discover-match";
  //      description "Use secondary match criteria for DISCOVER PDU";
  //      choice match-with {
  //        case case_1 {
  //          leaf option60-and-option82 {
  //            description "Use option 60 and option 82";
  //            type empty;
  //          }
  //        }
  //        case case_2 {
  //          leaf incoming-interface {
  //            description "Use incoming interface";
  //            type empty;
  //          }
  //        }
  //      }
  //    }
  //    container proxy-mode {
  //      presence "enable proxy-mode";
  //      description "Put the relay in proxy mode";
  //    }
  //    leaf asymmetric-lease-time {
  //      description "Use a reduced lease time for the client. In seconds";
  //      units "seconds";
  //      type union {
  //        type string {
  //          pattern "<.*>|$.*";
  //        }
  //        type uint32 {
  //          range "600 .. 86400";
  //        }
  //      }
  //    }
  //    container replace-ip-source-with {
  //      description "Replace IP source address in request and release packets";
  //      choice replacement-type {
  //        case case_1 {
  //          leaf giaddr {
  //            description "Replace IP source address with giaddr";
  //            type empty;
  //          }
  //        }
  //      }
  //    }
  //    leaf send-release-on-delete {
  //      description "Always send RELEASE to the server when a binding is deleted";
  //      type empty;
  //    }
  //    leaf relay-source {
  //      description "Interface for relay source";
  //      type union {
  //        type jt:interface-name;
  //        type string {
  //          pattern "<.*>|$.*";
  //        }
  //      }
  //    }
  //    leaf delete-binding-on-renegotiation {
  //      description "Delete binding on rengotiation";
  //      type empty;
  //    }
  //  }
  //  grouping p2mp_ldp_lsp_nh_obj {
  //    // uses apply-advanced;
  //    list root-address {
  //      key name;
  //      description "Configure the root address of P2MP LSP";
  //      leaf name {
  //        description "Root address of the P2MP LSP";
  //        type jt:ipaddr;
  //      }
  //      // uses apply-advanced;
  //      leaf lsp-id {
  //        description "Configure the generic LSP identifier";
  //        type union {
  //          type string {
  //            pattern "<.*>|$.*";
  //          }
  //          type uint32 {
  //            range "1 .. 65535";
  //          }
  //        }
  //      }
  //      list group-address {
  //        key name;
  //        description "IPv4/Ipv6 group address for mLDP LSP";
  //        leaf name {
  //          description "IPv4/Ipv6 group address";
  //          type jt:ipaddr;
  //        }
  //        // uses apply-advanced;
  //        list source-address {
  //          key name;
  //          description "IPv4/Ipv6 source address";
  //          leaf name {
  //            description "IPv4/Ipv6 source address for mLDP LSP";
  //            type jt:ipaddr;
  //          }
  //          // uses apply-advanced;
  //        }
  //      }
  //    }
  //  }
  //  grouping packet-capture-egress-intf-type {
  //    // uses apply-advanced;
  //    list interface {
  //      key name;
  //      description "Interface options";
  //      leaf name {
  //        description "Interface name";
  //        type union {
  //          type jt:interface-device;
  //          type string {
  //            pattern "<.*>|$.*";
  //          }
  //        }
  //      }
  //      // uses apply-advanced;
  //    }
  //  }
  //  grouping packet_accounting_output_type {
  //    // uses apply-advanced;
  //    leaf aggregate-export-interval {
  //      description "Interval of exporting aggregate accounting information";
  //      default "90";
  //      units "seconds";
  //      type union {
  //        type string {
  //          pattern "<.*>|$.*";
  //        }
  //        type uint32 {
  //          range "90 .. 1800";
  //        }
  //      }
  //    }
  //    leaf flow-inactive-timeout {
  //      description "Interval of inactivity that marks a flow inactive";
  //      default "60";
  //      units "seconds";
  //      type union {
  //        type string {
  //          pattern "<.*>|$.*";
  //        }
  //        type uint32 {
  //          range "15 .. 1800";
  //        }
  //      }
  //    }
  //    leaf flow-active-timeout {
  //      description "Interval after which an active flow is exported";
  //      default "1800";
  //      units "seconds";
  //      type union {
  //        type string {
  //          pattern "<.*>|$.*";
  //        }
  //        type uint32 {
  //          range "60 .. 1800";
  //        }
  //      }
  //    }
  //    list cflowd {
  //      key name;
  //      description "Cflowd collector where flow records are sent";
  //      uses cflowd_packet_accounting_type;
  //    }
  //    list interface {
  //      key name;
  //      description "Interfaces used to send monitored information";
  //      uses packet_export_intf_type;
  //    }
  //  }
  //  grouping cflowd_packet_accounting_type {
  //    leaf name {
  //      description "Name of host collecting cflowd packets";
  //      type jt:ipaddr;
  //    }
  //    // uses apply-advanced;
  //    leaf port {
  //      description "UDP port number on host collecting cflowd packets";
  //      type union {
  //        type uint16;
  //        type string {
  //          pattern "<.*>|$.*";
  //        }
  //      }
  //    }
  //    leaf dscp {
  //      description "Numeric DSCP value in the range 0 to 63";
  //      default "0";
  //      type union {
  //        type string {
  //          pattern "<.*>|$.*";
  //        }
  //        type uint8 {
  //          range "0 .. 63";
  //        }
  //      }
  //    }
  //    leaf forwarding-class {
  //      description "Forwarding-class for exported jflow packets, applicable only for inline-jflow";
  //      type string {
  //        length "1 .. 64";
  //      }
  //    }
  //    leaf routing-instance {
  //      description "Name of routing instance on which flow collector is reachable";
  //      type string;
  //    }
  //    leaf version {
  //      description "Format of exported cflowd aggregates";
  //      default "5";
  //      type enumeration {
  //        enum "5" {
  //          description "Export cflowd aggregates in version 5 format";
  //        }
  //        enum "8" {
  //          description "Export cflowd aggregates in version 8 format";
  //        }
  //      }
  //    }
  //    leaf autonomous-system-type {
  //      description "Type of autonomous system number to export";
  //      default "origin";
  //      type enumeration {
  //        enum "origin" {
  //          description "Export origin-AS numbers";
  //        }
  //        enum "peer" {
  //          description "Export peer-AS numbers";
  //        }
  //      }
  //    }
  //    container aggregation {
  //      description "Aggregations to perform for exported flows (version 8 only)";
  //      uses aggregation_type;
  //    }
  //  }
   grouping aggregation_type {
     // uses apply-advanced;
     leaf autonomous-system {
       description "Aggregate by autonomous system number";
       type empty;
     }
     leaf protocol-port {
       description "Aggregate by protocol and port number";
       type empty;
     }
     leaf source-prefix {
       description "Aggregate by source prefix";
       type empty;
     }
     leaf destination-prefix {
       description "Aggregate by destination prefix";
       type empty;
     }
     container source-destination-prefix {
       presence "enable source-destination-prefix";
       description "Aggregate by source and destination prefix";
       // uses apply-advanced;
       leaf caida-compliant {
         description "Compatible with Caida record format for prefix aggregation (v8)";
         type empty;
       }
     }
   }
  //  grouping packet_export_intf_type {
  //    leaf name {
  //      description "Interfaces used to send monitored information";
  //      type union {
  //        type jt:interface-unit;
  //        type string {
  //          pattern "<.*>|$.*";
  //        }
  //      }
  //    }
  //    // uses apply-advanced;
  //    leaf engine-id {
  //      description "Identity (number) of this accounting interface";
  //      type union {
  //        type uint8;
  //        type string {
  //          pattern "<.*>|$.*";
  //        }
  //      }
  //    }
  //    leaf engine-type {
  //      description "Type (number) of this accounting interface";
  //      type union {
  //        type uint8;
  //        type string {
  //          pattern "<.*>|$.*";
  //        }
  //      }
  //    }
  //    leaf source-address {
  //      description "Address to use for generating monitored packets";
  //      type jt:ipaddr;
  //    }
  //    container export-port {
  //      description "Jflow export port configuration";
  //      presence "enable export-port";
  //      uses export_port_address_type;
  //    }
  //  }
  //  grouping export_port_address_type {
  //    // uses apply-advanced;
  //    leaf address {
  //      description "Address to use for jflow export port";
  //      type jt:ipv4prefix;
  //    }
  //    leaf gateway {
  //      description "Gateway address to reach jflow server";
  //      type jt:ipv4addr;
  //    }
  //  }
  //  grouping periodic_oam {
     // uses apply-advanced;
     container mpls-tp-mode {
       presence "enable mpls-tp-mode";
       description "MPLS-TP Mode, Do not use IP addressing for OAM";
       // uses apply-advanced;
       container lsping-channel-type {
         description "Supported Control-channel types for MPLS-TP mode....";
         // uses apply-advanced;
         choice action-choice {
           case case_1 {
             leaf ipv4 {
               description "Use channel-type IPv4(0x0021), With IP-UDP encapsulation";
               type empty;
             }
           }
           case case_2 {
             leaf on-demand-cv {
               description "Use channel-type On-Demand-CV(0x0025), Without IP-UDP encapsulation";
               type empty;
             }
           }
         }
       }
     }
  //    container bfd-port {
  //      description "Egress knob to select MHOP-BFD port for MPLS BFD";
  //      // uses apply-advanced;
  //      leaf-list import {
  //        ordered-by user;
  //        description "Import policy";
  //        type jt:policy-algebra;
  //      }
  //    }
  //    container bfd-liveness-detection {
  //      description "Bidirectional Forwarding Detection options";
  //      // uses apply-advanced;
  //      leaf version {
  //        description "BFD protocol version number";
  //        default "automatic";
  //        type enumeration {
  //          enum "0" {
  //            description "BFD version 0 (deprecated)";
  //          }
  //          enum "1" {
  //            description "BFD version 1";
  //          }
  //          enum "automatic" {
  //            description "Choose BFD version automatically";
  //          }
  //        }
  //      }
  //      leaf minimum-interval {
  //        description "Minimum transmit and receive interval";
  //        units "milliseconds";
  //        type union {
  //          type string {
  //            pattern "<.*>|$.*";
  //          }
  //          type uint32 {
  //            range "1 .. 255000";
  //          }
  //        }
  //      }
  //      leaf minimum-transmit-interval {
  //        description "Minimum transmit interval";
  //        status deprecated;
  //        units "milliseconds";
  //        type union {
  //          type string {
  //            pattern "<.*>|$.*";
  //          }
  //          type uint32 {
  //            range "1 .. 255000";
  //          }
  //        }
  //      }
  //      leaf minimum-receive-interval {
  //        description "Minimum receive interval";
  //        units "milliseconds";
  //        type union {
  //          type string {
  //            pattern "<.*>|$.*";
  //          }
  //          type uint32 {
  //            range "1 .. 255000";
  //          }
  //        }
  //      }
  //      leaf multiplier {
  //        description "Detection time multiplier";
  //        default "3";
  //        type union {
  //          type string {
  //            pattern "<.*>|$.*";
  //          }
  //          type uint32 {
  //            range "1 .. 255";
  //          }
  //        }
  //      }
  //      leaf inline-disable {
  //        description "Disable inline mode for this BFD session";
  //        type empty;
  //      }
  //      leaf pdu-size {
  //        description "BFD transport protocol payload size";
  //        default "24";
  //        type union {
  //          type string {
  //            pattern "<.*>|$.*";
  //          }
  //          type uint32 {
  //            range "24 .. 9000";
  //          }
  //        }
  //      }
  //      choice adaptation-choice {
  //        case case_1 {
  //          leaf no-adaptation {
  //            description "Disable adaptation";
  //            type empty;
  //          }
  //        }
  //      }
  //      container transmit-interval {
  //        description "Transmit-interval options";
  //        // uses apply-advanced;
  //        leaf minimum-interval {
  //          description "Minimum transmit interval";
  //          units "milliseconds";
  //          type union {
  //            type string {
  //              pattern "<.*>|$.*";
  //            }
  //            type uint32 {
  //              range "1 .. 255000";
  //            }
  //          }
  //        }
  //        leaf threshold {
  //          description "High transmit interval triggering a trap";
  //          units "milliseconds";
  //          type union {
  //            type uint32;
  //            type string {
  //              pattern "<.*>|$.*";
  //            }
  //          }
  //        }
  //      }
  //      container detection-time {
  //        description "Detection-time options";
  //        // uses apply-advanced;
  //        leaf threshold {
  //          description "High detection-time triggering a trap";
  //          units "milliseconds";
  //          type union {
  //            type uint32;
  //            type string {
  //              pattern "<.*>|$.*";
  //            }
  //          }
  //        }
  //      }
  //      container failure-action {
  //        description "Action to take when BFD session goes down";
  //        choice action-choice {
  //          case case_1 {
  //            leaf teardown {
  //              description "Teardown label switched path and resignal";
  //              type empty;
  //            }
  //          }
  //          case case_2 {
  //            container make-before-break {
  //              presence "enable make-before-break";
  //              description "Resignal the label switched path before teardown";
  //              // uses apply-advanced;
  //              leaf teardown-timeout {
  //                description "Time to wait before teardown";
  //                units "seconds";
  //                type union {
  //                  type string {
  //                    pattern "<.*>|$.*";
  //                  }
  //                  type uint32 {
  //                    range "0 .. 30";
  //                  }
  //                }
  //              }
  //            }
  //          }
  //        }
  //      }
  //      leaf no-router-alert-option {
  //        description "Do not set Router-Alert options in IP header for MPLS-BFD";
  //        type empty;
  //      }
  //      leaf use-ip-ttl-1 {
  //        description "Set TTL value to 1 in IP header for MPLS-BFD";
  //        type empty;
  //      }
  //    }
  //    container performance-monitoring {
  //      description "Performance monitoring options";
  //      // uses apply-advanced;
  //      container traceoptions {
  //        description "Trace options for PM";
  //        // uses apply-advanced;
  //        container file {
  //          description "Trace file options";
  //          leaf filename {
  //            description "Name of file in which to write trace information";
  //            type string {
  //              length "1 .. 1024";
  //            }
  //          }
  //          leaf replace {
  //            description "Replace trace file rather than appending to it";
  //            status deprecated;
  //            type empty;
  //          }
  //          leaf size {
  //            description "Maximum trace file size";
  //            type string;
  //          }
  //          leaf files {
  //            description "Maximum number of trace files";
  //            default "10";
  //            type union {
  //              type string {
  //                pattern "<.*>|$.*";
  //              }
  //              type uint32 {
  //                range "2 .. 1000";
  //              }
  //            }
  //          }
  //          leaf no-stamp {
  //            description "Do not timestamp trace file";
  //            status deprecated;
  //            type empty;
  //          }
  //          choice world-readable-choice {
  //            leaf world-readable {
  //              description "Allow any user to read the log file";
  //              type empty;
  //            }
  //            leaf no-world-readable {
  //              description "Don't allow any user to read the log file";
  //              type empty;
  //            }
  //          }
  //        }
  //        list flag {
  //          key name;
  //          ordered-by user;
  //          description "Tracing parameters";
  //          leaf name {
  //            type enumeration {
  //              enum "init" {
  //                description "Trace init commnad";
  //              }
  //              enum "error" {
  //                description "Trace error conditions";
  //              }
  //              enum "event" {
  //                description "Trace state machine events";
  //              }
  //              enum "general" {
  //                description "Trace general events";
  //              }
  //              enum "packet" {
  //                description "Trace various packets ";
  //              }
  //              enum "timer" {
  //                description "Trace timer processing";
  //              }
  //              enum "all" {
  //                description "Trace everything";
  //              }
  //            }
  //          }
  //        }
  //      }
  //      container querier {
  //        description "Querier options";
  //        // uses apply-advanced;
  //        container loss {
  //          description "Loss measurement options";
  //          // uses apply-advanced;
  //          list traffic-class {
  //            key name;
  //            description "Traffic class specific options";
  //            leaf name {
  //              description "Traffic class value";
  //              type enumeration {
  //                enum "tc-0" {
  //                  description "Traffic class 0";
  //                }
  //                enum "tc-1" {
  //                  description "Traffic class 1";
  //                }
  //                enum "tc-2" {
  //                  description "Traffic class 2";
  //                }
  //                enum "tc-3" {
  //                  description "Traffic class 3";
  //                }
  //                enum "tc-4" {
  //                  description "Traffic class 4";
  //                }
  //                enum "tc-5" {
  //                  description "Traffic class 5";
  //                }
  //                enum "tc-6" {
  //                  description "Traffic class 6";
  //                }
  //                enum "tc-7" {
  //                  description "Traffic class 7";
  //                }
  //                enum "all" {
  //                  description "All Traffic class";
  //                }
  //                enum "none" {
  //                  description "No Traffic class";
  //                }
  //              }
  //            }
  //            // uses apply-advanced;
  //            leaf query-interval {
  //              description "Minimum transmit interval";
  //              units "milliseconds";
  //              type union {
  //                type string {
  //                  pattern "<.*>|$.*";
  //                }
  //                type uint32 {
  //                  range "1000 .. 4294967295";
  //                }
  //              }
  //            }
  //            leaf measurement-quantity {
  //              description "Loss measurement quantity";
  //              default "packets";
  //              type enumeration {
  //                enum "bytes" {
  //                  description "Byte loss measurement";
  //                }
  //                enum "packets" {
  //                  description "Packet loss measurement";
  //                }
  //              }
  //            }
  //            leaf average-sample-size {
  //              description "Number of samples used in average calculation";
  //              type union {
  //                type string {
  //                  pattern "<.*>|$.*";
  //                }
  //                type uint16 {
  //                  range "1 .. 30";
  //                }
  //              }
  //            }
  //            leaf loss-threshold {
  //              description "Loss threshold value";
  //              type union {
  //                type string {
  //                  pattern "<.*>|$.*";
  //                }
  //                type uint32 {
  //                  range "1 .. 4294967295";
  //                }
  //              }
  //            }
  //            leaf loss-threshold-window {
  //              description "Number of samples for loss threshold calculation";
  //              type union {
  //                type string {
  //                  pattern "<.*>|$.*";
  //                }
  //                type uint32 {
  //                  range "1 .. 30";
  //                }
  //              }
  //            }
  //          }
  //        }
  //        container delay {
  //          description "Delay measurement options";
  //          // uses apply-advanced;
  //          list traffic-class {
  //            key name;
  //            description "Traffic class specific options";
  //            leaf name {
  //              description "Traffic class value";
  //              type enumeration {
  //                enum "tc-0" {
  //                  description "Traffic class 0";
  //                }
  //                enum "tc-1" {
  //                  description "Traffic class 1";
  //                }
  //                enum "tc-2" {
  //                  description "Traffic class 2";
  //                }
  //                enum "tc-3" {
  //                  description "Traffic class 3";
  //                }
  //                enum "tc-4" {
  //                  description "Traffic class 4";
  //                }
  //                enum "tc-5" {
  //                  description "Traffic class 5";
  //                }
  //                enum "tc-6" {
  //                  description "Traffic class 6";
  //                }
  //                enum "tc-7" {
  //                  description "Traffic class 7";
  //                }
  //                enum "all" {
  //                  description "All Traffic classes";
  //                }
  //              }
  //            }
  //            // uses apply-advanced;
  //            leaf query-interval {
  //              description "Minimum transmit interval";
  //              units "milliseconds";
  //              type union {
  //                type string {
  //                  pattern "<.*>|$.*";
  //                }
  //                type uint32 {
  //                  range "1000 .. 4294967295";
  //                }
  //              }
  //            }
  //            leaf padding-size {
  //              description "Size of padding";
  //              type union {
  //                type string {
  //                  pattern "<.*>|$.*";
  //                }
  //                type uint16 {
  //                  range "1 .. 1500";
  //                }
  //              }
  //            }
  //            leaf average-sample-size {
  //              description "Number of samples used in average calculation";
  //              type union {
  //                type string {
  //                  pattern "<.*>|$.*";
  //                }
  //                type uint16 {
  //                  range "1 .. 30";
  //                }
  //              }
  //            }
  //            leaf twcd-delay-threshold {
  //              description "Two way channel delay threshold value";
  //              units "microseconds";
  //              type union {
  //                type string {
  //                  pattern "<.*>|$.*";
  //                }
  //                type uint32 {
  //                  range "1 .. 4294967295";
  //                }
  //              }
  //            }
  //            leaf rtt-delay-threshold {
  //              description "Round trip delay threshold value";
  //              units "microseconds";
  //              type union {
  //                type string {
  //                  pattern "<.*>|$.*";
  //                }
  //                type uint32 {
  //                  range "1 .. 4294967295";
  //                }
  //              }
  //            }
  //          }
  //        }
  //        container loss-delay {
  //          description "Combined loss-delay measurement options";
  //          // uses apply-advanced;
  //          list traffic-class {
  //            key name;
  //            description "Traffic class specific options";
  //            leaf name {
  //              description "Traffic class value";
  //              type enumeration {
  //                enum "tc-0" {
  //                  description "Traffic class 0";
  //                }
  //                enum "tc-1" {
  //                  description "Traffic class 1";
  //                }
  //                enum "tc-2" {
  //                  description "Traffic class 2";
  //                }
  //                enum "tc-3" {
  //                  description "Traffic class 3";
  //                }
  //                enum "tc-4" {
  //                  description "Traffic class 4";
  //                }
  //                enum "tc-5" {
  //                  description "Traffic class 5";
  //                }
  //                enum "tc-6" {
  //                  description "Traffic class 6";
  //                }
  //                enum "tc-7" {
  //                  description "Traffic class 7";
  //                }
  //                enum "all" {
  //                  description "All Traffic classes";
  //                }
  //                enum "none" {
  //                  description "No Traffic class";
  //                }
  //              }
  //            }
  //            // uses apply-advanced;
  //            leaf query-interval {
  //              description "Minimum transmit interval";
  //              units "milliseconds";
  //              type union {
  //                type string {
  //                  pattern "<.*>|$.*";
  //                }
  //                type uint32 {
  //                  range "1000 .. 4294967295";
  //                }
  //              }
  //            }
  //            leaf measurement-quantity {
  //              description "Loss measurement quantity";
  //              default "packets";
  //              type enumeration {
  //                enum "bytes" {
  //                  description "Byte loss measurement";
  //                }
  //                enum "packets" {
  //                  description "Packet loss measurement";
  //                }
  //              }
  //            }
  //            leaf padding-size {
  //              description "Size of padding";
  //              type union {
  //                type string {
  //                  pattern "<.*>|$.*";
  //                }
  //                type uint16 {
  //                  range "1 .. 1500";
  //                }
  //              }
  //            }
  //            leaf average-sample-size {
  //              description "Number of samples used in average calculation";
  //              type union {
  //                type string {
  //                  pattern "<.*>|$.*";
  //                }
  //                type uint16 {
  //                  range "1 .. 30";
  //                }
  //              }
  //            }
  //            leaf loss-threshold {
  //              description "Loss threshold value";
  //              type union {
  //                type string {
  //                  pattern "<.*>|$.*";
  //                }
  //                type uint32 {
  //                  range "1 .. 4294967295";
  //                }
  //              }
  //            }
  //            leaf loss-threshold-window {
  //              description "Number of samples for loss threshold calculation";
  //              type union {
  //                type string {
  //                  pattern "<.*>|$.*";
  //                }
  //                type uint32 {
  //                  range "1 .. 30";
  //                }
  //              }
  //            }
  //            leaf twcd-delay-threshold {
  //              description "Two way channel delay threshold value";
  //              units "microseconds";
  //              type union {
  //                type string {
  //                  pattern "<.*>|$.*";
  //                }
  //                type uint32 {
  //                  range "1 .. 4294967295";
  //                }
  //              }
  //            }
  //            leaf rtt-delay-threshold {
  //              description "Round trip delay threshold value";
  //              units "microseconds";
  //              type union {
  //                type string {
  //                  pattern "<.*>|$.*";
  //                }
  //                type uint32 {
  //                  range "1 .. 4294967295";
  //                }
  //              }
  //            }
  //          }
  //        }
  //      }
  //      container responder {
  //        description "Responder options";
  //        // uses apply-advanced;
  //        container loss {
  //          description "Loss measurement options";
  //          // uses apply-advanced;
  //          leaf min-query-interval {
  //            description "Minimum query interval";
  //            units "milliseconds";
  //            type union {
  //              type string {
  //                pattern "<.*>|$.*";
  //              }
  //              type uint32 {
  //                range "1000 .. 4294967295";
  //              }
  //            }
  //          }
  //        }
  //        container delay {
  //          description "Delay measurement options";
  //          // uses apply-advanced;
  //          leaf min-query-interval {
  //            description "Minimum query interval";
  //            units "milliseconds";
  //            type union {
  //              type string {
  //                pattern "<.*>|$.*";
  //              }
  //              type uint32 {
  //                range "1000 .. 4294967295";
  //              }
  //            }
  //          }
  //        }
  //      }
  //    }
  //    leaf lsp-ping-interval {
  //      description "Time interval between LSP ping messages";
  //      units "seconds";
  //      type union {
  //        type string {
  //          pattern "<.*>|$.*";
  //        }
  //        type uint16 {
  //          range "30 .. 3600";
  //        }
  //      }
  //    }
  //    leaf lsp-ping-multiplier {
  //      description "Number of ping reply missed before declaring BFD down";
  //      type union {
  //        type string {
  //          pattern "<.*>|$.*";
  //        }
  //        type uint8 {
  //          range "1 .. 5";
  //        }
  //      }
  //    }
  //    container traceoptions {
  //      description "Trace options for MPLSOAM process";
  //      // uses apply-advanced;
  //      leaf no-remote-trace {
  //        description "Disable remote tracing";
  //        type empty;
  //      }
  //      container file {
  //        description "Trace file information";
  //        leaf filename {
  //          description "Name of file in which to write trace information";
  //          type string {
  //            length "1 .. 1024";
  //          }
  //        }
  //        leaf size {
  //          description "Maximum trace file size";
  //          type string;
  //        }
  //        leaf files {
  //          description "Maximum number of trace files";
  //          default "3";
  //          type union {
  //            type string {
  //              pattern "<.*>|$.*";
  //            }
  //            type uint32 {
  //              range "2 .. 1000";
  //            }
  //          }
  //        }
  //        choice world-readable-choice {
  //          leaf world-readable {
  //            description "Allow any user to read the log file";
  //            type empty;
  //          }
  //          leaf no-world-readable {
  //            description "Don't allow any user to read the log file";
  //            type empty;
  //          }
  //        }
  //        leaf match {
  //          description "Regular expression for lines to be logged";
  //          type jt:regular-expression;
  //        }
  //      }
  //      list flag {
  //        key name;
  //        ordered-by user;
  //        description "Tracing parameters";
  //        leaf name {
  //          type enumeration {
  //            enum "configuration" {
  //              description "Trace configuration events";
  //            }
  //            enum "pipe" {
  //              description "Trace pipe activity";
  //            }
  //            enum "rpc-packet-details" {
  //              description "Trace RPC packet details";
  //            }
  //            enum "database" {
  //              description "Trace database activity";
  //            }
  //            enum "network" {
  //              description "Trace network activity";
  //            }
  //            enum "traceroute" {
  //              description "Trace traceroute activity";
  //            }
  //            enum "all" {
  //              description "Trace everything";
  //            }
  //          }
  //        }
  //      }
  //    }
  //  }
  //  grouping pim_bootstrap_options_type {
  //    // uses apply-advanced;
  //    leaf priority {
  //      description "Eligibility to be the bootstrap router";
  //      type union {
  //        type string {
  //          pattern "<.*>|$.*";
  //        }
  //        type uint32 {
  //          range "0 .. 255";
  //        }
  //      }
  //    }
  //    leaf-list import {
  //      ordered-by user;
  //      description "Bootstrap import policy";
  //      type jt:policy-algebra;
  //    }
  //    leaf-list export {
  //      ordered-by user;
  //      description "Bootstrap export policy";
  //      type jt:policy-algebra;
  //    }
  //  }
  //  grouping pim_filter_obj {
  //    description "Filter to apply to tracing";
  //    leaf match-on {
  //      description "Argument on which to match";
  //      type enumeration {
  //        enum "prefix" {
  //          description "Filter based on prefix";
  //        }
  //      }
  //    }
  //    leaf-list policy {
  //      ordered-by user;
  //      description "Filter policy";
  //      type jt:policy-algebra;
  //    }
  //  }
  //  grouping pim_rp_group_range_type {
  //    leaf name {
  //      type jt:ipprefix;
  //    }
  //    // uses apply-advanced;
  //    leaf nexthop-hold-time {
  //      description "Nexthop hold time in milliseconds";
  //      units "milliseconds";
  //      type union {
  //        type string {
  //          pattern "<.*>|$.*";
  //        }
  //        type uint32 {
  //          range "1 .. 1000";
  //        }
  //      }
  //    }
  //  }
  //  grouping pm-rspan-bridge-domain {
  //    description "RSPAN bridge-domain for pm";
  //    leaf name {
  //      description "Bridge domain name or VLAN id";
  //      type string {
  //      }
  //    }
  //    // uses apply-advanced;
  //  }
  //  grouping pm-rspan-vlan {
  //    description "RSPAN vlan for pm";
  //    leaf name {
  //      description "VLAN name or VLAN id";
  //      type string {
  //      }
  //    }
  //    // uses apply-advanced;
  //    leaf no-tag {
  //      description "Removes extra RSPAN tag from mirrored packets";
  //      type empty;
  //    }
  //  }
  //  grouping pm_family_input_type {
  //    description "Input options for port mirroring";
  //    // uses apply-advanced;
  //    leaf rate {
  //      description "Ratio of packets to be sampled (1 out of N)";
  //      type union {
  //        type string {
  //          pattern "<.*>|$.*";
  //        }
  //        type uint32;
  //      }
  //    }
  //    leaf run-length {
  //      description "Number of samples after initial trigger";
  //      type union {
  //        type string {
  //          pattern "<.*>|$.*";
  //        }
  //        type uint32 {
  //          range "0 .. 20";
  //        }
  //      }
  //    }
  //    leaf maximum-packet-length {
  //      description "Maximum length of the mirrored packet";
  //      default "0";
  //      units "bytes";
  //      type union {
  //        type string {
  //          pattern "<.*>|$.*";
  //        }
  //        type uint32 {
  //          range "0 .. 9216";
  //        }
  //      }
  //    }
  //  }
  //  grouping programmable-rpd-type {
  //    // uses apply-advanced;
  //    container traceoptions {
  //      description "Trace options";
  //      // uses apply-advanced;
  //      container file {
  //        description "Trace file options";
  //        leaf filename {
  //          description "Name of file in which to write trace information";
  //          type string {
  //            length "1 .. 1024";
  //          }
  //        }
  //        leaf replace {
  //          description "Replace trace file rather than appending to it";
  //          status deprecated;
  //          type empty;
  //        }
  //        leaf size {
  //          description "Maximum trace file size";
  //          type string;
  //        }
  //        leaf files {
  //          description "Maximum number of trace files";
  //          default "10";
  //          type union {
  //            type string {
  //              pattern "<.*>|$.*";
  //            }
  //            type uint32 {
  //              range "2 .. 1000";
  //            }
  //          }
  //        }
  //        leaf no-stamp {
  //          description "Do not timestamp trace file";
  //          status deprecated;
  //          type empty;
  //        }
  //        choice world-readable-choice {
  //          leaf world-readable {
  //            description "Allow any user to read the log file";
  //            type empty;
  //          }
  //          leaf no-world-readable {
  //            description "Don't allow any user to read the log file";
  //            type empty;
  //          }
  //        }
  //      }
  //      list flag {
  //        key name;
  //        ordered-by user;
  //        description "Tracing parameters";
  //        leaf name {
  //          type enumeration {
  //            enum "client" {
  //              description "Client events";
  //            }
  //            enum "japi" {
  //              description "JAPI related traces";
  //            }
  //            enum "routing-interface" {
  //              description "Routing interface traces";
  //            }
  //            enum "te-path-compute" {
  //              description "TE Path Computation traces";
  //            }
  //            enum "statistics" {
  //              description "Statistics related traces";
  //            }
  //            enum "route" {
  //              description "Trace routing information";
  //            }
  //            enum "normal" {
  //              description "Trace normal events";
  //            }
  //            enum "general" {
  //              description "Trace general events";
  //            }
  //            enum "state" {
  //              description "Trace state transitions";
  //            }
  //            enum "policy" {
  //              description "Trace policy processing";
  //            }
  //            enum "task" {
  //              description "Trace routing protocol task processing";
  //            }
  //            enum "timer" {
  //              description "Trace routing protocol timer processing";
  //            }
  //            enum "all" {
  //              description "Trace everything";
  //            }
  //          }
  //        }
  //      }
  //    }
  //    container purge-timeout {
  //      presence "enable purge-timeout";
  //      description "Purge timeout for all programmable-rpd clients in seconds";
  //      choice purge-parm {
  //        case case_1 {
  //          leaf never {
  //            description "Client programmed objects are never purged";
  //            type empty;
  //          }
  //        }
  //        case case_2 {
  //          leaf timeout {
  //            description "Timeout value, in seconds, for purging client programmed objects";
  //            units "seconds";
  //            type union {
  //              type string {
  //                pattern "<.*>|$.*";
  //              }
  //              type uint32 {
  //                range "1 .. 604800";
  //              }
  //            }
  //          }
  //        }
  //      }
  //    }
  //    list client {
  //      key name;
  //      ordered-by user;
  //      description "Programmable-rpd client options";
  //      leaf name {
  //        description "Client ID";
  //        type string {
  //          length "1 .. 255";
  //        }
  //      }
  //      // uses apply-advanced;
  //      list interface-notification {
  //        key name;
  //        ordered-by user;
  //        description "Interfaces for notification";
  //        leaf name {
  //          description "Interface";
  //          type string {
  //            length "1 .. 32";
  //          }
  //        }
  //        // uses apply-advanced;
  //      }
  //    }
  //    container rib-service {
  //      presence "enable rib-service";
  //      description "RIB service API options";
  //      // uses apply-advanced;
  //      container dynamic-next-hop-interface {
  //        presence "enable dynamic-next-hop-interface";
  //        description "Update routes for next-hop interface changes";
  //        // uses apply-advanced;
  //        choice enable-disable {
  //          case case_1 {
  //            leaf disable {
  //              description "Disable dynamic next-hop interface handling";
  //              type empty;
  //            }
  //          }
  //        }
  //      }
  //    }
  //    leaf stats-sampling-interval {
  //      description "Sampling interval for programmable rpd statisitics";
  //      default "30";
  //      units "seconds";
  //      type union {
  //        type string {
  //          pattern "<.*>|$.*";
  //        }
  //        type uint32 {
  //          range "30 .. 3600";
  //        }
  //      }
  //    }
  //    leaf stats-aggregation-interval {
  //      description "Aggregation interval for programmable rpd statistics";
  //      default "60";
  //      units "seconds";
  //      type union {
  //        type string {
  //          pattern "<.*>|$.*";
  //        }
  //        type uint32 {
  //          range "60 .. 3600";
  //        }
  //      }
  //    }
  //  }
  //  grouping qualified_nh_obj {
  //    leaf name {
  //      description "Next hop to destination";
  //      type union {
  //        type jt:ipaddr-or-interface;
  //        type string {
  //          pattern "<.*>|$.*";
  //        }
  //      }
  //    }
  //    // uses apply-advanced;
  //    leaf preference {
  //      description "Preference of qualified next hop";
  //      type union {
  //        type uint32;
  //        type string {
  //          pattern "<.*>|$.*";
  //        }
  //      }
  //    }
  //    leaf metric {
  //      description "Metric of qualified next hop";
  //      type union {
  //        type uint32;
  //        type string {
  //          pattern "<.*>|$.*";
  //        }
  //      }
  //    }
  //    leaf interface {
  //      description "Interface of qualified next hop";
  //      type union {
  //        type jt:interface-name;
  //        type string {
  //          pattern "<.*>|$.*";
  //        }
  //      }
  //    }
  //    leaf mac-address {
  //      description "Next-hop Mac Address";
  //      type jt:mac-unicast;
  //    }
  //    leaf order {
  //      description "Order of qualified next hop";
  //      type union {
  //        type string {
  //          pattern "<.*>|$.*";
  //        }
  //        type uint16 {
  //          range "1 .. 65535";
  //        }
  //      }
  //    }
  //    leaf tag {
  //      description "Tag string";
  //      type union {
  //        type uint32;
  //        type string {
  //          pattern "<.*>|$.*";
  //        }
  //      }
  //    }
  //    container bfd-liveness-detection {
  //      description "Bidirectional Forwarding Detection (BFD) options";
  //      // uses apply-advanced;
  //      leaf version {
  //        description "BFD protocol version number";
  //        default "automatic";
  //        type enumeration {
  //          enum "0" {
  //            description "BFD version 0 (deprecated)";
  //          }
  //          enum "1" {
  //            description "BFD version 1";
  //          }
  //          enum "automatic" {
  //            description "Choose BFD version automatically";
  //          }
  //        }
  //      }
  //      leaf minimum-interval {
  //        description "Minimum transmit and receive interval";
  //        units "milliseconds";
  //        type union {
  //          type string {
  //            pattern "<.*>|$.*";
  //          }
  //          type uint32 {
  //            range "1 .. 255000";
  //          }
  //        }
  //      }
  //      leaf minimum-transmit-interval {
  //        description "Minimum transmit interval";
  //        status deprecated;
  //        units "milliseconds";
  //        type union {
  //          type string {
  //            pattern "<.*>|$.*";
  //          }
  //          type uint32 {
  //            range "1 .. 255000";
  //          }
  //        }
  //      }
  //      leaf minimum-receive-interval {
  //        description "Minimum receive interval";
  //        units "milliseconds";
  //        type union {
  //          type string {
  //            pattern "<.*>|$.*";
  //          }
  //          type uint32 {
  //            range "1 .. 255000";
  //          }
  //        }
  //      }
  //      leaf multiplier {
  //        description "Detection time multiplier";
  //        default "3";
  //        type union {
  //          type string {
  //            pattern "<.*>|$.*";
  //          }
  //          type uint32 {
  //            range "1 .. 255";
  //          }
  //        }
  //      }
  //      leaf inline-disable {
  //        description "Disable inline mode for this BFD session";
  //        type empty;
  //      }
  //      leaf pdu-size {
  //        description "BFD transport protocol payload size";
  //        default "24";
  //        type union {
  //          type string {
  //            pattern "<.*>|$.*";
  //          }
  //          type uint32 {
  //            range "24 .. 9000";
  //          }
  //        }
  //      }
  //      choice adaptation-choice {
  //        case case_1 {
  //          leaf no-adaptation {
  //            description "Disable adaptation";
  //            type empty;
  //          }
  //        }
  //      }
  //      container transmit-interval {
  //        description "Transmit-interval options";
  //        // uses apply-advanced;
  //        leaf minimum-interval {
  //          description "Minimum transmit interval";
  //          units "milliseconds";
  //          type union {
  //            type string {
  //              pattern "<.*>|$.*";
  //            }
  //            type uint32 {
  //              range "1 .. 255000";
  //            }
  //          }
  //        }
  //        leaf threshold {
  //          description "High transmit interval triggering a trap";
  //          units "milliseconds";
  //          type union {
  //            type uint32;
  //            type string {
  //              pattern "<.*>|$.*";
  //            }
  //          }
  //        }
  //      }
  //      container detection-time {
  //        description "Detection-time options";
  //        // uses apply-advanced;
  //        leaf threshold {
  //          description "High detection-time triggering a trap";
  //          units "milliseconds";
  //          type union {
  //            type uint32;
  //            type string {
  //              pattern "<.*>|$.*";
  //            }
  //          }
  //        }
  //      }
  //      container authentication {
  //        description "Authentication options";
  //        // uses apply-advanced;
  //        leaf key-chain {
  //          description "Key chain name";
  //          type string;
  //        }
  //        leaf algorithm {
  //          description "Algorithm name";
  //          type enumeration {
  //            enum "simple-password" {
  //              description "Simple password";
  //            }
  //            enum "keyed-md5" {
  //              description "Keyed message Digest 5";
  //            }
  //            enum "meticulous-keyed-md5" {
  //              description "Meticulous keyed message Digest 5";
  //            }
  //            enum "keyed-sha-1" {
  //              description "Keyed secure hash algorithm (SHA1) ";
  //            }
  //            enum "meticulous-keyed-sha-1" {
  //              description "Meticulous keyed secure hash algorithm (SHA1) ";
  //            }
  //          }
  //        }
  //        leaf loose-check {
  //          description "Verify authentication only if authentication is negotiated";
  //          type empty;
  //        }
  //      }
  //      container echo {
  //        description "Echo mode parameters";
  //        // uses apply-advanced;
  //        leaf minimum-interval {
  //          description "Minimum transmit and receive interval";
  //          units "milliseconds";
  //          type union {
  //            type string {
  //              pattern "<.*>|$.*";
  //            }
  //            type uint32 {
  //              range "100 .. 255000";
  //            }
  //          }
  //        }
  //      }
  //      container echo-lite {
  //        description "Echo-lite more parameters";
  //        // uses apply-advanced;
  //        leaf minimum-interval {
  //          description "Minimum transmit and receive interval";
  //          units "milliseconds";
  //          type union {
  //            type string {
  //              pattern "<.*>|$.*";
  //            }
  //            type uint32 {
  //              range "100 .. 255000";
  //            }
  //          }
  //        }
  //      }
  //      leaf neighbor {
  //        description "BFD neighbor address";
  //        type jt:ipaddr;
  //      }
  //      leaf local-address {
  //        description "BFD local address (for multihop only)";
  //        type jt:ipaddr;
  //      }
  //      leaf holddown-interval {
  //        description "Time to hold the session-UP notification to the client";
  //        units "milliseconds";
  //        type union {
  //          type string {
  //            pattern "<.*>|$.*";
  //          }
  //          type uint32 {
  //            range "0 .. 255000";
  //          }
  //        }
  //      }
  //      leaf minimum-receive-ttl {
  //        description "Minimum receive TTL below which to drop";
  //        type union {
  //          type string {
  //            pattern "<.*>|$.*";
  //          }
  //          type uint8 {
  //            range "1 .. 255";
  //          }
  //        }
  //      }
  //    }
  //  }
  //  grouping reconfigure-trigger-type {
  //    description "DHCP reconfigure trigger";
  //    // uses apply-advanced;
  //    leaf radius-disconnect {
  //      description "Trigger DHCP reconfigure by radius initiated disconnect";
  //      type empty;
  //    }
  //  }
  //  grouping reconfigure-type {
  //    description "DHCP reconfigure processing";
  //    // uses apply-advanced;
  //    leaf clear-on-abort {
  //      description "Delete client on reconfiguration abort";
  //      type empty;
  //    }
  //    leaf attempts {
  //      description "Number of reconfigure attempts before aborting";
  //      type union {
  //        type string {
  //          pattern "<.*>|$.*";
  //        }
  //        type uint32 {
  //          range "1 .. 10";
  //        }
  //      }
  //    }
  //    leaf timeout {
  //      description "Initial timeout value for retry";
  //      type union {
  //        type string {
  //          pattern "<.*>|$.*";
  //        }
  //        type uint32 {
  //          range "1 .. 10";
  //        }
  //      }
  //    }
  //    leaf token {
  //      description "Reconfigure token";
  //      type string {
  //        length "1 .. 244";
  //      }
  //    }
  //    container trigger {
  //      description "DHCP reconfigure trigger";
  //      uses reconfigure-trigger-type;
  //    }
  //    leaf support-option-pd-exclude {
  //      description "Request prefix exclude option in reconfigure message";
  //      type empty;
  //    }
  //  }
  //  grouping relay-bulk-leasequery-v4-type {
  //    description "Configure bulk leasequery";
  //    // uses apply-advanced;
  //    leaf attempts {
  //      description "Number of retry attempts";
  //      default "360";
  //      type union {
  //        type string {
  //          pattern "<.*>|$.*";
  //        }
  //        type uint32 {
  //          range "1 .. 720";
  //        }
  //      }
  //    }
  //    leaf timeout {
  //      description "Number of seconds";
  //      default "10";
  //      units "seconds";
  //      type union {
  //        type string {
  //          pattern "<.*>|$.*";
  //        }
  //        type uint32 {
  //          range "1 .. 10";
  //        }
  //      }
  //    }
  //  }
  //  grouping relay-bulk-leasequery-v6-type {
  //    description "Configure bulk leasequery";
  //    // uses apply-advanced;
  //    leaf attempts {
  //      description "Number of retry attempts";
  //      default "6";
  //      type union {
  //        type string {
  //          pattern "<.*>|$.*";
  //        }
  //        type uint32 {
  //          range "1 .. 10";
  //        }
  //      }
  //    }
  //    leaf timeout {
  //      description "Number of seconds";
  //      default "10";
  //      units "seconds";
  //      type union {
  //        type string {
  //          pattern "<.*>|$.*";
  //        }
  //        type uint32 {
  //          range "1 .. 10";
  //        }
  //      }
  //    }
  //    container trigger {
  //      description "Trigger for bulk leasequery";
  //      leaf automatic {
  //        description "Trigger automatically";
  //        type empty;
  //      }
  //    }
  //  }
  //  grouping relay-leasequery-type {
  //    description "Configure leasequery";
  //    // uses apply-advanced;
  //    leaf attempts {
  //      description "Number of retry attempts";
  //      default "6";
  //      type union {
  //        type string {
  //          pattern "<.*>|$.*";
  //        }
  //        type uint32 {
  //          range "1 .. 10";
  //        }
  //      }
  //    }
  //    leaf timeout {
  //      description "Number of seconds";
  //      default "10";
  //      units "seconds";
  //      type union {
  //        type string {
  //          pattern "<.*>|$.*";
  //        }
  //        type uint32 {
  //          range "1 .. 10";
  //        }
  //      }
  //    }
  //  }
  //  grouping relay-option-60-type-group {
  //    description "DHCP option-60 processing";
  //    // uses apply-advanced;
  //    container vendor-option {
  //      description "Add vendor option";
  //      // uses apply-advanced;
  //      container equals {
  //        description "Option 60 equals";
  //        uses relay-option-60-match-group;
  //      }
  //      container not-equals {
  //        description "Option 60 does not equal";
  //        status deprecated;
  //        uses relay-option-60-match-group;
  //      }
  //      container starts-with {
  //        description "Option 60 starts with";
  //        uses relay-option-60-match-group;
  //      }
  //      choice server-group-choice {
  //        case case_1 {
  //          leaf default-relay-server-group {
  //            description "Name of DHCP relay server group when match is not made";
  //            type string {
  //              length "1 .. 64";
  //            }
  //          }
  //        }
  //        case case_2 {
  //          leaf default-local-server-group {
  //            description "Name of DHCP local server group when match is not made";
  //            type string {
  //              length "1 .. 64";
  //            }
  //          }
  //        }
  //        case case_3 {
  //          leaf drop {
  //            description "Discard when a match is not made";
  //            type empty;
  //          }
  //        }
  //        case case_4 {
  //          leaf forward-only {
  //            description "Forward without subscriber services when a match is not made";
  //            type empty;
  //          }
  //        }
  //      }
  //    }
  //  }
  //  grouping relay-option-60-match-group {
  //    // uses apply-advanced;
  //    list ascii {
  //      key name;
  //      description "ASCII string";
  //      leaf name {
  //        description "ASCII string";
  //        type string {
  //          length "1 .. 256";
  //        }
  //      }
  //      // uses apply-advanced;
  //      choice server-group-choice {
  //        case case_1 {
  //          leaf relay-server-group {
  //            description "Name of DHCP relay server group when match is made";
  //            type string {
  //              length "1 .. 64";
  //            }
  //          }
  //        }
  //        case case_2 {
  //          leaf local-server-group {
  //            description "Name of DHCP local server group when match is made";
  //            type string {
  //              length "1 .. 64";
  //            }
  //          }
  //        }
  //        case case_3 {
  //          leaf drop {
  //            description "Discard when a match is made";
  //            type empty;
  //          }
  //        }
  //        case case_4 {
  //          leaf forward-only {
  //            description "Forward without subscriber services when a match is made";
  //            type empty;
  //          }
  //        }
  //      }
  //    }
  //    list hexadecimal {
  //      key name;
  //      description "Hexadecimal string";
  //      leaf name {
  //        description "Hexadecimal string";
  //        type string {
  //          length "1 .. 512";
  //        }
  //      }
  //      // uses apply-advanced;
  //      choice server-group-choice {
  //        case case_1 {
  //          leaf relay-server-group {
  //            description "Name of DHCP relay server group when match is made";
  //            type string {
  //              length "1 .. 64";
  //            }
  //          }
  //        }
  //        case case_2 {
  //          leaf local-server-group {
  //            description "Name of DHCP local server group when match is made";
  //            type string {
  //              length "1 .. 64";
  //            }
  //          }
  //        }
  //        case case_3 {
  //          leaf drop {
  //            description "Discard when a match is made";
  //            type empty;
  //          }
  //        }
  //        case case_4 {
  //          leaf forward-only {
  //            description "Forward without subscriber services when a match is made";
  //            type empty;
  //          }
  //        }
  //      }
  //    }
  //  }
  //  grouping relay-option-60-type-top {
  //    description "DHCP option-60 processing";
  //    // uses apply-advanced;
  //    container vendor-option {
  //      description "Add vendor option";
  //      // uses apply-advanced;
  //      container equals {
  //        description "Option 60 equals";
  //        uses relay-option-60-match-top;
  //      }
  //      container not-equals {
  //        description "Option 60 does not equal";
  //        status deprecated;
  //        uses relay-option-60-match-top;
  //      }
  //      container starts-with {
  //        description "Option 60 starts with";
  //        uses relay-option-60-match-top;
  //      }
  //      choice server-group-choice {
  //        case case_1 {
  //          leaf default-relay-server-group {
  //            description "Name of DHCP relay server group when match is not made";
  //            type string {
  //              length "1 .. 64";
  //            }
  //          }
  //        }
  //        case case_2 {
  //          leaf default-local-server-group {
  //            description "Name of DHCP local server group when match is not made";
  //            type string {
  //              length "1 .. 64";
  //            }
  //          }
  //        }
  //        case case_3 {
  //          leaf drop {
  //            description "Discard when a match is not made";
  //            type empty;
  //          }
  //        }
  //        case case_4 {
  //          leaf forward-only {
  //            description "Forward without subscriber services when a match is not made";
  //            type empty;
  //          }
  //        }
  //      }
  //    }
  //  }
  //  grouping relay-option-60-match-top {
  //    // uses apply-advanced;
  //    list ascii {
  //      key name;
  //      description "ASCII string";
  //      leaf name {
  //        description "ASCII string";
  //        type string {
  //          length "1 .. 256";
  //        }
  //      }
  //      // uses apply-advanced;
  //      choice server-group-choice {
  //        case case_1 {
  //          leaf relay-server-group {
  //            description "Name of DHCP relay server group when match is made";
  //            type string {
  //              length "1 .. 64";
  //            }
  //          }
  //        }
  //        case case_2 {
  //          leaf local-server-group {
  //            description "Name of DHCP local server group when match is made";
  //            type string {
  //              length "1 .. 64";
  //            }
  //          }
  //        }
  //        case case_3 {
  //          leaf drop {
  //            description "Discard when a match is made";
  //            type empty;
  //          }
  //        }
  //        case case_4 {
  //          leaf forward-only {
  //            description "Forward without subscriber services when a match is made";
  //            type empty;
  //          }
  //        }
  //      }
  //    }
  //    list hexadecimal {
  //      key name;
  //      description "Hexadecimal string";
  //      leaf name {
  //        description "Hexadecimal string";
  //        type string {
  //          length "1 .. 512";
  //        }
  //      }
  //      // uses apply-advanced;
  //      choice server-group-choice {
  //        case case_1 {
  //          leaf relay-server-group {
  //            description "Name of DHCP relay server group when match is made";
  //            type string {
  //              length "1 .. 64";
  //            }
  //          }
  //        }
  //        case case_2 {
  //          leaf local-server-group {
  //            description "Name of DHCP local server group when match is made";
  //            type string {
  //              length "1 .. 64";
  //            }
  //          }
  //        }
  //        case case_3 {
  //          leaf drop {
  //            description "Discard when a match is made";
  //            type empty;
  //          }
  //        }
  //        case case_4 {
  //          leaf forward-only {
  //            description "Forward without subscriber services when a match is made";
  //            type empty;
  //          }
  //        }
  //      }
  //    }
  //  }
  //  grouping relay-option-82-type {
  //    description "DHCP option-82 processing";
  //    // uses apply-advanced;
  //    container circuit-id {
  //      presence "enable circuit-id";
  //      description "Add circuit identifier";
  //      // uses apply-advanced;
  //      container prefix {
  //        description "Add prefix to circuit/interface-id or remote-id";
  //        // uses apply-advanced;
  //        leaf host-name {
  //          description "Add router host name to circuit / interface-id or remote-id";
  //          type empty;
  //        }
  //        leaf logical-system-name {
  //          description "Add logical system name to circuit / interface-id or remote-id";
  //          type empty;
  //        }
  //        leaf routing-instance-name {
  //          description "Add routing instance name to circuit / interface-id or remote-id";
  //          type empty;
  //        }
  //      }
  //      leaf use-interface-description {
  //        description "Use interface description instead of circuit identifier";
  //        type enumeration {
  //          enum "logical" {
  //            description "Use the logical interface description";
  //          }
  //          enum "device" {
  //            description "Use the device interface description";
  //          }
  //        }
  //      }
  //      leaf use-vlan-id {
  //        description "Use VLAN id instead of name";
  //        type empty;
  //      }
  //      container vlan-id-only {
  //        presence "enable vlan-id-only";
  //        description "Use only VLAN id";
  //        // uses apply-advanced;
  //      }
  //      leaf no-vlan-interface-name {
  //        description "Not include vlan or interface name";
  //        type empty;
  //      }
  //      leaf include-irb-and-l2 {
  //        description "Include IRB and L2 interface name";
  //        type empty;
  //      }
  //      leaf user-defined {
  //        description "Include user defined string";
  //        type empty;
  //      }
  //      leaf keep-incoming-circuit-id {
  //        description "Keep incoming circuit identifier";
  //        type empty;
  //      }
  //    }
  //    container remote-id {
  //      presence "enable remote-id";
  //      description "Add remote identifier";
  //      // uses apply-advanced;
  //      container prefix {
  //        description "Add prefix to circuit/interface-id or remote-id";
  //        // uses apply-advanced;
  //        leaf host-name {
  //          description "Add router host name to circuit / interface-id or remote-id";
  //          type empty;
  //        }
  //        leaf logical-system-name {
  //          description "Add logical system name to circuit / interface-id or remote-id";
  //          type empty;
  //        }
  //        leaf routing-instance-name {
  //          description "Add routing instance name to circuit / interface-id or remote-id";
  //          type empty;
  //        }
  //      }
  //      leaf use-interface-description {
  //        description "Use interface description instead of circuit identifier";
  //        type enumeration {
  //          enum "logical" {
  //            description "Use the logical interface description";
  //          }
  //          enum "device" {
  //            description "Use the device interface description";
  //          }
  //        }
  //      }
  //      leaf use-vlan-id {
  //        description "Use VLAN id instead of name";
  //        type empty;
  //      }
  //      leaf no-vlan-interface-name {
  //        description "Not include vlan or interface name";
  //        type empty;
  //      }
  //      leaf include-irb-and-l2 {
  //        description "Include IRB and L2 interface name";
  //        type empty;
  //      }
  //      container hostname-only {
  //        presence "enable hostname-only";
  //        description "Include hostname only";
  //        // uses apply-advanced;
  //      }
  //      leaf keep-incoming-remote-id {
  //        description "Keep incoming remote identifier";
  //        type empty;
  //      }
  //      leaf use-string {
  //        description "Use raw string instead of the default remote id";
  //        type string;
  //      }
  //    }
  //    leaf server-id-override {
  //      description "Add link-selection and server-id sub-options on packets to server";
  //      type empty;
  //    }
  //    leaf link-selection {
  //      description "Add link-selection suboption on packets to server";
  //      type empty;
  //    }
  //    leaf exclude-relay-agent-identifier {
  //      description "Exclude relay agent identifier from packets to server";
  //      type empty;
  //    }
  //    container vendor-specific {
  //      description "Add vendor-specific information";
  //      uses jdhcp-vendor-specific-type;
  //    }
  //  }
  //  grouping relay-v4-option-ascii-hex {
  //    // uses apply-advanced;
  //    list ascii {
  //      key name;
  //      description "ASCII string";
  //      leaf name {
  //        description "ASCII string";
  //        type string {
  //          length "1 .. 256";
  //        }
  //      }
  //      // uses apply-advanced;
  //      choice server-group-choice {
  //        case case_1 {
  //          leaf relay-server-group {
  //            description "Name of DHCP relay server group when match is made";
  //            type string {
  //              length "1 .. 64";
  //            }
  //          }
  //        }
  //        case case_2 {
  //          leaf local-server-group {
  //            description "Name of DHCP local server group when match is made";
  //            type string {
  //              length "1 .. 64";
  //            }
  //          }
  //        }
  //        case case_3 {
  //          leaf drop {
  //            description "Discard when a match is made";
  //            type empty;
  //          }
  //        }
  //        case case_4 {
  //          leaf forward-only {
  //            description "Forward without subscriber services when a match is made";
  //            type empty;
  //          }
  //        }
  //      }
  //    }
  //    list hexadecimal {
  //      key name;
  //      description "Hexadecimal string";
  //      leaf name {
  //        description "Hexadecimal string";
  //        type string {
  //          length "1 .. 512";
  //        }
  //      }
  //      // uses apply-advanced;
  //      choice server-group-choice {
  //        case case_1 {
  //          leaf relay-server-group {
  //            description "Name of DHCP relay server group when match is made";
  //            type string {
  //              length "1 .. 64";
  //            }
  //          }
  //        }
  //        case case_2 {
  //          leaf local-server-group {
  //            description "Name of DHCP local server group when match is made";
  //            type string {
  //              length "1 .. 64";
  //            }
  //          }
  //        }
  //        case case_3 {
  //          leaf drop {
  //            description "Discard when a match is made";
  //            type empty;
  //          }
  //        }
  //        case case_4 {
  //          leaf forward-only {
  //            description "Forward without subscriber services when a match is made";
  //            type empty;
  //          }
  //        }
  //      }
  //    }
  //  }
  //  grouping relay-v6-option-ascii-hex {
  //    // uses apply-advanced;
  //    list ascii {
  //      key name;
  //      description "ASCII string";
  //      leaf name {
  //        description "ASCII string";
  //        type string {
  //          length "1 .. 256";
  //        }
  //      }
  //      // uses apply-advanced;
  //      choice server-group-choice {
  //        case case_1 {
  //          leaf relay-server-group {
  //            description "Name of DHCP relay server group when match is made";
  //            type string {
  //              length "1 .. 64";
  //            }
  //          }
  //        }
  //        case case_2 {
  //          leaf drop {
  //            description "Discard when a match is made";
  //            type empty;
  //          }
  //        }
  //        case case_3 {
  //          leaf forward-only {
  //            description "Forward without subscriber services when a match is made";
  //            type empty;
  //          }
  //        }
  //      }
  //    }
  //    list hexadecimal {
  //      key name;
  //      description "Hexadecimal string";
  //      leaf name {
  //        description "Hexadecimal string";
  //        type string {
  //          length "1 .. 512";
  //        }
  //      }
  //      // uses apply-advanced;
  //      choice server-group-choice {
  //        case case_1 {
  //          leaf relay-server-group {
  //            description "Name of DHCP relay server group when match is made";
  //            type string {
  //              length "1 .. 64";
  //            }
  //          }
  //        }
  //        case case_2 {
  //          leaf drop {
  //            description "Discard when a match is made";
  //            type empty;
  //          }
  //        }
  //        case case_3 {
  //          leaf forward-only {
  //            description "Forward without subscriber services when a match is made";
  //            type empty;
  //          }
  //        }
  //      }
  //    }
  //  }
   grouping rib-inet3 {
     // uses apply-advanced;
     container inet.3 {
       presence "enable inet.3";
       description "Use inet.3 to exchange labeled unicast routes";
       // uses apply-advanced;
     }
   }
   grouping rib_aggregate_type {
     // uses apply-advanced;
     container defaults {
       description "Global route options";
       // uses apply-advanced;
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         // uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
       container algorithm {
         description "Algorithm number";
         leaf number {
           description "Algorithm number";
           type union {
             type string {
               pattern "<.*>|$.*";
             }
             type uint32 {
               range "0 .. 255";
             }
           }
         }
       }
     }
     leaf protocol-instance-name {
       description "Name of protocol instance under routing instance";
       type string;
     }
     list route {
       key name;
       description "Individual route options";
       leaf name {
         description "Destination prefix";
         type jt:ipprefix;
       }
       // uses apply-advanced;
       leaf description {
         description "Description for aggregate routes";
         type string {
         }
       }
       leaf-list policy {
         ordered-by user;
         description "Policy filter";
         type jt:policy-algebra;
       }
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         // uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
       container algorithm {
         description "Algorithm number";
         leaf number {
           description "Algorithm number";
           type union {
             type string {
               pattern "<.*>|$.*";
             }
             type uint32 {
               range "0 .. 255";
             }
           }
         }
       }
     }
   }
   grouping rib_group_inet_type {
     description "Routing table group";
     leaf ribgroup-name {
       description "Name of the routing table group";
       type string;
     }
   }
   grouping rib_group_type {
     // uses apply-advanced;
     leaf inet-old-style {
       description "Name of the IPv4 routing table group";
       status deprecated;
       type string;
     }
     leaf inet {
       description "Name of the IPv4 routing table group";
       type string;
     }
     leaf inet3 {
       description "Name of the IPv4 inet.3 routing table group";
       type string;
     }
     leaf inet6 {
       description "Name of the IPv6 routing table group";
       type string;
     }
     leaf inet63 {
       description "Name of the IPv6 inet6.3 routing table group";
       type string;
     }
   }
   grouping rib_static_metric_type {
     leaf metric-value {
       description "Metric value";
       type union {
         type uint32;
         type string {
           pattern "<.*>|$.*";
         }
       }
     }
     leaf type {
       description "Metric type";
       type union {
         type string {
           pattern "<.*>|$.*";
         }
         type uint32 {
           range "1 .. 16";
         }
       }
     }
   }
  //  grouping rip_filter_obj {
  //    description "Filter to apply to tracing";
  //    leaf match-on {
  //      description "Argument on which to match";
  //      type enumeration {
  //        enum "prefix" {
  //          description "Filter based on prefix";
  //        }
  //      }
  //    }
  //    leaf-list policy {
  //      ordered-by user;
  //      description "Filter policy";
  //      type jt:policy-algebra;
  //    }
  //  }
  //  grouping route_record_traceoptions {
  //    description "Traceoptions for sampling route record";
  //    // uses apply-advanced;
  //    leaf no-remote-trace {
  //      description "Disable remote tracing";
  //      type empty;
  //    }
  //    container file {
  //      description "Trace file information";
  //      leaf filename {
  //        description "Name of file in which to write trace information";
  //        type string {
  //          length "1 .. 1024";
  //        }
  //      }
  //      leaf size {
  //        description "Maximum trace file size";
  //        type string;
  //      }
  //      leaf files {
  //        description "Maximum number of trace files";
  //        default "3";
  //        type union {
  //          type string {
  //            pattern "<.*>|$.*";
  //          }
  //          type uint32 {
  //            range "2 .. 1000";
  //          }
  //        }
  //      }
  //      choice world-readable-choice {
  //        leaf world-readable {
  //          description "Allow any user to read the log file";
  //          type empty;
  //        }
  //        leaf no-world-readable {
  //          description "Don't allow any user to read the log file";
  //          type empty;
  //        }
  //      }
  //      leaf match {
  //        description "Regular expression for lines to be logged";
  //        type jt:regular-expression;
  //      }
  //    }
  //    leaf level {
  //      description "Level of debugging output";
  //      default "error";
  //      type enumeration {
  //        enum "error" {
  //          description "Match error conditions";
  //        }
  //        enum "warning" {
  //          description "Match warning messages";
  //        }
  //        enum "notice" {
  //          description "Match conditions that should be handled specially";
  //        }
  //        enum "info" {
  //          description "Match informational messages";
  //        }
  //        enum "verbose" {
  //          description "Match verbose messages";
  //        }
  //        enum "all" {
  //          description "Match all levels";
  //        }
  //      }
  //    }
  //    list flag {
  //      key name;
  //      ordered-by user;
  //      description "Area of route-record to enable debuging output";
  //      leaf name {
  //        type enumeration {
  //          enum "parse" {
  //            description "Trace parsing code";
  //          }
  //          enum "all" {
  //            description "Trace all area of jflow-service code";
  //          }
  //        }
  //      }
  //    }
  //  }
  //  grouping rpd_rib_group_type {
  //    description "Routing table group";
  //    leaf name {
  //      description "Routing table group";
  //      type string;
  //    }
  //    // uses apply-advanced;
  //    leaf export-rib {
  //      description "Export routing table";
  //      type string;
  //    }
  //    leaf-list import-rib {
  //      ordered-by user;
  //      description "Import routing table";
  //      type string;
  //    }
  //    leaf-list import-policy {
  //      ordered-by user;
  //      description "Import policy";
  //      type jt:policy-algebra;
  //    }
  //  }
  //  grouping rpm-next-hop {
  //    leaf name {
  //      description "Next hop to destination";
  //      type jt:ipaddr;
  //    }
  //    // uses apply-advanced;
  //    leaf description {
  //      description "Text description of RPM route-tracking information";
  //      type string {
  //      }
  //    }
  //    list rpm-probe {
  //      key name;
  //      ordered-by user;
  //      leaf name {
  //        description "RPM probe to track";
  //        type string;
  //      }
  //      leaf rpm-test {
  //        description "RPM test to track";
  //        type string;
  //      }
  //    }
  //  }
  //  grouping sampling_family_inet6_output_type {
  //    description "Configure output options for packet sampling";
  //    // uses apply-advanced;
  //    leaf aggregate-export-interval {
  //      description "Interval of exporting aggregate accounting information";
  //      default "90";
  //      units "seconds";
  //      type union {
  //        type string {
  //          pattern "<.*>|$.*";
  //        }
  //        type uint32 {
  //          range "90 .. 1800";
  //        }
  //      }
  //    }
  //    leaf flow-inactive-timeout {
  //      description "Interval of inactivity that marks a flow inactive";
  //      default "60";
  //      units "seconds";
  //      type union {
  //        type string {
  //          pattern "<.*>|$.*";
  //        }
  //        type uint32 {
  //          range "15 .. 1800";
  //        }
  //      }
  //    }
  //    leaf flow-active-timeout {
  //      description "Interval after which an active flow is exported";
  //      default "1800";
  //      units "seconds";
  //      type union {
  //        type string {
  //          pattern "<.*>|$.*";
  //        }
  //        type uint32 {
  //          range "60 .. 1800";
  //        }
  //      }
  //    }
  //    list flow-server {
  //      key name;
  //      description "Configure sending traffic aggregates in cflowd format";
  //      max-elements 8;
  //      uses cflowd_sampling_inet6_sampling_type;
  //    }
  //    list interface {
  //      key name;
  //      description "Interfaces used to send monitored information";
  //      max-elements 1;
  //      uses packet_export_intf_type;
  //    }
  //    container inline-jflow {
  //      description "Inline processing of sampled packets";
  //      presence "enable inline-jflow";
  //      uses packet_export_inline;
  //    }
  //    list extension-service {
  //      key name;
  //      ordered-by user;
  //      description "Define the customer specific sampling configuration";
  //      leaf name {
  //        description "Customer prefixed sampling service name";
  //        type string {
  //          length "1 .. 63";
  //        }
  //      }
  //      // uses apply-advanced;
  //    }
  //  }
  //  grouping cflowd_sampling_inet6_sampling_type {
  //    leaf name {
  //      description "Name of host collecting cflowd packets";
  //      type jt:ipaddr;
  //    }
  //    // uses apply-advanced;
  //    leaf port {
  //      description "UDP port number on host collecting cflowd packets";
  //      type union {
  //        type uint16;
  //        type string {
  //          pattern "<.*>|$.*";
  //        }
  //      }
  //    }
  //    leaf dscp {
  //      description "Numeric DSCP value in the range 0 to 63";
  //      default "0";
  //      type union {
  //        type string {
  //          pattern "<.*>|$.*";
  //        }
  //        type uint8 {
  //          range "0 .. 63";
  //        }
  //      }
  //    }
  //    leaf forwarding-class {
  //      description "Forwarding-class for exported jflow packets, applicable only for inline-jflow";
  //      type string {
  //        length "1 .. 64";
  //      }
  //    }
  //    leaf routing-instance {
  //      description "Name of routing instance on which flow collector is reachable";
  //      type string;
  //    }
  //    leaf autonomous-system-type {
  //      description "Type of autonomous system number to export";
  //      default "origin";
  //      type enumeration {
  //        enum "origin" {
  //          description "Export origin-AS numbers";
  //        }
  //        enum "peer" {
  //          description "Export peer-AS numbers";
  //        }
  //      }
  //    }
  //    container aggregation {
  //      description "Aggregations to perform for exported flows (version 8 only)";
  //      uses aggregation_type;
  //    }
  //    choice local-dump-choice {
  //      leaf local-dump {
  //        description "Dump cflowd records to log file before exporting";
  //        type empty;
  //      }
  //      leaf no-local-dump {
  //        description "Don't dump cflowd records to log file before exporting";
  //        type empty;
  //      }
  //    }
  //    leaf source-address {
  //      description "Source IPv4 address for cflowd packets";
  //      type jt:ipv4addr;
  //    }
  //    container version9 {
  //      presence "enable version9";
  //      description "Export data in version 9 format";
  //      // uses apply-advanced;
  //      container template {
  //        description "Template configuration";
  //        // uses apply-advanced;
  //        leaf template-name {
  //          description "Template name";
  //          type string;
  //        }
  //      }
  //    }
  //  }
  //  grouping packet_export_inline {
  //    // uses apply-advanced;
  //    leaf source-address {
  //      description "Address to use for generating monitored packets";
  //      type jt:ipaddr;
  //    }
  //    leaf flow-export-rate {
  //      description "Flow export rate of monitored packets in kpps";
  //      type union {
  //        type string {
  //          pattern "<.*>|$.*";
  //        }
  //        type uint32 {
  //          range "1 .. 3200";
  //        }
  //      }
  //    }
  //  }
  //  grouping sampling_family_input_type {
  //    description "Configure input options for packet sampling";
  //    // uses apply-advanced;
  //    leaf rate {
  //      description "Ratio of packets to be sampled (1 out of N)";
  //      type union {
  //        type string {
  //          pattern "<.*>|$.*";
  //        }
  //        type uint32;
  //      }
  //    }
  //    leaf run-length {
  //      description "Number of samples after initial trigger";
  //      default "0";
  //      type union {
  //        type string {
  //          pattern "<.*>|$.*";
  //        }
  //        type uint32 {
  //          range "0 .. 20";
  //        }
  //      }
  //    }
  //    leaf max-packets-per-second {
  //      description "Threshold of samples per second before dropping";
  //      default "1000";
  //      type union {
  //        type uint16;
  //        type string {
  //          pattern "<.*>|$.*";
  //        }
  //      }
  //    }
  //    leaf maximum-packet-length {
  //      description "Maximum length of the sampled packet";
  //      default "0";
  //      units "bytes";
  //      type union {
  //        type string {
  //          pattern "<.*>|$.*";
  //        }
  //        type uint32 {
  //          range "0 .. 9192";
  //        }
  //      }
  //    }
  //  }
  //  grouping sampling_global_mpls_output_type {
  //    description "Configure output options for packet sampling";
  //    // uses apply-advanced;
  //    leaf aggregate-export-interval {
  //      description "Interval of exporting aggregate accounting information";
  //      default "90";
  //      units "seconds";
  //      type union {
  //        type string {
  //          pattern "<.*>|$.*";
  //        }
  //        type uint32 {
  //          range "90 .. 1800";
  //        }
  //      }
  //    }
  //    leaf flow-inactive-timeout {
  //      description "Interval of inactivity that marks a flow inactive";
  //      default "60";
  //      units "seconds";
  //      type union {
  //        type string {
  //          pattern "<.*>|$.*";
  //        }
  //        type uint32 {
  //          range "15 .. 1800";
  //        }
  //      }
  //    }
  //    leaf flow-active-timeout {
  //      description "Interval after which an active flow is exported";
  //      default "1800";
  //      units "seconds";
  //      type union {
  //        type string {
  //          pattern "<.*>|$.*";
  //        }
  //        type uint32 {
  //          range "60 .. 1800";
  //        }
  //      }
  //    }
  //    list flow-server {
  //      key name;
  //      description "Configure sending traffic aggregates in cflowd format";
  //      max-elements 8;
  //      uses cflowd_global_mpls_sampling_type;
  //    }
  //    list interface {
  //      key name;
  //      description "Interfaces used to send monitored information";
  //      max-elements 1;
  //      uses packet_export_intf_type;
  //    }
  //  }
  //  grouping cflowd_global_mpls_sampling_type {
  //    leaf name {
  //      description "Name of host collecting cflowd packets";
  //      type jt:ipaddr;
  //    }
  //    // uses apply-advanced;
  //    leaf port {
  //      description "UDP port number on host collecting cflowd packets";
  //      type union {
  //        type uint16;
  //        type string {
  //          pattern "<.*>|$.*";
  //        }
  //      }
  //    }
  //    leaf dscp {
  //      description "Numeric DSCP value in the range 0 to 63";
  //      default "0";
  //      type union {
  //        type string {
  //          pattern "<.*>|$.*";
  //        }
  //        type uint8 {
  //          range "0 .. 63";
  //        }
  //      }
  //    }
  //    leaf forwarding-class {
  //      description "Forwarding-class for exported jflow packets, applicable only for inline-jflow";
  //      type string {
  //        length "1 .. 64";
  //      }
  //    }
  //    leaf routing-instance {
  //      description "Name of routing instance on which flow collector is reachable";
  //      type string;
  //    }
  //    leaf autonomous-system-type {
  //      description "Type of autonomous system number to export";
  //      default "origin";
  //      type enumeration {
  //        enum "origin" {
  //          description "Export origin-AS numbers";
  //        }
  //        enum "peer" {
  //          description "Export peer-AS numbers";
  //        }
  //      }
  //    }
  //    container aggregation {
  //      description "Aggregations to perform for exported flows (version 8 only)";
  //      uses aggregation_type;
  //    }
  //    choice local-dump-choice {
  //      leaf local-dump {
  //        description "Dump cflowd records to log file before exporting";
  //        type empty;
  //      }
  //      leaf no-local-dump {
  //        description "Don't dump cflowd records to log file before exporting";
  //        type empty;
  //      }
  //    }
  //    leaf source-address {
  //      description "Source IPv4 address for cflowd packets";
  //      type jt:ipv4addr;
  //    }
  //    container version9 {
  //      presence "enable version9";
  //      description "Export data in version 9 format";
  //      // uses apply-advanced;
  //      container template {
  //        description "Template configuration";
  //        // uses apply-advanced;
  //        leaf template-name {
  //          description "Template name";
  //          type string;
  //        }
  //      }
  //    }
  //  }
  //  grouping sampling_input_type {
  //    description "Configure input options for packet sampling";
  //    // uses apply-advanced;
  //    leaf rate {
  //      description "Ratio of packets to be sampled (1 out of N)";
  //      type union {
  //        type string {
  //          pattern "<.*>|$.*";
  //        }
  //        type uint32;
  //      }
  //    }
  //    leaf run-length {
  //      description "Number of samples after initial trigger";
  //      default "0";
  //      type union {
  //        type string {
  //          pattern "<.*>|$.*";
  //        }
  //        type uint32 {
  //          range "0 .. 20";
  //        }
  //      }
  //    }
  //    leaf max-packets-per-second {
  //      description "Threshold of samples per second before dropping";
  //      default "1000";
  //      type union {
  //        type uint16;
  //        type string {
  //          pattern "<.*>|$.*";
  //        }
  //      }
  //    }
  //    leaf maximum-packet-length {
  //      description "Maximum length of the sampled packet";
  //      default "0";
  //      units "bytes";
  //      type union {
  //        type string {
  //          pattern "<.*>|$.*";
  //        }
  //        type uint32 {
  //          range "0 .. 9192";
  //        }
  //      }
  //    }
  //    container family {
  //      presence "enable family";
  //      description "Protocol family";
  //      status deprecated;
  //      container inet {
  //        description "Sampling parameters for IPv4";
  //        // uses apply-advanced;
  //        leaf rate {
  //          description "Ratio of packets to be sampled (1 out of N)";
  //          type union {
  //            type string {
  //              pattern "<.*>|$.*";
  //            }
  //            type uint32;
  //          }
  //        }
  //        leaf run-length {
  //          description "Number of samples after initial trigger";
  //          default "0";
  //          type union {
  //            type string {
  //              pattern "<.*>|$.*";
  //            }
  //            type uint32 {
  //              range "0 .. 20";
  //            }
  //          }
  //        }
  //        leaf max-packets-per-second {
  //          description "Threshold of samples per second before dropping";
  //          default "1000";
  //          type union {
  //            type uint16;
  //            type string {
  //              pattern "<.*>|$.*";
  //            }
  //          }
  //        }
  //        leaf maximum-packet-length {
  //          description "Maximum length of the sampled packet";
  //          default "0";
  //          units "bytes";
  //          type union {
  //            type string {
  //              pattern "<.*>|$.*";
  //            }
  //            type uint32 {
  //              range "0 .. 9192";
  //            }
  //          }
  //        }
  //      }
  //      container mpls {
  //        description "Sampling parameters for MPLS";
  //        // uses apply-advanced;
  //        leaf rate {
  //          description "Ratio of packets to be sampled (1 out of N)";
  //          type union {
  //            type string {
  //              pattern "<.*>|$.*";
  //            }
  //            type uint32;
  //          }
  //        }
  //        leaf run-length {
  //          description "Number of samples after initial trigger";
  //          default "0";
  //          type union {
  //            type string {
  //              pattern "<.*>|$.*";
  //            }
  //            type uint32 {
  //              range "0 .. 20";
  //            }
  //          }
  //        }
  //        leaf max-packets-per-second {
  //          description "Threshold of samples per second before dropping";
  //          default "1000";
  //          type union {
  //            type uint16;
  //            type string {
  //              pattern "<.*>|$.*";
  //            }
  //          }
  //        }
  //        leaf maximum-packet-length {
  //          description "Maximum length of the sampled packet";
  //          default "0";
  //          units "bytes";
  //          type union {
  //            type string {
  //              pattern "<.*>|$.*";
  //            }
  //            type uint32 {
  //              range "0 .. 9192";
  //            }
  //          }
  //        }
  //      }
  //      container inet6 {
  //        description "Sampling parameters for IPv6";
  //        // uses apply-advanced;
  //        leaf rate {
  //          description "Ratio of packets to be sampled (1 out of N)";
  //          type union {
  //            type string {
  //              pattern "<.*>|$.*";
  //            }
  //            type uint32;
  //          }
  //        }
  //        leaf run-length {
  //          description "Number of samples after initial trigger";
  //          default "0";
  //          type union {
  //            type string {
  //              pattern "<.*>|$.*";
  //            }
  //            type uint32 {
  //              range "0 .. 20";
  //            }
  //          }
  //        }
  //        leaf max-packets-per-second {
  //          description "Threshold of samples per second before dropping";
  //          default "1000";
  //          type union {
  //            type uint16;
  //            type string {
  //              pattern "<.*>|$.*";
  //            }
  //          }
  //        }
  //        leaf maximum-packet-length {
  //          description "Maximum length of the sampled packet";
  //          default "0";
  //          units "bytes";
  //          type union {
  //            type string {
  //              pattern "<.*>|$.*";
  //            }
  //            type uint32 {
  //              range "0 .. 9192";
  //            }
  //          }
  //        }
  //      }
  //    }
  //  }
  //  grouping sampling_instance_bridge_output_type {
  //    description "Configure output options for packet sampling";
  //    // uses apply-advanced;
  //    list flow-server {
  //      key name;
  //      description "Configure sending traffic aggregates in cflowd format";
  //      max-elements 8;
  //      uses cflowd_instance_bridge_sampling_type;
  //    }
  //    container inline-jflow {
  //      description "Inline processing of sampled packets";
  //      presence "enable inline-jflow";
  //      uses packet_export_inline_instance;
  //    }
  //  }
  //  grouping cflowd_instance_bridge_sampling_type {
  //    leaf name {
  //      description "Name of host collecting cflowd packets";
  //      type jt:ipaddr;
  //    }
  //    // uses apply-advanced;
  //    leaf port {
  //      description "UDP port number on host collecting cflowd packets";
  //      type union {
  //        type uint16;
  //        type string {
  //          pattern "<.*>|$.*";
  //        }
  //      }
  //    }
  //    leaf dscp {
  //      description "Numeric DSCP value in the range 0 to 63";
  //      default "0";
  //      type union {
  //        type string {
  //          pattern "<.*>|$.*";
  //        }
  //        type uint8 {
  //          range "0 .. 63";
  //        }
  //      }
  //    }
  //    leaf forwarding-class {
  //      description "Forwarding-class for exported jflow packets, applicable only for inline-jflow";
  //      type string {
  //        length "1 .. 64";
  //      }
  //    }
  //    leaf routing-instance {
  //      description "Name of routing instance on which flow collector is reachable";
  //      type string;
  //    }
  //    container version9 {
  //      presence "enable version9";
  //      description "Export data in version 9 format";
  //      // uses apply-advanced;
  //      container template {
  //        description "Template configuration";
  //        // uses apply-advanced;
  //        leaf template-name {
  //          description "Template name";
  //          type string;
  //        }
  //      }
  //    }
  //    container version-ipfix {
  //      presence "enable version-ipfix";
  //      description "Export data in version ipfix format";
  //      // uses apply-advanced;
  //      container template {
  //        description "Template configuration";
  //        // uses apply-advanced;
  //        leaf template-name {
  //          description "Template name";
  //          type string;
  //        }
  //      }
  //    }
  //  }
  //  grouping packet_export_inline_instance {
  //    // uses apply-advanced;
  //    leaf source-address {
  //      description "Address to use for generating monitored packets";
  //      type jt:ipaddr;
  //    }
  //    leaf flow-export-rate {
  //      description "Flow export rate of monitored packets in kpps";
  //      type union {
  //        type string {
  //          pattern "<.*>|$.*";
  //        }
  //        type uint32 {
  //          range "1 .. 3200";
  //        }
  //      }
  //    }
  //  }
  //  grouping sampling_instance_inet6_output_type {
  //    description "Configure output options for packet sampling";
  //    // uses apply-advanced;
  //    leaf aggregate-export-interval {
  //      description "Interval of exporting aggregate accounting information";
  //      default "90";
  //      units "seconds";
  //      type union {
  //        type string {
  //          pattern "<.*>|$.*";
  //        }
  //        type uint32 {
  //          range "90 .. 1800";
  //        }
  //      }
  //    }
  //    leaf flow-inactive-timeout {
  //      description "Interval of inactivity that marks a flow inactive";
  //      default "60";
  //      units "seconds";
  //      type union {
  //        type string {
  //          pattern "<.*>|$.*";
  //        }
  //        type uint32 {
  //          range "15 .. 1800";
  //        }
  //      }
  //    }
  //    leaf flow-active-timeout {
  //      description "Interval after which an active flow is exported";
  //      default "1800";
  //      units "seconds";
  //      type union {
  //        type string {
  //          pattern "<.*>|$.*";
  //        }
  //        type uint32 {
  //          range "60 .. 1800";
  //        }
  //      }
  //    }
  //    list flow-server {
  //      key name;
  //      description "Configure sending traffic aggregates in cflowd format";
  //      max-elements 8;
  //      uses cflowd_instance_inet6_sampling_type;
  //    }
  //    list interface {
  //      key name;
  //      description "Interfaces used to send monitored information";
  //      max-elements 1;
  //      uses packet_export_intf_type;
  //    }
  //    container inline-jflow {
  //      description "Inline processing of sampled packets";
  //      presence "enable inline-jflow";
  //      uses packet_export_inline_instance;
  //    }
  //    list extension-service {
  //      key name;
  //      ordered-by user;
  //      description "Define the customer specific sampling configuration";
  //      leaf name {
  //        description "Customer prefixed sampling service name";
  //        type string {
  //          length "1 .. 63";
  //        }
  //      }
  //      // uses apply-advanced;
  //    }
  //  }
  //  grouping cflowd_instance_inet6_sampling_type {
  //    leaf name {
  //      description "Name of host collecting cflowd packets";
  //      type jt:ipaddr;
  //    }
  //    // uses apply-advanced;
  //    leaf port {
  //      description "UDP port number on host collecting cflowd packets";
  //      type union {
  //        type uint16;
  //        type string {
  //          pattern "<.*>|$.*";
  //        }
  //      }
  //    }
  //    leaf dscp {
  //      description "Numeric DSCP value in the range 0 to 63";
  //      default "0";
  //      type union {
  //        type string {
  //          pattern "<.*>|$.*";
  //        }
  //        type uint8 {
  //          range "0 .. 63";
  //        }
  //      }
  //    }
  //    leaf forwarding-class {
  //      description "Forwarding-class for exported jflow packets, applicable only for inline-jflow";
  //      type string {
  //        length "1 .. 64";
  //      }
  //    }
  //    leaf routing-instance {
  //      description "Name of routing instance on which flow collector is reachable";
  //      type string;
  //    }
  //    leaf autonomous-system-type {
  //      description "Type of autonomous system number to export";
  //      default "origin";
  //      type enumeration {
  //        enum "origin" {
  //          description "Export origin-AS numbers";
  //        }
  //        enum "peer" {
  //          description "Export peer-AS numbers";
  //        }
  //      }
  //    }
  //    container aggregation {
  //      description "Aggregations to perform for exported flows (version 8 only)";
  //      uses aggregation_type;
  //    }
  //    choice local-dump-choice {
  //      leaf local-dump {
  //        description "Dump cflowd records to log file before exporting";
  //        type empty;
  //      }
  //      leaf no-local-dump {
  //        description "Don't dump cflowd records to log file before exporting";
  //        type empty;
  //      }
  //    }
  //    leaf source-address {
  //      description "Source IPv4 address for cflowd packets";
  //      type jt:ipv4addr;
  //    }
  //    container version9 {
  //      presence "enable version9";
  //      description "Export data in version 9 format";
  //      // uses apply-advanced;
  //      container template {
  //        description "Template configuration";
  //        // uses apply-advanced;
  //        leaf template-name {
  //          description "Template name";
  //          type string;
  //        }
  //      }
  //    }
  //    container version-ipfix {
  //      presence "enable version-ipfix";
  //      description "Export data in version ipfix format";
  //      // uses apply-advanced;
  //      container template {
  //        description "Template configuration";
  //        // uses apply-advanced;
  //        leaf template-name {
  //          description "Template name";
  //          type string;
  //        }
  //      }
  //    }
  //  }
  //  grouping sampling_instance_inet_global_output_type {
  //    description "Configure output options for packet sampling";
  //    // uses apply-advanced;
  //    leaf aggregate-export-interval {
  //      description "Interval of exporting aggregate accounting information";
  //      default "90";
  //      units "seconds";
  //      type union {
  //        type string {
  //          pattern "<.*>|$.*";
  //        }
  //        type uint32 {
  //          range "90 .. 1800";
  //        }
  //      }
  //    }
  //    leaf flow-inactive-timeout {
  //      description "Interval of inactivity that marks a flow inactive";
  //      default "60";
  //      units "seconds";
  //      type union {
  //        type string {
  //          pattern "<.*>|$.*";
  //        }
  //        type uint32 {
  //          range "15 .. 1800";
  //        }
  //      }
  //    }
  //    leaf flow-active-timeout {
  //      description "Interval after which an active flow is exported";
  //      default "1800";
  //      units "seconds";
  //      type union {
  //        type string {
  //          pattern "<.*>|$.*";
  //        }
  //        type uint32 {
  //          range "60 .. 1800";
  //        }
  //      }
  //    }
  //    container file {
  //      description "Configure parameters for dumping sampled packets";
  //      choice enable-disable {
  //        case case_1 {
  //          leaf disable {
  //            description "Disable sampled packet dumps";
  //            type empty;
  //          }
  //        }
  //      }
  //      leaf filename {
  //        description "Name of file to contain sampled packet dumps";
  //        type string {
  //          length "1 .. 1024";
  //        }
  //      }
  //      leaf files {
  //        description "Maximum number of sampled packet dump files";
  //        default "10";
  //        type union {
  //          type string {
  //            pattern "<.*>|$.*";
  //          }
  //          type uint32 {
  //            range "2 .. 10000";
  //          }
  //        }
  //      }
  //      leaf size {
  //        description "Maximum sample dump file size";
  //        type string;
  //      }
  //      choice world-readable-choice {
  //        leaf world-readable {
  //          description "Allow any user to read the sampled dump";
  //          type empty;
  //        }
  //        leaf no-world-readable {
  //          description "Don't allow any user to read the sampled dump";
  //          type empty;
  //        }
  //      }
  //      choice stamp-choice {
  //        leaf stamp {
  //          description "Timestamp every packet in the dump";
  //          type empty;
  //        }
  //        leaf no-stamp {
  //          description "Don't timestamp every packet in the dump";
  //          type empty;
  //        }
  //      }
  //    }
  //    container port-mirroring {
  //      description "Configure sending sampled traffic out through an interface";
  //      presence "enable port-mirroring";
  //      uses inet_pm_family_output_type;
  //    }
  //    list flow-server {
  //      key name;
  //      description "Configure sending traffic aggregates in cflowd format";
  //      max-elements 8;
  //      uses cflowd_sampling_inet_type;
  //    }
  //    list interface {
  //      key name;
  //      description "Interfaces used to send monitored information";
  //      max-elements 1;
  //      uses packet_export_intf_type;
  //    }
  //    container inline-jflow {
  //      description "Inline processing of sampled packets";
  //      presence "enable inline-jflow";
  //      uses packet_export_inline;
  //    }
  //    list extension-service {
  //      key name;
  //      ordered-by user;
  //      description "Define the customer specific sampling configuration";
  //      leaf name {
  //        description "Customer prefixed sampling service name";
  //        type string {
  //          length "1 .. 63";
  //        }
  //      }
  //      // uses apply-advanced;
  //    }
  //  }
  //  grouping cflowd_sampling_inet_type {
  //    leaf name {
  //      description "Name of host collecting cflowd packets";
  //      type jt:ipaddr;
  //    }
  //    // uses apply-advanced;
  //    leaf port {
  //      description "UDP port number on host collecting cflowd packets";
  //      type union {
  //        type uint16;
  //        type string {
  //          pattern "<.*>|$.*";
  //        }
  //      }
  //    }
  //    leaf dscp {
  //      description "Numeric DSCP value in the range 0 to 63";
  //      default "0";
  //      type union {
  //        type string {
  //          pattern "<.*>|$.*";
  //        }
  //        type uint8 {
  //          range "0 .. 63";
  //        }
  //      }
  //    }
  //    leaf forwarding-class {
  //      description "Forwarding-class for exported jflow packets, applicable only for inline-jflow";
  //      type string {
  //        length "1 .. 64";
  //      }
  //    }
  //    leaf routing-instance {
  //      description "Name of routing instance on which flow collector is reachable";
  //      type string;
  //    }
  //    leaf autonomous-system-type {
  //      description "Type of autonomous system number to export";
  //      default "origin";
  //      type enumeration {
  //        enum "origin" {
  //          description "Export origin-AS numbers";
  //        }
  //        enum "peer" {
  //          description "Export peer-AS numbers";
  //        }
  //      }
  //    }
  //    container aggregation {
  //      description "Aggregations to perform for exported flows (version 8 only)";
  //      uses aggregation_type;
  //    }
  //    choice local-dump-choice {
  //      leaf local-dump {
  //        description "Dump cflowd records to log file before exporting";
  //        type empty;
  //      }
  //      leaf no-local-dump {
  //        description "Don't dump cflowd records to log file before exporting";
  //        type empty;
  //      }
  //    }
  //    leaf source-address {
  //      description "Source IPv4 address for cflowd packets";
  //      type jt:ipv4addr;
  //    }
  //    container version9 {
  //      presence "enable version9";
  //      description "Export data in version 9 format";
  //      // uses apply-advanced;
  //      container template {
  //        description "Template configuration";
  //        // uses apply-advanced;
  //        leaf template-name {
  //          description "Template name";
  //          type string;
  //        }
  //      }
  //    }
  //    container version-ipfix {
  //      presence "enable version-ipfix";
  //      description "Export data in version ipfix format";
  //      status deprecated;
  //      // uses apply-advanced;
  //      container template {
  //        description "Template configuration";
  //        // uses apply-advanced;
  //        leaf template-name {
  //          description "Template name";
  //          type string;
  //        }
  //      }
  //    }
  //    leaf version {
  //      description "Format of exported cflowd aggregates";
  //      default "5";
  //      type enumeration {
  //        enum "5" {
  //          description "Export cflowd aggregates in version 5 format";
  //        }
  //        enum "8" {
  //          description "Export cflowd aggregates in version 8 format";
  //        }
  //        enum "500" {
  //          description "Export cflowd aggregates in ASN 500 format";
  //        }
  //      }
  //    }
  //  }
  //  grouping sampling_instance_inet_output_type {
  //    description "Configure output options for packet sampling";
  //    // uses apply-advanced;
  //    leaf aggregate-export-interval {
  //      description "Interval of exporting aggregate accounting information";
  //      default "90";
  //      units "seconds";
  //      type union {
  //        type string {
  //          pattern "<.*>|$.*";
  //        }
  //        type uint32 {
  //          range "90 .. 1800";
  //        }
  //      }
  //    }
  //    leaf flow-inactive-timeout {
  //      description "Interval of inactivity that marks a flow inactive";
  //      default "60";
  //      units "seconds";
  //      type union {
  //        type string {
  //          pattern "<.*>|$.*";
  //        }
  //        type uint32 {
  //          range "15 .. 1800";
  //        }
  //      }
  //    }
  //    leaf flow-active-timeout {
  //      description "Interval after which an active flow is exported";
  //      default "1800";
  //      units "seconds";
  //      type union {
  //        type string {
  //          pattern "<.*>|$.*";
  //        }
  //        type uint32 {
  //          range "60 .. 1800";
  //        }
  //      }
  //    }
  //    list flow-server {
  //      key name;
  //      description "Configure sending traffic aggregates in cflowd format";
  //      max-elements 8;
  //      uses cflowd_instance_inet_sampling_type;
  //    }
  //    list interface {
  //      key name;
  //      description "Interfaces used to send monitored information";
  //      max-elements 1;
  //      uses packet_export_intf_type;
  //    }
  //    container inline-jflow {
  //      description "Inline processing of sampled packets";
  //      presence "enable inline-jflow";
  //      uses packet_export_inline_instance;
  //    }
  //    list extension-service {
  //      key name;
  //      ordered-by user;
  //      description "Define the customer specific sampling configuration";
  //      leaf name {
  //        description "Customer prefixed sampling service name";
  //        type string {
  //          length "1 .. 63";
  //        }
  //      }
  //      // uses apply-advanced;
  //    }
  //  }
  //  grouping cflowd_instance_inet_sampling_type {
  //    leaf name {
  //      description "Name of host collecting cflowd packets";
  //      type jt:ipaddr;
  //    }
  //    // uses apply-advanced;
  //    leaf port {
  //      description "UDP port number on host collecting cflowd packets";
  //      type union {
  //        type uint16;
  //        type string {
  //          pattern "<.*>|$.*";
  //        }
  //      }
  //    }
  //    leaf dscp {
  //      description "Numeric DSCP value in the range 0 to 63";
  //      default "0";
  //      type union {
  //        type string {
  //          pattern "<.*>|$.*";
  //        }
  //        type uint8 {
  //          range "0 .. 63";
  //        }
  //      }
  //    }
  //    leaf forwarding-class {
  //      description "Forwarding-class for exported jflow packets, applicable only for inline-jflow";
  //      type string {
  //        length "1 .. 64";
  //      }
  //    }
  //    leaf routing-instance {
  //      description "Name of routing instance on which flow collector is reachable";
  //      type string;
  //    }
  //    leaf autonomous-system-type {
  //      description "Type of autonomous system number to export";
  //      default "origin";
  //      type enumeration {
  //        enum "origin" {
  //          description "Export origin-AS numbers";
  //        }
  //        enum "peer" {
  //          description "Export peer-AS numbers";
  //        }
  //      }
  //    }
  //    container aggregation {
  //      description "Aggregations to perform for exported flows (version 8 only)";
  //      uses aggregation_type;
  //    }
  //    choice local-dump-choice {
  //      leaf local-dump {
  //        description "Dump cflowd records to log file before exporting";
  //        type empty;
  //      }
  //      leaf no-local-dump {
  //        description "Don't dump cflowd records to log file before exporting";
  //        type empty;
  //      }
  //    }
  //    leaf source-address {
  //      description "Source IPv4 address for cflowd packets";
  //      type jt:ipv4addr;
  //    }
  //    container version9 {
  //      presence "enable version9";
  //      description "Export data in version 9 format";
  //      // uses apply-advanced;
  //      container template {
  //        description "Template configuration";
  //        // uses apply-advanced;
  //        leaf template-name {
  //          description "Template name";
  //          type string;
  //        }
  //      }
  //    }
  //    container version-ipfix {
  //      presence "enable version-ipfix";
  //      description "Export data in version ipfix format";
  //      // uses apply-advanced;
  //      container template {
  //        description "Template configuration";
  //        // uses apply-advanced;
  //        leaf template-name {
  //          description "Template name";
  //          type string;
  //        }
  //      }
  //    }
  //    leaf version {
  //      description "Format of exported cflowd aggregates";
  //      default "5";
  //      type enumeration {
  //        enum "5" {
  //          description "Export cflowd aggregates in version 5 format";
  //        }
  //        enum "8" {
  //          description "Export cflowd aggregates in version 8 format";
  //        }
  //      }
  //    }
  //  }
  //  grouping sampling_instance_input_type {
  //    description "Configure input options for packet sampling";
  //    // uses apply-advanced;
  //    leaf rate {
  //      description "Ratio of packets to be sampled (1 out of N)";
  //      type union {
  //        type string {
  //          pattern "<.*>|$.*";
  //        }
  //        type uint32;
  //      }
  //    }
  //    leaf run-length {
  //      description "Number of samples after initial trigger";
  //      default "0";
  //      type union {
  //        type string {
  //          pattern "<.*>|$.*";
  //        }
  //        type uint32 {
  //          range "0 .. 20";
  //        }
  //      }
  //    }
  //    leaf max-packets-per-second {
  //      description "Threshold of samples per second before dropping";
  //      default "1000";
  //      type union {
  //        type uint16;
  //        type string {
  //          pattern "<.*>|$.*";
  //        }
  //      }
  //    }
  //    leaf maximum-packet-length {
  //      description "Maximum length of the sampled packet";
  //      default "0";
  //      units "bytes";
  //      type union {
  //        type string {
  //          pattern "<.*>|$.*";
  //        }
  //        type uint32 {
  //          range "0 .. 9192";
  //        }
  //      }
  //    }
  //  }
  //  grouping sampling_instance_mpls_output_type {
  //    description "Configure output options for packet sampling";
  //    // uses apply-advanced;
  //    leaf aggregate-export-interval {
  //      description "Interval of exporting aggregate accounting information";
  //      default "90";
  //      units "seconds";
  //      type union {
  //        type string {
  //          pattern "<.*>|$.*";
  //        }
  //        type uint32 {
  //          range "90 .. 1800";
  //        }
  //      }
  //    }
  //    leaf flow-inactive-timeout {
  //      description "Interval of inactivity that marks a flow inactive";
  //      default "60";
  //      units "seconds";
  //      type union {
  //        type string {
  //          pattern "<.*>|$.*";
  //        }
  //        type uint32 {
  //          range "15 .. 1800";
  //        }
  //      }
  //    }
  //    leaf flow-active-timeout {
  //      description "Interval after which an active flow is exported";
  //      default "1800";
  //      units "seconds";
  //      type union {
  //        type string {
  //          pattern "<.*>|$.*";
  //        }
  //        type uint32 {
  //          range "60 .. 1800";
  //        }
  //      }
  //    }
  //    list flow-server {
  //      key name;
  //      description "Configure sending traffic aggregates in cflowd format";
  //      max-elements 8;
  //      uses cflowd_instance_mpls_sampling_type;
  //    }
  //    list interface {
  //      key name;
  //      description "Interfaces used to send monitored information";
  //      max-elements 1;
  //      uses packet_export_intf_type;
  //    }
  //    container inline-jflow {
  //      description "Inline processing of sampled packets";
  //      presence "enable inline-jflow";
  //      uses packet_export_inline_instance;
  //    }
  //  }
  //  grouping cflowd_instance_mpls_sampling_type {
  //    leaf name {
  //      description "Name of host collecting cflowd packets";
  //      type jt:ipaddr;
  //    }
  //    // uses apply-advanced;
  //    leaf port {
  //      description "UDP port number on host collecting cflowd packets";
  //      type union {
  //        type uint16;
  //        type string {
  //          pattern "<.*>|$.*";
  //        }
  //      }
  //    }
  //    leaf dscp {
  //      description "Numeric DSCP value in the range 0 to 63";
  //      default "0";
  //      type union {
  //        type string {
  //          pattern "<.*>|$.*";
  //        }
  //        type uint8 {
  //          range "0 .. 63";
  //        }
  //      }
  //    }
  //    leaf forwarding-class {
  //      description "Forwarding-class for exported jflow packets, applicable only for inline-jflow";
  //      type string {
  //        length "1 .. 64";
  //      }
  //    }
  //    leaf routing-instance {
  //      description "Name of routing instance on which flow collector is reachable";
  //      type string;
  //    }
  //    leaf autonomous-system-type {
  //      description "Type of autonomous system number to export";
  //      default "origin";
  //      type enumeration {
  //        enum "origin" {
  //          description "Export origin-AS numbers";
  //        }
  //        enum "peer" {
  //          description "Export peer-AS numbers";
  //        }
  //      }
  //    }
  //    container aggregation {
  //      description "Aggregations to perform for exported flows (version 8 only)";
  //      uses aggregation_type;
  //    }
  //    choice local-dump-choice {
  //      leaf local-dump {
  //        description "Dump cflowd records to log file before exporting";
  //        type empty;
  //      }
  //      leaf no-local-dump {
  //        description "Don't dump cflowd records to log file before exporting";
  //        type empty;
  //      }
  //    }
  //    leaf source-address {
  //      description "Source IPv4 address for cflowd packets";
  //      type jt:ipv4addr;
  //    }
  //    container version9 {
  //      presence "enable version9";
  //      description "Export data in version 9 format";
  //      // uses apply-advanced;
  //      container template {
  //        description "Template configuration";
  //        // uses apply-advanced;
  //        leaf template-name {
  //          description "Template name";
  //          type string;
  //        }
  //      }
  //    }
  //    container version-ipfix {
  //      presence "enable version-ipfix";
  //      description "Export data in version ipfix format";
  //      // uses apply-advanced;
  //      container template {
  //        description "Template configuration";
  //        // uses apply-advanced;
  //        leaf template-name {
  //          description "Template name";
  //          type string;
  //        }
  //      }
  //    }
  //  }
  //  grouping sampling_instance_vpls_output_type {
  //    description "Configure output options for packet sampling";
  //    // uses apply-advanced;
  //    list flow-server {
  //      key name;
  //      description "Configure sending traffic aggregates in cflowd format";
  //      max-elements 8;
  //      uses cflowd_instance_vpls_sampling_type;
  //    }
  //    container inline-jflow {
  //      description "Inline processing of sampled packets";
  //      presence "enable inline-jflow";
  //      uses packet_export_inline_instance;
  //    }
  //  }
  //  grouping cflowd_instance_vpls_sampling_type {
  //    leaf name {
  //      description "Name of host collecting cflowd packets";
  //      type jt:ipaddr;
  //    }
  //    // uses apply-advanced;
  //    leaf port {
  //      description "UDP port number on host collecting cflowd packets";
  //      type union {
  //        type uint16;
  //        type string {
  //          pattern "<.*>|$.*";
  //        }
  //      }
  //    }
  //    leaf dscp {
  //      description "Numeric DSCP value in the range 0 to 63";
  //      default "0";
  //      type union {
  //        type string {
  //          pattern "<.*>|$.*";
  //        }
  //        type uint8 {
  //          range "0 .. 63";
  //        }
  //      }
  //    }
  //    leaf forwarding-class {
  //      description "Forwarding-class for exported jflow packets, applicable only for inline-jflow";
  //      type string {
  //        length "1 .. 64";
  //      }
  //    }
  //    leaf routing-instance {
  //      description "Name of routing instance on which flow collector is reachable";
  //      type string;
  //    }
  //    container version9 {
  //      presence "enable version9";
  //      description "Export data in version 9 format";
  //      // uses apply-advanced;
  //      container template {
  //        description "Template configuration";
  //        // uses apply-advanced;
  //        leaf template-name {
  //          description "Template name";
  //          type string;
  //        }
  //      }
  //    }
  //    container version-ipfix {
  //      presence "enable version-ipfix";
  //      description "Export data in version ipfix format";
  //      // uses apply-advanced;
  //      container template {
  //        description "Template configuration";
  //        // uses apply-advanced;
  //        leaf template-name {
  //          description "Template name";
  //          type string;
  //        }
  //      }
  //    }
  //  }
  //  grouping sampling_output_type {
  //    description "Configure output options for packet sampling";
  //    // uses apply-advanced;
  //    leaf aggregate-export-interval {
  //      description "Interval of exporting aggregate accounting information";
  //      default "90";
  //      units "seconds";
  //      type union {
  //        type string {
  //          pattern "<.*>|$.*";
  //        }
  //        type uint32 {
  //          range "90 .. 1800";
  //        }
  //      }
  //    }
  //    leaf flow-inactive-timeout {
  //      description "Interval of inactivity that marks a flow inactive";
  //      default "60";
  //      units "seconds";
  //      type union {
  //        type string {
  //          pattern "<.*>|$.*";
  //        }
  //        type uint32 {
  //          range "15 .. 1800";
  //        }
  //      }
  //    }
  //    leaf flow-active-timeout {
  //      description "Interval after which an active flow is exported";
  //      default "1800";
  //      units "seconds";
  //      type union {
  //        type string {
  //          pattern "<.*>|$.*";
  //        }
  //        type uint32 {
  //          range "60 .. 1800";
  //        }
  //      }
  //    }
  //    container file {
  //      description "Configure parameters for dumping sampled packets";
  //      choice enable-disable {
  //        case case_1 {
  //          leaf disable {
  //            description "Disable sampled packet dumps";
  //            type empty;
  //          }
  //        }
  //      }
  //      leaf filename {
  //        description "Name of file to contain sampled packet dumps";
  //        type string {
  //          length "1 .. 1024";
  //        }
  //      }
  //      leaf files {
  //        description "Maximum number of sampled packet dump files";
  //        default "10";
  //        type union {
  //          type string {
  //            pattern "<.*>|$.*";
  //          }
  //          type uint32 {
  //            range "2 .. 10000";
  //          }
  //        }
  //      }
  //      leaf size {
  //        description "Maximum sample dump file size";
  //        type string;
  //      }
  //      choice world-readable-choice {
  //        leaf world-readable {
  //          description "Allow any user to read the sampled dump";
  //          type empty;
  //        }
  //        leaf no-world-readable {
  //          description "Don't allow any user to read the sampled dump";
  //          type empty;
  //        }
  //      }
  //      choice stamp-choice {
  //        leaf stamp {
  //          description "Timestamp every packet in the dump";
  //          type empty;
  //        }
  //        leaf no-stamp {
  //          description "Don't timestamp every packet in the dump";
  //          type empty;
  //        }
  //      }
  //    }
  //    container port-mirroring {
  //      description "Configure sending sampled traffic out through an interface";
  //      presence "enable port-mirroring";
  //      uses inet_pm_family_output_type;
  //    }
  //    list flow-server {
  //      key name;
  //      description "Configure sending traffic aggregates in cflowd format";
  //      max-elements 8;
  //      uses cflowd_sampling_type;
  //    }
  //    list interface {
  //      key name;
  //      description "Interfaces used to send monitored information";
  //      max-elements 1;
  //      uses packet_export_intf_type;
  //    }
  //    container inline-jflow {
  //      description "Inline processing of sampled packets";
  //      presence "enable inline-jflow";
  //      uses packet_export_inline;
  //    }
  //    list extension-service {
  //      key name;
  //      ordered-by user;
  //      description "Define the customer specific sampling configuration";
  //      leaf name {
  //        description "Customer prefixed sampling service name";
  //        type string {
  //          length "1 .. 63";
  //        }
  //      }
  //      // uses apply-advanced;
  //    }
  //  }
  //  grouping cflowd_sampling_type {
  //    leaf name {
  //      description "Name of host collecting cflowd packets";
  //      type jt:ipaddr;
  //    }
  //    // uses apply-advanced;
  //    leaf port {
  //      description "UDP port number on host collecting cflowd packets";
  //      type union {
  //        type uint16;
  //        type string {
  //          pattern "<.*>|$.*";
  //        }
  //      }
  //    }
  //    leaf dscp {
  //      description "Numeric DSCP value in the range 0 to 63";
  //      default "0";
  //      type union {
  //        type string {
  //          pattern "<.*>|$.*";
  //        }
  //        type uint8 {
  //          range "0 .. 63";
  //        }
  //      }
  //    }
  //    leaf forwarding-class {
  //      description "Forwarding-class for exported jflow packets, applicable only for inline-jflow";
  //      type string {
  //        length "1 .. 64";
  //      }
  //    }
  //    leaf routing-instance {
  //      description "Name of routing instance on which flow collector is reachable";
  //      type string;
  //    }
  //    leaf autonomous-system-type {
  //      description "Type of autonomous system number to export";
  //      default "origin";
  //      type enumeration {
  //        enum "origin" {
  //          description "Export origin-AS numbers";
  //        }
  //        enum "peer" {
  //          description "Export peer-AS numbers";
  //        }
  //      }
  //    }
  //    container aggregation {
  //      description "Aggregations to perform for exported flows (version 8 only)";
  //      uses aggregation_type;
  //    }
  //    choice local-dump-choice {
  //      leaf local-dump {
  //        description "Dump cflowd records to log file before exporting";
  //        type empty;
  //      }
  //      leaf no-local-dump {
  //        description "Don't dump cflowd records to log file before exporting";
  //        type empty;
  //      }
  //    }
  //    leaf source-address {
  //      description "Source IPv4 address for cflowd packets";
  //      type jt:ipv4addr;
  //    }
  //    container version9 {
  //      presence "enable version9";
  //      description "Export data in version 9 format";
  //      // uses apply-advanced;
  //      container template {
  //        description "Template configuration";
  //        // uses apply-advanced;
  //        leaf template-name {
  //          description "Template name";
  //          type string;
  //        }
  //      }
  //    }
  //    container version-ipfix {
  //      presence "enable version-ipfix";
  //      description "Export data in version ipfix format";
  //      status deprecated;
  //      // uses apply-advanced;
  //      container template {
  //        description "Template configuration";
  //        // uses apply-advanced;
  //        leaf template-name {
  //          description "Template name";
  //          type string;
  //        }
  //      }
  //    }
  //    leaf version {
  //      description "Format of exported cflowd aggregates";
  //      default "5";
  //      type enumeration {
  //        enum "5" {
  //          description "Export cflowd aggregates in version 5 format";
  //        }
  //        enum "8" {
  //          description "Export cflowd aggregates in version 8 format";
  //        }
  //        enum "500" {
  //          description "Export cflowd aggregates in ASN 500 format";
  //        }
  //      }
  //    }
  //  }
  //  grouping sampling_traceoptions_type {
  //    description "Configure packet sampling traceoptions";
  //    // uses apply-advanced;
  //    leaf no-remote-trace {
  //      description "Disable remote tracing";
  //      type empty;
  //    }
  //    container file {
  //      description "Trace file information";
  //      leaf filename {
  //        description "Name of file in which to write trace information";
  //        type string {
  //          length "1 .. 1024";
  //        }
  //      }
  //      leaf size {
  //        description "Maximum trace file size";
  //        type string;
  //      }
  //      leaf files {
  //        description "Maximum number of trace files";
  //        default "3";
  //        type union {
  //          type string {
  //            pattern "<.*>|$.*";
  //          }
  //          type uint32 {
  //            range "2 .. 1000";
  //          }
  //        }
  //      }
  //      choice world-readable-choice {
  //        leaf world-readable {
  //          description "Allow any user to read the log file";
  //          type empty;
  //        }
  //        leaf no-world-readable {
  //          description "Don't allow any user to read the log file";
  //          type empty;
  //        }
  //      }
  //      leaf match {
  //        description "Regular expression for lines to be logged";
  //        type jt:regular-expression;
  //      }
  //    }
  //  }
  //  grouping security-dhcpv6-options-type {
  //    description "Configure DHCPv6 options";
  //    // uses apply-advanced;
  //    container option-37 {
  //      presence "enable option-37";
  //      description "Configure DHCPv6 remote identifier option";
  //      // uses apply-advanced;
  //      container prefix {
  //        description "Configure DHCPv6 remote identifier prefix";
  //        // uses apply-advanced;
  //        leaf host-name {
  //          description "Prefix router host name to DHCPv6 remote identifier";
  //          type empty;
  //        }
  //        leaf logical-system-name {
  //          description "Prefix logical system name to DHCPv6 remote identifier";
  //          type empty;
  //        }
  //        leaf routing-instance-name {
  //          description "Prefix routing instance name to DHCPv6 remote identifier";
  //          type empty;
  //        }
  //        leaf vlan-name {
  //          description "Prefix vlan name to DHCPv6 remote identifier";
  //          type empty;
  //        }
  //        leaf vlan-id {
  //          description "Prefix vlan tag to DHCPv6 remote identifier";
  //          type empty;
  //        }
  //      }
  //      leaf use-interface-mac {
  //        description "Add incoming interface's MAC address to DHCPv6 remote identifier";
  //        type empty;
  //      }
  //      leaf use-interface-index {
  //        description "Add interface index to DHCPv6 remote identifier";
  //        type enumeration {
  //          enum "logical" {
  //            description "Use the logical interface index";
  //          }
  //          enum "device" {
  //            description "Use the device interface index";
  //          }
  //        }
  //      }
  //      leaf use-interface-name {
  //        description "Add interface name to DHCPv6 remote identifier";
  //        type enumeration {
  //          enum "logical" {
  //            description "Use the logical interface name";
  //          }
  //          enum "device" {
  //            description "Use the device interface name";
  //          }
  //        }
  //      }
  //      leaf use-interface-description {
  //        description "Add interface description to DHCPv6 remote identifier";
  //        type enumeration {
  //          enum "logical" {
  //            description "Use the logical interface description";
  //          }
  //          enum "device" {
  //            description "Use the device interface description";
  //          }
  //        }
  //      }
  //      leaf use-string {
  //        description "Add custom string to DHCPv6 remote identifier";
  //        type string;
  //      }
  //    }
  //    container option-18 {
  //      presence "enable option-18";
  //      description "Configure DHCPv6 interface identifier option";
  //      // uses apply-advanced;
  //      container prefix {
  //        description "Configure DHCPv6 interface identifier prefix";
  //        // uses apply-advanced;
  //        leaf host-name {
  //          description "Prefix router host name to DHCPv6 interface identifier";
  //          type empty;
  //        }
  //        leaf logical-system-name {
  //          description "Prefix logical system name to DHCPv6 interface identifier";
  //          type empty;
  //        }
  //        leaf routing-instance-name {
  //          description "Prefix routing instance name to DHCPv6 interface identifier";
  //          type empty;
  //        }
  //        leaf vlan-name {
  //          description "Prefix vlan name to DHCPv6 interface identifier";
  //          type empty;
  //        }
  //        leaf vlan-id {
  //          description "Prefix vlan tag to DHCPv6 interface identifier";
  //          type empty;
  //        }
  //      }
  //      leaf use-interface-mac {
  //        description "Add incoming interface's MAC address to DHCPv6 circuit identifier";
  //        type empty;
  //      }
  //      leaf use-interface-index {
  //        description "Add interface index to DHCPv6 interface identifier";
  //        type enumeration {
  //          enum "logical" {
  //            description "Use the logical interface index";
  //          }
  //          enum "device" {
  //            description "Use the device interface index";
  //          }
  //        }
  //      }
  //      leaf use-interface-name {
  //        description "Add interface name to DHCPv6 remote identifier";
  //        type enumeration {
  //          enum "logical" {
  //            description "Use the logical interface name";
  //          }
  //          enum "device" {
  //            description "Use the device interface name";
  //          }
  //        }
  //      }
  //      leaf use-interface-description {
  //        description "Add interface description to DHCPv6 interface identifier";
  //        type enumeration {
  //          enum "logical" {
  //            description "Use the logical interface description";
  //          }
  //          enum "device" {
  //            description "Use the device interface description";
  //          }
  //        }
  //      }
  //      leaf use-string {
  //        description "Add custom string to DHCPv6 interface identifier";
  //        type string;
  //      }
  //    }
  //    container option-16 {
  //      presence "enable option-16";
  //      description "Configure DHCPv6 vendor class identifier option. Overwrite if exists";
  //      // uses apply-advanced;
  //      leaf use-string {
  //        description "Add custom string to DHCPv6 vendor identifier";
  //        type string;
  //      }
  //    }
  //    leaf option-79 {
  //      description "Configure DHCPv6 client link layer address option";
  //      type empty;
  //    }
  //  }
  //  grouping security-option-82-type {
  //    description "DHCP option-82 processing";
  //    // uses apply-advanced;
  //    container circuit-id {
  //      presence "enable circuit-id";
  //      description "Configure DHCP option 82 circuit id";
  //      // uses apply-advanced;
  //      container prefix {
  //        description "Configure DHCP option 82 circuit id prefix";
  //        // uses apply-advanced;
  //        leaf host-name {
  //          description "Add router host name to DHCP option-82 circuit id";
  //          type empty;
  //        }
  //        leaf logical-system-name {
  //          description "Add logical system name to DHCP option-82 circuit id";
  //          type empty;
  //        }
  //        leaf routing-instance-name {
  //          description "Add routing instance name to DHCP option-82 circuit id";
  //          type empty;
  //        }
  //      }
  //      leaf use-interface-description {
  //        description "Use interface description instead of circuit identifier";
  //        type enumeration {
  //          enum "logical" {
  //            description "Use the logical interface description";
  //          }
  //          enum "device" {
  //            description "Use the device interface description";
  //          }
  //        }
  //      }
  //      leaf use-vlan-id {
  //        description "Use VLAN id instead of name";
  //        type empty;
  //      }
  //    }
  //    container remote-id {
  //      presence "enable remote-id";
  //      description "Configure DHCP option 82 remote id";
  //      // uses apply-advanced;
  //      leaf host-name {
  //        description "Add router host name to DHCP option-82 remote id";
  //        type empty;
  //      }
  //      leaf use-interface-description {
  //        description "Use interface description instead of interface name";
  //        type enumeration {
  //          enum "logical" {
  //            description "Use the logical interface description";
  //          }
  //          enum "device" {
  //            description "Use the device interface description";
  //          }
  //        }
  //      }
  //      leaf use-string {
  //        description "Use raw string instead of the default remote id";
  //        type string;
  //      }
  //      leaf mac {
  //        description "Add chassis MAC Address to DHCP option-82 remote id";
  //        type empty;
  //      }
  //    }
  //    container vendor-id {
  //      presence "enable vendor-id";
  //      description "Configure DHCP option 82 vendor id";
  //      // uses apply-advanced;
  //      leaf use-string {
  //        description "Use raw string instead of the default vendor id";
  //        default "Juniper Networks";
  //        type string;
  //      }
  //    }
  //  }
  //  grouping server-active-leasequery-type {
  //    description "Allow active leasequery";
  //    // uses apply-advanced;
  //    leaf timeout {
  //      description "Read/write timeout in seconds";
  //      default "120";
  //      units "seconds";
  //      type union {
  //        type string {
  //          pattern "<.*>|$.*";
  //        }
  //        type uint32 {
  //          range "10 .. 3600";
  //        }
  //      }
  //    }
  //    leaf idle-timeout {
  //      description "Idle-timeout in seconds";
  //      default "60";
  //      units "seconds";
  //      type union {
  //        type string {
  //          pattern "<.*>|$.*";
  //        }
  //        type uint32 {
  //          range "10 .. 3600";
  //        }
  //      }
  //    }
  //  }
  //  grouping server-bulk-leasequery-type {
  //    description "Allow bulk leasequery";
  //    // uses apply-advanced;
  //    leaf max-connections {
  //      description "Max TCP connections allowed at a time";
  //      default "3";
  //      type union {
  //        type string {
  //          pattern "<.*>|$.*";
  //        }
  //        type uint32 {
  //          range "1 .. 10";
  //        }
  //      }
  //    }
  //    leaf timeout {
  //      description "Timeout for blocked connection";
  //      default "120";
  //      units "seconds";
  //      type union {
  //        type string {
  //          pattern "<.*>|$.*";
  //        }
  //        type uint32 {
  //          range "1 .. 1000";
  //        }
  //      }
  //    }
  //    leaf max-empty-replies {
  //      description "Maximum number of empty replies for a connection";
  //      default "5";
  //      units "seconds";
  //      type union {
  //        type string {
  //          pattern "<.*>|$.*";
  //        }
  //        type uint32 {
  //          range "1 .. 100";
  //        }
  //      }
  //    }
  //    leaf restricted-requestor {
  //      description "Allow bulk leasequery only from restricted requestors";
  //      type empty;
  //    }
  //  }
  //  grouping server-group-type {
  //    // uses apply-advanced;
  //    list server-group {
  //      key name;
  //      description "One or more server groups";
  //      leaf name {
  //        description "Server group name";
  //        type string {
  //          length "1 .. 64";
  //        }
  //      }
  //      // uses apply-advanced;
  //      list address {
  //        key name;
  //        description "IP Address of one or more DHCP servers";
  //        max-elements 32;
  //        leaf name {
  //          description "IP Address of DHCP server";
  //          type jt:ipaddr;
  //        }
  //        // uses apply-advanced;
  //      }
  //    }
  //  }
  //  grouping server-leasequery-type {
  //    description "Allow leasequery";
  //    // uses apply-advanced;
  //    leaf restricted-requestor {
  //      description "Allow leasequery only from restricted requestors";
  //      type empty;
  //    }
  //  }
  //  grouping server-match-action-choice {
  //    // uses apply-advanced;
  //    choice v4-action-choice {
  //      case case_1 {
  //        leaf forward-only {
  //          description "Forward without subscriber services";
  //          type empty;
  //        }
  //      }
  //      case case_2 {
  //        leaf create-relay-entry {
  //          description "Create relay entry and allow subscriber services";
  //          type empty;
  //        }
  //      }
  //    }
  //  }
  //  grouping server-match-v6-ascii-hex {
  //    // uses apply-advanced;
  //    list ascii {
  //      key name;
  //      description "ASCII string";
  //      leaf name {
  //        description "ASCII string";
  //        type string {
  //          length "1 .. 256";
  //        }
  //      }
  //      // uses apply-advanced;
  //      choice server-match-action-choice {
  //        case case_1 {
  //          leaf forward-only {
  //            description "Forward without subscriber services when a match is made";
  //            type empty;
  //          }
  //        }
  //        case case_2 {
  //          leaf create-relay-entry {
  //            description "Create relay entry and allow subscriber services";
  //            type empty;
  //          }
  //        }
  //      }
  //    }
  //    list hexadecimal {
  //      key name;
  //      description "Hexadecimal string";
  //      leaf name {
  //        description "Hexadecimal string";
  //        type string {
  //          length "1 .. 512";
  //        }
  //      }
  //      // uses apply-advanced;
  //      choice server-match-action-choice {
  //        case case_1 {
  //          leaf forward-only {
  //            description "Forward without subscriber services when a match is made";
  //            type empty;
  //          }
  //        }
  //        case case_2 {
  //          leaf create-relay-entry {
  //            description "Create relay entry and allow subscriber services";
  //            type empty;
  //          }
  //        }
  //      }
  //    }
  //  }
  //  grouping server-v6-option-ascii-hex {
  //    // uses apply-advanced;
  //    list ascii {
  //      key name;
  //      description "ASCII string";
  //      leaf name {
  //        description "ASCII string";
  //        type string {
  //          length "1 .. 256";
  //        }
  //      }
  //      // uses apply-advanced;
  //    }
  //    list hexadecimal {
  //      key name;
  //      description "Hexadecimal string";
  //      leaf name {
  //        description "Hexadecimal string";
  //        type string {
  //          length "1 .. 512";
  //        }
  //      }
  //      // uses apply-advanced;
  //    }
  //  }
  //  grouping service-device-object {
  //    leaf name {
  //      description "Service device name";
  //      type string {
  //        length "1 .. 64";
  //      }
  //    }
  //    // uses apply-advanced;
  //    leaf address {
  //      description "Service device ip address";
  //      type jt:ipv4addr;
  //    }
  //    container access-domain {
  //      description "Subscriber access configuration";
  //      // uses apply-advanced;
  //      leaf-list vlan-id-list {
  //        description "List of access VLAN identifiers";
  //        type jt:vlan-range;
  //      }
  //    }
  //    container provisioning-method {
  //      description "Provisioning method configuration";
  //      // uses apply-advanced;
  //      choice prov_method {
  //        case case_1 {
  //          container netconf {
  //            description "Netconf provisioning method";
  //            presence "enable netconf";
  //            uses netconf-object;
  //          }
  //        }
  //      }
  //    }
  //    container dictionary {
  //      description "Dictionary file path";
  //      // uses apply-advanced;
  //      leaf dictionary-path {
  //        description "Complete path with dictionary name";
  //        type jt:filename;
  //      }
  //    }
  //  }
  //  grouping netconf-object {
  //    // uses apply-advanced;
  //    leaf user-name {
  //      description "User name for netconf";
  //      type string {
  //        length "1 .. 64";
  //      }
  //    }
  //    leaf password {
  //      description "Password for netconf";
  //      type string {
  //        length "1 .. 64";
  //      }
  //    }
  //    leaf connection-retry-interval {
  //      description "Retry interval for connection establishment";
  //      default "3";
  //      units "seconds";
  //      type union {
  //        type string {
  //          pattern "<.*>|$.*";
  //        }
  //        type uint16 {
  //          range "1 .. 10";
  //        }
  //      }
  //    }
  //    leaf response-timeout {
  //      description "Timeout for provisioning response";
  //      default "10";
  //      units "seconds";
  //      type union {
  //        type string {
  //          pattern "<.*>|$.*";
  //        }
  //        type uint16 {
  //          range "1 .. 180";
  //        }
  //      }
  //    }
  //    leaf response-timeout-count {
  //      description "Consecutive timeout failures before taking action";
  //      default "3";
  //      type union {
  //        type string {
  //          pattern "<.*>|$.*";
  //        }
  //        type uint16 {
  //          range "1 .. 10";
  //        }
  //      }
  //    }
  //    leaf bulk-interval {
  //      description "Bulked services time interval per commit";
  //      default "1000";
  //      units "milliseconds";
  //      type union {
  //        type string {
  //          pattern "<.*>|$.*";
  //        }
  //        type uint16 {
  //          range "500 .. 50000";
  //        }
  //      }
  //    }
  //    leaf bulk-limit {
  //      description "Maximum number of bulked services per commit";
  //      default "1";
  //      type union {
  //        type string {
  //          pattern "<.*>|$.*";
  //        }
  //        type uint16 {
  //          range "1 .. 1000";
  //        }
  //      }
  //    }
  //    leaf reconfigure-bulk-limit {
  //      description "Maximum number of bulked services per reconfiguration";
  //      default "100";
  //      type union {
  //        type string {
  //          pattern "<.*>|$.*";
  //        }
  //        type uint16 {
  //          range "1 .. 1000";
  //        }
  //      }
  //    }
  //    leaf port {
  //      description "Tcp port number for netconf";
  //      default "830";
  //      type union {
  //        type string {
  //          pattern "<.*>|$.*";
  //        }
  //        type uint32 {
  //          range "1 .. 65535";
  //        }
  //      }
  //    }
  //  }
  //  grouping slaacd-config-type {
  //    description "Slaacd configuration options";
  //    // uses apply-advanced;
  //    container vlans {
  //      description "Slaac config on vlan";
  //      // uses apply-advanced;
  //      list vlan-config {
  //        key name;
  //        description "Virtual LAN configuration";
  //        uses vlan-slaacd;
  //      }
  //    }
  //    container interface {
  //      description "Slaac config on interface";
  //      // uses apply-advanced;
  //      list intf-config {
  //        key name;
  //        description "Interface configuration";
  //        uses slaacd-interface;
  //      }
  //    }
  //    container link-local-expiry-interval {
  //      description "Link local address expiry interval";
  //      // uses apply-advanced;
  //      leaf interval {
  //        description "Expiry interval";
  //        default "86400";
  //        units "seconds";
  //        type union {
  //          type string {
  //            pattern "<.*>|$.*";
  //          }
  //          type uint32 {
  //            range "60 .. 86400";
  //          }
  //        }
  //      }
  //    }
  //    container traceoptions {
  //      description "Slaac Snooping trace options";
  //      // uses apply-advanced;
  //      leaf no-remote-trace {
  //        description "Disable remote tracing";
  //        type empty;
  //      }
  //      container file {
  //        description "Trace file information";
  //        leaf filename {
  //          description "Name of file in which to write trace information";
  //          type string {
  //            length "1 .. 1024";
  //          }
  //        }
  //        leaf size {
  //          description "Maximum trace file size";
  //          type string;
  //        }
  //        leaf files {
  //          description "Maximum number of trace files";
  //          default "3";
  //          type union {
  //            type string {
  //              pattern "<.*>|$.*";
  //            }
  //            type uint32 {
  //              range "2 .. 1000";
  //            }
  //          }
  //        }
  //        choice world-readable-choice {
  //          leaf world-readable {
  //            description "Allow any user to read the log file";
  //            type empty;
  //          }
  //          leaf no-world-readable {
  //            description "Don't allow any user to read the log file";
  //            type empty;
  //          }
  //        }
  //        leaf match {
  //          description "Regular expression for lines to be logged";
  //          type jt:regular-expression;
  //        }
  //      }
  //      list flag {
  //        key name;
  //        description "Tracing parameters";
  //        leaf name {
  //          type enumeration {
  //            enum "configuration" {
  //              description "Log configuration events";
  //            }
  //            enum "init" {
  //              description "Trace init message events";
  //            }
  //            enum "state" {
  //              description "Trace state message events";
  //            }
  //            enum "rtsock" {
  //              description "Trace rtsock message events";
  //            }
  //            enum "packet" {
  //              description "Trace packet events";
  //            }
  //            enum "fsm" {
  //              description "Trace fsm update events";
  //            }
  //            enum "io" {
  //              description "Trace io events";
  //            }
  //            enum "verbose" {
  //              description "Trace verbose events";
  //            }
  //            enum "task" {
  //              description "Trace TASK related events";
  //            }
  //            enum "all" {
  //              description "Trace all events";
  //            }
  //          }
  //        }
  //      }
  //    }
  //  }
  //  grouping slaacd-interface {
  //    description "Interface name";
  //    leaf name {
  //      description "Interface name";
  //      type string;
  //    }
  //    // uses apply-advanced;
  //    container mark-interface {
  //      description "Mark interface";
  //      // uses apply-advanced;
  //      leaf trusted {
  //        description "Mark interface trusted";
  //        type empty;
  //      }
  //    }
  //    container max-allowed-contention {
  //      description "Maximum allowed contention count(will be valid only for un-trusted ports)";
  //      // uses apply-advanced;
  //      leaf count {
  //        description "Contention count";
  //        type union {
  //          type string {
  //            pattern "<.*>|$.*";
  //          }
  //          type uint16 {
  //            range "1 .. 10";
  //          }
  //        }
  //      }
  //      leaf duration {
  //        description "Contention duration";
  //        units "seconds";
  //        type union {
  //          type string {
  //            pattern "<.*>|$.*";
  //          }
  //          type uint16 {
  //            range "60 .. 3600";
  //          }
  //        }
  //      }
  //    }
  //    container auto-dad {
  //      description "Auto duplicate address detection";
  //      // uses apply-advanced;
  //      leaf retries {
  //        description "DAD retry value";
  //        default "1";
  //        type union {
  //          type string {
  //            pattern "<.*>|$.*";
  //          }
  //          type uint16 {
  //            range "1 .. 3";
  //          }
  //        }
  //      }
  //      leaf retrans-interval {
  //        description "DAD re-transmission interval";
  //        default "1";
  //        units "seconds";
  //        type union {
  //          type string {
  //            pattern "<.*>|$.*";
  //          }
  //          type uint16 {
  //            range "1 .. 6";
  //          }
  //        }
  //      }
  //    }
  //  }
  //  grouping sm-ippool-pool {
  //    description "Address pool configuration";
  //    leaf name {
  //      description "Address pool name";
  //      type string {
  //        length "1 .. 64";
  //      }
  //    }
  //    // uses apply-advanced;
  //    leaf service-mode {
  //      description "Service mode";
  //      type enumeration {
  //        enum "maintenance" {
  //          description "Maintenance mode";
  //        }
  //      }
  //    }
  //    container family {
  //      presence "enable family";
  //      description "Address family";
  //      choice family_type {
  //        case case_1 {
  //          container inet {
  //            presence "enable inet";
  //            description "IPv4 address pool configuration";
  //            // uses apply-advanced;
  //            list network {
  //              key name;
  //              ordered-by user;
  //              description "Specify IPv4 network prefix";
  //              leaf name {
  //                description "IPv4 network prefix";
  //                type jt:ipv4prefix-only;
  //              }
  //              // uses apply-advanced;
  //              leaf external-assigned {
  //                description "Assigned by an external authority";
  //                type empty;
  //              }
  //              leaf allocation-prefix-length {
  //                description "Size of address allocation block";
  //                type union {
  //                  type string {
  //                    pattern "<.*>|$.*";
  //                  }
  //                  type uint8 {
  //                    range "22 .. 32";
  //                  }
  //                }
  //              }
  //              list range {
  //                key name;
  //                ordered-by user;
  //                description "Specify ranges within the prefix";
  //                leaf name {
  //                  description "Range name";
  //                  type string {
  //                    length "1 .. 64";
  //                  }
  //                }
  //                // uses apply-advanced;
  //                leaf low {
  //                  description "Lower limit of the range";
  //                  type jt:ipv4addr;
  //                }
  //                leaf high {
  //                  description "Upper limit of the range";
  //                  type jt:ipv4addr;
  //                }
  //                leaf external-assigned {
  //                  description "Assigned by an external authority";
  //                  type empty;
  //                }
  //              }
  //            }
  //          }
  //        }
  //        case case_2 {
  //          container inet6 {
  //            presence "enable inet6";
  //            description "IPv6 address pool configuration";
  //            // uses apply-advanced;
  //            list network {
  //              key name;
  //              ordered-by user;
  //              description "Specify IPv6 network prefix";
  //              leaf name {
  //                description "IPv6 network prefix";
  //                type jt:ipv6prefix-only;
  //              }
  //              // uses apply-advanced;
  //              leaf external-assigned {
  //                description "Assigned by an external authority";
  //                type empty;
  //              }
  //              leaf allocation-prefix-length {
  //                description "Size of address allocation block";
  //                type union {
  //                  type string {
  //                    pattern "<.*>|$.*";
  //                  }
  //                  type uint8 {
  //                    range "54 .. 64";
  //                  }
  //                }
  //              }
  //              list range {
  //                key name;
  //                ordered-by user;
  //                description "Specify ranges within the prefix";
  //                leaf name {
  //                  description "Range name";
  //                  type string {
  //                    length "1 .. 64";
  //                  }
  //                }
  //                // uses apply-advanced;
  //                leaf low {
  //                  description "Lower limit of the range";
  //                  type jt:ipv6prefix-only;
  //                }
  //                leaf high {
  //                  description "Upper limit of the range";
  //                  type jt:ipv6prefix-only;
  //                }
  //                leaf external-assigned {
  //                  description "Addresses in this range are assigned to the client by an external authority";
  //                  type empty;
  //                }
  //              }
  //            }
  //          }
  //        }
  //      }
  //    }
  //    leaf ageing-window {
  //      description "Time in sec when the address should not be re-used";
  //      default "2";
  //      units "seconds";
  //      type union {
  //        type string {
  //          pattern "<.*>|$.*";
  //        }
  //        type uint16 {
  //          range "1 .. 65535";
  //        }
  //      }
  //    }
  //    leaf pool-prefetch-threshold {
  //      description "Pool usage threshold to prefetch more addresses";
  //      default "80";
  //      units "percent";
  //      type union {
  //        type string {
  //          pattern "<.*>|$.*";
  //        }
  //        type uint8 {
  //          range "1 .. 100";
  //        }
  //      }
  //    }
  //    leaf pool-snmp-trap-threshold {
  //      description "Pool usage threshold to generate SNMP trap";
  //      default "80";
  //      units "percent";
  //      type union {
  //        type string {
  //          pattern "<.*>|$.*";
  //        }
  //        type uint8 {
  //          range "1 .. 100";
  //        }
  //      }
  //    }
  //    leaf default-pool {
  //      description "Pool usage as one of default pools or APN(s) specific";
  //      type empty;
  //    }
  //  }
  //  grouping smpl-analyzer-type {
  //    leaf name {
  //      description "Analyzer name";
  //      type string {
  //        length "1 .. 63";
  //      }
  //    }
  //    // uses apply-advanced;
  //    container input {
  //      description "Ports and VLANs to monitor";
  //      uses smpl-analyzer-input-type;
  //    }
  //    container output {
  //      description "Outgoing port or VLAN for mirrored packets";
  //      uses smpl-analyzer-output-type;
  //    }
  //  }
  //  grouping smpl-analyzer-input-type {
  //    // uses apply-advanced;
  //    leaf rate {
  //      description "Ratio of packets to be sampled (1 out of N)";
  //      type union {
  //        type string {
  //          pattern "<.*>|$.*";
  //        }
  //        type uint32 {
  //          range "1 .. 65535";
  //        }
  //      }
  //    }
  //    leaf maximum-packet-length {
  //      description "Maximum length of the mirrored packet";
  //      units "bytes";
  //      type union {
  //        type string {
  //          pattern "<.*>|$.*";
  //        }
  //        type uint32 {
  //          range "0 .. 9216";
  //        }
  //      }
  //    }
  //    container ingress {
  //      description "Ports and VLANs to monitor incoming traffic";
  //      uses smpl-analyzer-ingress-type;
  //    }
  //    container egress {
  //      description "Ports and VLANs to monitor outgoing traffic";
  //      uses smpl-analyzer-egress-type;
  //    }
  //  }
  //  grouping smpl-analyzer-egress-type {
  //    // uses apply-advanced;
  //    list interface {
  //      key name;
  //      ordered-by user;
  //      description "Port to monitor outgoing traffic";
  //      uses analyzer-egress-interface-type;
  //    }
  //    list routing-instance {
  //      key name;
  //      description "Routing instances";
  //      uses analyzer-egress-routing-instance-type;
  //    }
  //    list vlan {
  //      key name;
  //      ordered-by user;
  //      description "VLAN to monitor outgoing traffic";
  //      uses analyzer-egress-vlan-type;
  //    }
  //    list bridge-domain {
  //      key name;
  //      ordered-by user;
  //      description "Bridge-domain to monitor outgoing traffic";
  //      uses analyzer-egress-bridge-domain-type;
  //    }
  //  }
  //  grouping analyzer-egress-bridge-domain-type {
  //    leaf name {
  //      description "Bridge domain name, VLAN id or VLAN range string";
  //      type string;
  //    }
  //    // uses apply-advanced;
  //  }
  //  grouping analyzer-egress-interface-type {
  //    leaf name {
  //      description "Logical interface name";
  //      type string;
  //    }
  //    // uses apply-advanced;
  //  }
  //  grouping analyzer-egress-routing-instance-type {
  //    leaf name {
  //      description "Routing instance name";
  //      type string {
  //      }
  //    }
  //    // uses apply-advanced;
  //    list vlan {
  //      key name;
  //      ordered-by user;
  //      description "VLAN to monitor outgoing traffic";
  //      uses analyzer-egress-vlan-type;
  //    }
  //    list bridge-domain {
  //      key name;
  //      ordered-by user;
  //      description "Bridge-domain to monitor outgoing traffic";
  //      uses analyzer-egress-bridge-domain-type;
  //    }
  //  }
  //  grouping analyzer-egress-vlan-type {
  //    leaf name {
  //      description "VLAN name, VLAN id or VLAN range string";
  //      type string;
  //    }
  //    // uses apply-advanced;
  //  }
  //  grouping smpl-analyzer-ingress-type {
  //    // uses apply-advanced;
  //    list interface {
  //      key name;
  //      ordered-by user;
  //      description "Port to monitor incoming traffic";
  //      uses analyzer-ingress-interface-type;
  //    }
  //    list routing-instance {
  //      key name;
  //      description "Routing instances";
  //      uses analyzer-ingress-routing-instance-type;
  //    }
  //    list vlan {
  //      key name;
  //      ordered-by user;
  //      description "VLAN to monitor incoming traffic";
  //      uses analyzer-ingress-vlan-type;
  //    }
  //    list bridge-domain {
  //      key name;
  //      ordered-by user;
  //      description "Bridge-domain to monitor incoming traffic";
  //      uses analyzer-ingress-bridge-domain-type;
  //    }
  //  }
  //  grouping analyzer-ingress-bridge-domain-type {
  //    leaf name {
  //      description "Bridge domain name, VLAN id or VLAN range string";
  //      type string;
  //    }
  //    // uses apply-advanced;
  //  }
  //  grouping analyzer-ingress-interface-type {
  //    leaf name {
  //      description "Logical interface name";
  //      type string;
  //    }
  //    // uses apply-advanced;
  //  }
  //  grouping analyzer-ingress-routing-instance-type {
  //    leaf name {
  //      description "Routing instance name";
  //      type string {
  //      }
  //    }
  //    // uses apply-advanced;
  //    list vlan {
  //      key name;
  //      ordered-by user;
  //      description "VLAN to monitor incoming traffic";
  //      uses analyzer-ingress-vlan-type;
  //    }
  //    list bridge-domain {
  //      key name;
  //      ordered-by user;
  //      description "Bridge-domain to monitor incoming traffic";
  //      uses analyzer-ingress-bridge-domain-type;
  //    }
  //  }
  //  grouping analyzer-ingress-vlan-type {
  //    leaf name {
  //      description "VLAN name, VLAN id or VLAN range string";
  //      type string;
  //    }
  //    // uses apply-advanced;
  //  }
  //  grouping smpl-analyzer-output-type {
  //    // uses apply-advanced;
  //    choice interface_or_vlan {
  //      case case_1 {
  //        leaf interface {
  //          description "Outgoing port for mirrored packets";
  //          type union {
  //            type jt:interface-name;
  //            type string {
  //              pattern "<.*>|$.*";
  //            }
  //          }
  //        }
  //      }
  //      case case_2 {
  //        leaf ip-address {
  //          description "ERSPAN Destination IP Address";
  //          type jt:ipv4addr;
  //        }
  //      }
  //      case case_3 {
  //        leaf ipv6-address {
  //          description "ERSPAN Destination IPv6 Address";
  //          type jt:ipv6addr;
  //        }
  //      }
  //      case case_4 {
  //        leaf next-hop-group {
  //          description "Next-hop-group through which to send port-mirror traffic";
  //          type string;
  //        }
  //      }
  //      case case_5 {
  //        list routing-instance {
  //          key name;
  //          description "Routing instances";
  //          max-elements 1;
  //          uses output-routing-instance-type;
  //        }
  //      }
  //      case case_6 {
  //        list vlan {
  //          key name;
  //          description "Outgoing VLAN for mirrored packets";
  //          max-elements 1;
  //          uses pm-rspan-vlan;
  //        }
  //      }
  //      case case_7 {
  //        list bridge-domain {
  //          key name;
  //          description "Outgoing bridge-domain for mirrored packets";
  //          max-elements 1;
  //          uses pm-rspan-bridge-domain;
  //        }
  //      }
  //    }
  //  }
  //  grouping output-routing-instance-type {
  //    leaf name {
  //      description "Routing instance name";
  //      type string {
  //      }
  //    }
  //    // uses apply-advanced;
  //    choice ipaddr_or_vlan {
  //      case case_1 {
  //        leaf ip-address {
  //          description "ERSPAN Destination IP Address";
  //          type jt:ipv4addr;
  //        }
  //      }
  //      case case_2 {
  //        leaf ipv6-address {
  //          description "ERSPAN Destination IPv6 Address";
  //          type jt:ipv6addr;
  //        }
  //      }
  //      case case_3 {
  //        list vlan {
  //          key name;
  //          description "Outgoing VLAN for mirrored packets";
  //          max-elements 1;
  //          uses pm-rspan-vlan;
  //        }
  //      }
  //      case case_4 {
  //        list bridge-domain {
  //          key name;
  //          description "Outgoing bridge-domain for mirrored packets";
  //          max-elements 1;
  //          uses pm-rspan-bridge-domain;
  //        }
  //      }
  //    }
  //  }
  //  grouping source-class-filters {
  //    leaf name {
  //      description "Source class name";
  //      type string;
  //    }
  //    // uses apply-advanced;
  //    container family {
  //      description "Protocol family";
  //      container inet {
  //        description "Protocol family IPv4 for firewall filter";
  //        // uses apply-advanced;
  //        container filter {
  //          description "Packet filtering";
  //          // uses apply-advanced;
  //          leaf filter-name {
  //            description "Inet Filter name";
  //            type string;
  //          }
  //        }
  //      }
  //      container inet6 {
  //        description "Protocol family IPv6 for firewall filter";
  //        // uses apply-advanced;
  //        container filter {
  //          description "Packet filtering";
  //          // uses apply-advanced;
  //          leaf filter-name {
  //            description "Inet6 Filter name";
  //            type string;
  //          }
  //        }
  //      }
  //    }
  //  }
  //  grouping spring-te-template-map {
  //    description "SPRING-TE template color map";
  //    leaf name {
  //      description "Name of SPRING-TE template";
  //      type string;
  //    }
  //    // uses apply-advanced;
  //    choice colors {
  //      case case_1 {
  //        leaf-list color {
  //          description "Set of color list to be mapped to corresponding SPRING-TE template";
  //          type union {
  //            type uint32;
  //            type string {
  //              pattern "<.*>|$.*";
  //            }
  //          }
  //        }
  //      }
  //      case case_2 {
  //        leaf color-any {
  //          description "Map any color to corresponding SPRING-TE template";
  //          type empty;
  //        }
  //      }
  //    }
  //  }
  //  grouping springte_lsp_nh_obj {
  //    // uses apply-advanced;
  //    leaf nexthop {
  //      description "SPRING-TE LSP to use to reach destination";
  //      type string {
  //        length "1 .. 128";
  //      }
  //    }
  //    container lsp-source {
  //      description "Source of tunnel creation";
  //      // uses apply-advanced;
  //      choice lsp-src-choice {
  //        case case_1 {
  //          leaf pcep {
  //            description "Path computation element protocol";
  //            type empty;
  //          }
  //        }
  //        case case_2 {
  //          leaf static {
  //            description "Static configuration";
  //            type empty;
  //          }
  //        }
  //        case case_3 {
  //          leaf dtm {
  //            description "Dynamic tunnel module";
  //            type empty;
  //          }
  //        }
  //        case case_4 {
  //          leaf bgp {
  //            description "BGP SRTE";
  //            type empty;
  //          }
  //        }
  //      }
  //    }
  //  }
  //  grouping stp-interface {
  //    leaf name {
  //      type string;
  //    }
  //    // uses apply-advanced;
  //    leaf priority {
  //      description "Interface priority (in increments of 16 - 0,16,..240)";
  //      type union {
  //        type string {
  //          pattern "<.*>|$.*";
  //        }
  //        type uint16 {
  //          range "0 .. 255";
  //        }
  //      }
  //    }
  //    leaf cost {
  //      description "Cost of the interface";
  //      type union {
  //        type string {
  //          pattern "<.*>|$.*";
  //        }
  //        type uint32 {
  //          range "1 .. 200000000";
  //        }
  //      }
  //    }
  //    leaf mode {
  //      description "Interface mode (P2P or shared)";
  //      type enumeration {
  //        enum "point-to-point" {
  //          description "Interface mode is point-to-point";
  //        }
  //        enum "shared" {
  //          description "Interface mode is shared";
  //        }
  //      }
  //    }
  //    leaf edge {
  //      description "Port is an edge port";
  //      type empty;
  //    }
  //    leaf access-trunk {
  //      description "Send/Receive untagged RSTP BPDUs on this interface";
  //      type empty;
  //    }
  //    container bpdu-timeout-action {
  //      presence "enable bpdu-timeout-action";
  //      description "Define action on BPDU expiry (Loop Protect)";
  //      // uses apply-advanced;
  //      leaf block {
  //        description "Block the interface";
  //        type empty;
  //      }
  //      leaf alarm {
  //        description "Generate an alarm";
  //        type empty;
  //      }
  //    }
  //    leaf no-root-port {
  //      description "Do not allow the interface to become root (Root Protect)";
  //      type empty;
  //    }
  //    leaf disable {
  //      description "Disable Spanning Tree on port";
  //      type empty;
  //    }
  //  }
  //  grouping stp-trace-options {
  //    description "Trace options for Spanning Tree Protocol";
  //    // uses apply-advanced;
  //    container file {
  //      description "Trace file options";
  //      leaf filename {
  //        description "Name of file in which to write trace information";
  //        type string {
  //          length "1 .. 1024";
  //        }
  //      }
  //      leaf replace {
  //        description "Replace trace file rather than appending to it";
  //        status deprecated;
  //        type empty;
  //      }
  //      leaf size {
  //        description "Maximum trace file size";
  //        type string;
  //      }
  //      leaf files {
  //        description "Maximum number of trace files";
  //        default "10";
  //        type union {
  //          type string {
  //            pattern "<.*>|$.*";
  //          }
  //          type uint32 {
  //            range "2 .. 1000";
  //          }
  //        }
  //      }
  //      leaf no-stamp {
  //        description "Do not timestamp trace file";
  //        status deprecated;
  //        type empty;
  //      }
  //      choice world-readable-choice {
  //        leaf world-readable {
  //          description "Allow any user to read the log file";
  //          type empty;
  //        }
  //        leaf no-world-readable {
  //          description "Don't allow any user to read the log file";
  //          type empty;
  //        }
  //      }
  //    }
  //    list flag {
  //      key name;
  //      ordered-by user;
  //      description "Tracing parameters";
  //      leaf name {
  //        type enumeration {
  //          enum "events" {
  //            description "Trace events to the protocol state machine";
  //          }
  //          enum "bpdu" {
  //            description "Trace BPDU reception and transmission";
  //          }
  //          enum "timers" {
  //            description "Trace protocol timers";
  //          }
  //          enum "port-information-state-machine" {
  //            description "Trace port information state machine";
  //          }
  //          enum "port-receive-state-machine" {
  //            description "Trace port receive state machine";
  //          }
  //          enum "port-role-select-state-machine" {
  //            description "Trace port role selection state machine";
  //          }
  //          enum "port-role-transit-state-machine" {
  //            description "Trace port role transit state machine";
  //          }
  //          enum "port-state-transit-state-machine" {
  //            description "Trace port state transit state machine";
  //          }
  //          enum "port-migration-state-machine" {
  //            description "Trace port migration state machine";
  //          }
  //          enum "port-transmit-state-machine" {
  //            description "Trace port transmit state machine";
  //          }
  //          enum "topology-change-state-machine" {
  //            description "Trace topology change state machine";
  //          }
  //          enum "bridge-detection-state-machine" {
  //            description "Trace Bridge detection state machine";
  //          }
  //          enum "state-machine-variables" {
  //            description "Trace when state machine variables change";
  //          }
  //          enum "ppmd" {
  //            description "Trace state and events for ppmd process";
  //          }
  //          enum "all-failures" {
  //            description "Trace all failure conditions";
  //          }
  //          enum "all" {
  //            description "Trace all";
  //          }
  //        }
  //      }
  //      leaf disable {
  //        description "Disable this trace flag";
  //        type empty;
  //      }
  //    }
  //  }
  //  grouping subscription-type {
  //    // uses apply-advanced;
  //    leaf link-subscription {
  //      description "Link bandwidth percentage for RSVP reservation";
  //      default "100";
  //      type string;
  //    }
  //    leaf ct0 {
  //      description "Subscription percentage for traffic class 0";
  //      default "100";
  //      type string;
  //    }
  //    leaf ct1 {
  //      description "Subscription percentage for traffic class 1";
  //      default "100";
  //      type string;
  //    }
  //    leaf ct2 {
  //      description "Subscription percentage for traffic class 2";
  //      default "100";
  //      type string;
  //    }
  //    leaf ct3 {
  //      description "Subscription percentage for traffic class 3";
  //      default "100";
  //      type string;
  //    }
  //    list priority {
  //      key priority-value;
  //      ordered-by user;
  //      description "Subscription percentage for a specific priority";
  //      leaf priority-value {
  //        description "Priority for which subscription percent is being configured";
  //        type union {
  //          type string {
  //            pattern "<.*>|$.*";
  //          }
  //          type uint32 {
  //            range "0 .. 7";
  //          }
  //        }
  //      }
  //      // uses apply-advanced;
  //      leaf percent {
  //        description "Subscription percent for the specific priority";
  //        type string;
  //      }
  //    }
  //  }
  //  grouping system-id-ip-map {
  //    leaf name {
  //      type jt:mac-unicast;
  //    }
  //    // uses apply-advanced;
  //    leaf ip-address {
  //      description "Peer ID (IP Address)";
  //      type jt:ipv4prefix;
  //    }
  //  }
  //  grouping te-class-object {
  //    leaf traffic-class {
  //      description "Traffic class";
  //      type enumeration {
  //        enum "ct0" {
  //          description "Traffic class 0";
  //        }
  //        enum "ct1" {
  //          description "Traffic class 1";
  //        }
  //        enum "ct2" {
  //          description "Traffic class 2";
  //        }
  //        enum "ct3" {
  //          description "Traffic class 3";
  //        }
  //      }
  //    }
  //    leaf priority {
  //      description "Preemption priority for this class";
  //      type union {
  //        type string {
  //          pattern "<.*>|$.*";
  //        }
  //        type uint32 {
  //          range "0 .. 7";
  //        }
  //      }
  //    }
  //  }
  //  grouping v6-relay-option-interface-id-type {
  //    description "Interface ID processing";
  //    // uses apply-advanced;
  //    container prefix {
  //      description "Add prefix to circuit/interface-id or remote-id";
  //      // uses apply-advanced;
  //      leaf host-name {
  //        description "Add router host name to circuit / interface-id or remote-id";
  //        type empty;
  //      }
  //      leaf logical-system-name {
  //        description "Add logical system name to circuit / interface-id or remote-id";
  //        type empty;
  //      }
  //      leaf routing-instance-name {
  //        description "Add routing instance name to circuit / interface-id or remote-id";
  //        type empty;
  //      }
  //    }
  //    leaf use-interface-description {
  //      description "Use interface description instead of circuit identifier";
  //      type enumeration {
  //        enum "logical" {
  //          description "Use the logical interface description";
  //        }
  //        enum "device" {
  //          description "Use the device interface description";
  //        }
  //      }
  //    }
  //    leaf use-vlan-id {
  //      description "Use VLAN id instead of name";
  //      type empty;
  //    }
  //    leaf no-vlan-interface-name {
  //      description "Not include vlan or interface name";
  //      type empty;
  //    }
  //    leaf include-irb-and-l2 {
  //      description "Include IRB and L2 interface name";
  //      type empty;
  //    }
  //    container use-option-82 {
  //      description "Use option-82 circuit-id for interface-id";
  //      presence "enable use-option-82";
  //      uses v6-relay-option-cid-rid-action;
  //    }
  //    container keep-incoming-interface-id {
  //      description "Keep incoming interface identifier";
  //      presence "enable keep-incoming-interface-id";
  //      uses v6-relay-option-cid-rid-action;
  //    }
  //  }
  //  grouping v6-relay-option-cid-rid-action {
  //    // uses apply-advanced;
  //    leaf strict {
  //      description "Drop packet if id not present";
  //      type empty;
  //    }
  //  }
  //  grouping v6-relay-option-remote-id-type {
  //    description "Remote ID processing";
  //    // uses apply-advanced;
  //    container prefix {
  //      description "Add prefix to circuit/interface-id or remote-id";
  //      // uses apply-advanced;
  //      leaf host-name {
  //        description "Add router host name to circuit / interface-id or remote-id";
  //        type empty;
  //      }
  //      leaf logical-system-name {
  //        description "Add logical system name to circuit / interface-id or remote-id";
  //        type empty;
  //      }
  //      leaf routing-instance-name {
  //        description "Add routing instance name to circuit / interface-id or remote-id";
  //        type empty;
  //      }
  //    }
  //    leaf use-interface-description {
  //      description "Use interface description instead of circuit identifier";
  //      type enumeration {
  //        enum "logical" {
  //          description "Use the logical interface description";
  //        }
  //        enum "device" {
  //          description "Use the device interface description";
  //        }
  //      }
  //    }
  //    leaf use-vlan-id {
  //      description "Use VLAN id instead of name";
  //      type empty;
  //    }
  //    leaf no-vlan-interface-name {
  //      description "Not include vlan or interface name";
  //      type empty;
  //    }
  //    leaf include-irb-and-l2 {
  //      description "Include IRB and L2 interface name";
  //      type empty;
  //    }
  //    container use-option-82 {
  //      description "Use option-82 remote-id for v6 remote-id";
  //      presence "enable use-option-82";
  //      uses v6-relay-option-cid-rid-action;
  //    }
  //    leaf keep-incoming-remote-id {
  //      description "Keep incoming remote identifier";
  //      type empty;
  //    }
  //  }
  //  grouping v6-server-group-type {
  //    // uses apply-advanced;
  //    list server-group {
  //      key name;
  //      description "One or more server groups";
  //      leaf name {
  //        description "DHCPv6 Server group name";
  //        type string {
  //          length "1 .. 64";
  //        }
  //      }
  //      // uses apply-advanced;
  //      list address {
  //        key name;
  //        description "IP Address of one or more DHCP servers";
  //        max-elements 32;
  //        leaf name {
  //          description "IP Address of DHCP server";
  //          type jt:ipaddr;
  //        }
  //        // uses apply-advanced;
  //      }
  //    }
  //  }
  //  grouping vlan-policy {
  //    description "Virtual LAN";
  //    leaf name {
  //      description "VLAN id";
  //      type string;
  //    }
  //    // uses apply-advanced;
  //    container policy {
  //      description "Attach policy";
  //      // uses apply-advanced;
  //      leaf policy-name {
  //        description "Router Advertisement Guard policy name";
  //        type string;
  //      }
  //      choice policy-type {
  //        case case_1 {
  //          leaf stateful {
  //            description "Stateful router advertisement guard";
  //            type empty;
  //          }
  //        }
  //        case case_2 {
  //          leaf stateless {
  //            description "Stateless router advertisement guard";
  //            type empty;
  //          }
  //        }
  //      }
  //    }
  //  }
  //  grouping vlan-slaacd {
  //    description "Virtual LAN";
  //    leaf name {
  //      description "VLAN id";
  //      type string;
  //    }
  //    // uses apply-advanced;
  //  }
  //  grouping vlan-types-routing-instance {
  //    description "Virtual LAN";
  //    leaf name {
  //      description "VLAN name";
  //      type string {
  //        length "2 .. 64";
  //      }
  //    }
  //    // uses apply-advanced;
  //    leaf description {
  //      description "Text description of VLANs";
  //      type string {
  //      }
  //    }
  //    choice vlan-identifier-choice {
  //      case case_1 {
  //        leaf vlan-id {
  //          description "IEEE 802.1q VLAN identifier for VLAN";
  //          type string;
  //        }
  //      }
  //      case case_2 {
  //        leaf-list vlan-id-list {
  //          description "Create VLAN for each of the vlan-id specified in the vlan-id-list";
  //          type jt:vlan-range;
  //        }
  //      }
  //      case case_3 {
  //        container vlan-tags {
  //          presence "enable vlan-tags";
  //          description "IEEE 802.1q VLAN tags for VLANs";
  //          leaf outer {
  //            description "[tpid.]vlan-id, tpid format is 0xNNNN and is optional";
  //            type string {
  //            }
  //          }
  //          leaf inner {
  //            description "[tpid.]vlan-id, tpid format is 0xNNNN and is optional";
  //            type string {
  //            }
  //          }
  //        }
  //      }
  //    }
  //    list interface {
  //      key name;
  //      ordered-by user;
  //      description "Interface name for this VLAN";
  //      leaf name {
  //        type string;
  //      }
  //      // uses apply-advanced;
  //    }
  //    leaf l3-interface {
  //      description "L3 interface name for this vlans";
  //      type union {
  //        type jt:interface-unit;
  //        type string {
  //          pattern "<.*>|$.*";
  //        }
  //      }
  //    }
  //    leaf no-local-switching {
  //      description "Disable local switching within CE-facing interfaces";
  //      type empty;
  //    }
  //   //  container forwarding-options {
  //   //    description "Forwarding options configuration";
  //   //    uses juniper-ethernet-switching-forwarding-options;
  //   //  }
  //   //  container multicast-snooping-options {
  //   //    description "Multicast snooping option configuration";
  //   //    uses juniper-multicast-snooping-options;
  //   //  }
  //   //  container switch-options {
  //   //    description "VLANs switch-options configuration";
  //   //    uses juniper-protocols-vlan;
  //   //  }
  //   //  leaf domain-type {
  //   //    description "Type of VLANs SVLAN/DVLAN";
  //   //    type enumeration {
  //   //      enum "bridge" {
  //   //        description "Forwarding instance";
  //   //      }
  //   //    }
  //   //  }
  //    leaf no-irb-layer-2-copy {
  //      description "Disable transmission of layer-2 copy of packets of IRB routing-interface";
  //      type empty;
  //    }
  //    leaf service-id {
  //      description "Service id required if VLAN is of type MC-AE, and vlan-id all or vlan-id none or vlan-tags is configured";
  //      type union {
  //        type string {
  //          pattern "<.*>|$.*";
  //        }
  //        type uint32 {
  //          range "1 .. 65535";
  //        }
  //      }
  //    }
  //    leaf mcae-mac-synchronize {
  //      description "Enable IRB MAC synchronization in this VLAN";
  //      type empty;
  //    }
  //    container proxy-mac {
  //      description "Proxy MAC settings";
  //      // uses apply-advanced;
  //      leaf irb {
  //        description "Reply with virtual-gateway MAC or IRB MAC";
  //        type empty;
  //      }
  //      leaf proxy-mac-address {
  //        description "Reply with configured MAC for all requests";
  //        type jt:mac-unicast;
  //      }
  //    }
  //    leaf mcae-mac-flush {
  //      description "Enable IRB MAC flush in a/s mode for this VLAN on MCAE link up";
  //      type empty;
  //    }
  //    leaf private-vlan {
  //      description "Type of secondary vlan for private vlan";
  //      type enumeration {
  //        enum "isolated" {
  //          description "Isolated vlan";
  //        }
  //        enum "community" {
  //          description "Community vlan";
  //        }
  //      }
  //    }
  //    leaf isolated-vlan {
  //      description "VLAN id or name";
  //      type string {
  //      }
  //    }
  //    leaf-list community-vlans {
  //      ordered-by user;
  //      description "List of VLAN id or name";
  //      type string;
  //    }
  //    container vxlan {
  //      // uses apply-advanced;
  //      leaf ovsdb-managed {
  //        description "Bridge-domain is managed remotely via VXLAN OVSDB Controller";
  //        type empty;
  //      }
  //      leaf vni {
  //        description "VXLAN identifier";
  //        type union {
  //          type string {
  //            pattern "<.*>|$.*";
  //          }
  //          type uint32 {
  //            range "0 .. 16777214";
  //          }
  //        }
  //      }
  //      leaf translation-vni {
  //        description "Translated VXLAN identifier";
  //        type union {
  //          type string {
  //            pattern "<.*>|$.*";
  //          }
  //          type uint32 {
  //            range "1 .. 16777214";
  //          }
  //        }
  //      }
  //      leaf multicast-group {
  //        description "Multicast group registered for VXLAN segment";
  //        type jt:ipv4addr;
  //      }
  //      leaf encapsulate-inner-vlan {
  //        description "Retain inner VLAN in the packet";
  //        type empty;
  //      }
  //      leaf decapsulate-accept-inner-vlan {
  //        description "Accept VXLAN packets with inner VLAN";
  //        type empty;
  //      }
  //      leaf unreachable-vtep-aging-timer {
  //        description "Unreachable VXLAN tunnel endpoint removal timer";
  //        units "seconds";
  //        type union {
  //          type string {
  //            pattern "<.*>|$.*";
  //          }
  //          type uint16 {
  //            range "300 .. 1800";
  //          }
  //        }
  //      }
  //      leaf ingress-node-replication {
  //        description "Enable ingress node replication";
  //        type empty;
  //      }
  //      leaf-list static-remote-vtep-list {
  //        description "Configure vlan specific static remote VXLAN tunnel endpoints";
  //        type jt:ipaddr;
  //        max-elements 1024;
  //      }
  //      leaf riot-loopback {
  //        description "Enable loopback on RIOT platform";
  //        type empty;
  //      }
  //    }
  //  }
  //  grouping juniper-ethernet-switching-forwarding-options {
  //    // uses apply-advanced;
  //    container filter {
  //      description "Filtering for ethernet switching forwarding table";
  //      // uses apply-advanced;
  //      leaf input {
  //        description "Name of input filter to apply for forwarded packets";
  //        type string;
  //      }
  //      leaf output {
  //        description "Name of output filter to apply for forwarded packets";
  //        type string;
  //      }
  //    }
  //    container flood {
  //      description "Filtering for ethernet switching flood table";
  //      // uses apply-advanced;
  //      leaf input {
  //        description "Name of input filter to apply for ethernet switching flood packets";
  //        type string;
  //      }
  //    }
  //    container dhcp-relay {
  //      description "Dynamic Host Configuration Protocol relay configuration";
  //      status deprecated;
  //      uses jdhcp-relay-type;
  //    }
  //    container dhcp-security {
  //      description "DHCP access security configuration";
  //      presence "enable dhcp-security";
  //      uses jdhcp-security-type;
  //    }
  //  }
  //  grouping juniper-protocols-vlan {
  //    description "VLANs switch-options configuration";
  //    // uses apply-advanced;
  //    leaf no-mac-aging {
  //      description "Disable MAC address aging";
  //      type empty;
  //    }
  //    container mac-table-size {
  //      description "Size of MAC address forwarding table";
  //      // uses apply-advanced;
  //      leaf limit {
  //        description "Maximum number of MAC addresses";
  //        type union {
  //          type string {
  //            pattern "<.*>|$.*";
  //          }
  //          type uint32;
  //        }
  //      }
  //      leaf packet-action {
  //        description "Action when MAC limit is reached";
  //        type enumeration {
  //          enum "none" {
  //            description "Forward the packet";
  //          }
  //          enum "drop" {
  //            description "Drop packets and do not learn. Default is forward";
  //          }
  //        }
  //      }
  //    }
  //    container mac-ip-table-size {
  //      description "Size of MAC+IP bindings table";
  //      // uses apply-advanced;
  //      leaf limit {
  //        description "Maximum number of MAC+IP bindings";
  //        type union {
  //          type string {
  //            pattern "<.*>|$.*";
  //          }
  //          type uint32;
  //        }
  //      }
  //    }
  //    container interface-mac-limit {
  //      description "Maximum MAC address learned per interface";
  //      // uses apply-advanced;
  //      leaf limit {
  //        description "Maximum number of MAC addresses per interface";
  //        type union {
  //          type string {
  //            pattern "<.*>|$.*";
  //          }
  //          type uint32;
  //        }
  //      }
  //      leaf packet-action {
  //        description "Action when MAC limit is reached";
  //        type enumeration {
  //          enum "none" {
  //            description "Forward the packet";
  //          }
  //          enum "drop" {
  //            description "Drop packets and do not learn. Default is forward";
  //          }
  //          enum "log" {
  //            description "Do not drop the packet but generate an alarm, an SNMP trap or a system log entry";
  //          }
  //          enum "shutdown" {
  //            description "Disable the interface and generate an alarm, an SNMP trap or a system log entry";
  //          }
  //          enum "drop-and-log" {
  //            description "Drop the packet and generate an alarm, an SNMP trap or a system log entry";
  //          }
  //        }
  //      }
  //    }
  //    container interface-mac-ip-limit {
  //      description "Maximum number of MAC+IP bindings learned on the interface";
  //      // uses apply-advanced;
  //      leaf limit {
  //        description "Maximum number of MAC+IP bindings per interface";
  //        type union {
  //          type string {
  //            pattern "<.*>|$.*";
  //          }
  //          type uint32;
  //        }
  //      }
  //    }
  //    container mac-move-limit {
  //      presence "enable mac-move-limit";
  //      description "Number of MAC movements allowed on this VLAN";
  //      // uses apply-advanced;
  //      choice limit-choice {
  //        case case_1 {
  //          leaf none {
  //            description "Disable mac-move-limit for this VLAN";
  //            type empty;
  //          }
  //        }
  //        case case_2 {
  //          leaf limit {
  //            description "Number of MAC movements allowed on this VLAN";
  //            type union {
  //              type string {
  //                pattern "<.*>|$.*";
  //              }
  //              type uint32 {
  //                range "1 .. 4294967295";
  //              }
  //            }
  //          }
  //        }
  //      }
  //      leaf packet-action {
  //        description "Action to be taken in case the MAC movement limit is exceeded";
  //        default "drop";
  //        type enumeration {
  //          enum "none" {
  //            description "Take no action";
  //          }
  //          enum "drop" {
  //            description "Drop the packet and do not generate an alarm";
  //          }
  //          enum "log" {
  //            description "Do not drop the packet but generate an alarm, an SNMP trap, or a system log entry.";
  //          }
  //          enum "shutdown" {
  //            description "Disable the interface and generate an alarm, an SNMP trap, or a system log entry.";
  //          }
  //          enum "drop-and-log" {
  //            description "Drop the packet and generate an alarm, an SNMP trap, or a system log entry.";
  //          }
  //          enum "vlan-member-shutdown" {
  //            description "Disable the interface of this VLAN";
  //          }
  //        }
  //      }
  //      list interface {
  //        key name;
  //        description "Interface that connect this site to the VPN";
  //        leaf name {
  //          description "Interface name";
  //          type union {
  //            type jt:interface-name;
  //            type string {
  //              pattern "<.*>|$.*";
  //            }
  //          }
  //        }
  //        // uses apply-advanced;
  //        leaf action-priority {
  //          description "Blocking priority of this interface on mac move detection";
  //          type union {
  //            type string {
  //              pattern "<.*>|$.*";
  //            }
  //            type uint32 {
  //              range "0 .. 7";
  //            }
  //          }
  //        }
  //      }
  //    }
  //    leaf mac-table-aging-time {
  //      description "Delay for discarding MAC address if no updates are received";
  //      units "seconds";
  //      type union {
  //        type string {
  //          pattern "<.*>|$.*";
  //        }
  //        type uint32;
  //      }
  //    }
  //    leaf no-mac-learning {
  //      description "Disable dynamic MAC address learning";
  //      type empty;
  //    }
  //    leaf no-normalization {
  //      description "Disable vlan id normalization for interfaces";
  //      type empty;
  //    }
  //    leaf drop-unknown-mac-ip {
  //      description "Drop unknown MAC-IP traffic";
  //      type empty;
  //    }
  //    leaf mac-statistics {
  //      description "Enable MAC address statistics";
  //      type empty;
  //    }
  //    container static-rvtep-mac {
  //      description "Configure Static MAC and remote VxLAN tunnel endpoint entries";
  //      // uses apply-advanced;
  //      list mac {
  //        key "mac_addr remote-vtep";
  //        description "Unicast MAC address";
  //        leaf mac_addr {
  //          type jt:mac-unicast;
  //        }
  //        leaf remote-vtep {
  //          description "Configure static remote VXLAN tunnel endpoints";
  //          type jt:ipaddr;
  //        }
  //      }
  //    }
  //    container network-isolation-profile {
  //      description "Network isolation configuration";
  //      // uses apply-advanced;
  //      list group {
  //        key name;
  //        description "Network isolation group";
  //        leaf name {
  //          description "Group name";
  //          type string;
  //        }
  //        // uses apply-advanced;
  //      }
  //    }
  //    list interface {
  //      key name;
  //      description "Interface that connect this site to the VPN";
  //      leaf name {
  //        description "Interface name";
  //        type union {
  //          type jt:interface-name;
  //          type string {
  //            pattern "<.*>|$.*";
  //          }
  //        }
  //      }
  //      // uses apply-advanced;
  //      container mac-learning-priority {
  //        description "MAC learning priority for the interface";
  //        // uses apply-advanced;
  //        leaf priority {
  //          description "Mac learning priority for the interface";
  //          type union {
  //            type string {
  //              pattern "<.*>|$.*";
  //            }
  //            type uint32 {
  //              range "1 .. 65535";
  //            }
  //          }
  //        }
  //        leaf packet-action {
  //          default "discard";
  //          type enumeration {
  //            enum "discard" {
  //              description "Discard the packets and do not learn. Default is forward";
  //            }
  //            enum "forward" {
  //              description "Forward the packet";
  //            }
  //          }
  //        }
  //      }
  //      container interface-mac-limit {
  //        description "Maximum number of MAC addresses learned on the interface";
  //        // uses apply-advanced;
  //        leaf limit {
  //          description "Maximum number of MAC addresses per interface";
  //          type union {
  //            type string {
  //              pattern "<.*>|$.*";
  //            }
  //            type uint32;
  //          }
  //        }
  //        leaf disable {
  //          description "Disable interface for interface-mac-limit";
  //          type empty;
  //        }
  //        leaf packet-action {
  //          description "Action when MAC limit is reached";
  //          type enumeration {
  //            enum "none" {
  //              description "Forward the packet";
  //            }
  //            enum "drop" {
  //              description "Drop packets and do not learn. Default is forward";
  //            }
  //            enum "log" {
  //              description "Do not drop the packet but generate an alarm, an SNMP trap or a system log entry";
  //            }
  //            enum "shutdown" {
  //              description "Disable the interface and generate an alarm, an SNMP trap or a system log entry";
  //            }
  //            enum "drop-and-log" {
  //              description "Drop the packet and generate an alarm, an SNMP trap or a system log entry";
  //            }
  //          }
  //        }
  //      }
  //      leaf action-priority {
  //        description "Blocking priority of this interface on mac move detection";
  //        type union {
  //          type string {
  //            pattern "<.*>|$.*";
  //          }
  //          type uint32 {
  //            range "0 .. 8";
  //          }
  //        }
  //      }
  //      list static-mac {
  //        key name;
  //        ordered-by user;
  //        description "Static MAC addresses assigned to this interface";
  //        leaf name {
  //          description "MAC address";
  //          type jt:mac-addr;
  //        }
  //        // uses apply-advanced;
  //        list vlan-id {
  //          key name;
  //          ordered-by user;
  //          description "VLAN ID of learning VLAN";
  //          leaf name {
  //            description "Learning VLAN";
  //            type union {
  //              type string {
  //                pattern "<.*>|$.*";
  //              }
  //              type uint32 {
  //                range "0 .. 4094";
  //              }
  //            }
  //          }
  //          // uses apply-advanced;
  //        }
  //      }
  //      list static-mac-ip {
  //        key name;
  //        ordered-by user;
  //        description "Static MAC-IP address bindings";
  //        leaf name {
  //          description "IP address";
  //          type jt:ipaddr;
  //        }
  //        // uses apply-advanced;
  //        leaf-list mac-address {
  //          ordered-by user;
  //          description "MAC address";
  //          type jt:mac-unicast;
  //          max-elements 8;
  //        }
  //        leaf router {
  //          description "Router flag for ipv6 addresses";
  //          type empty;
  //        }
  //      }
  //      container interface-mac-ip-limit {
  //        description "Maximum number of MAC+IP bindings learned on the interface";
  //        // uses apply-advanced;
  //        leaf limit {
  //          description "Maximum number of MAC+IP bindings per interface";
  //          type union {
  //            type string {
  //              pattern "<.*>|$.*";
  //            }
  //            type uint32;
  //          }
  //        }
  //      }
  //      leaf no-mac-learning {
  //        description "Disable dynamic MAC address learning";
  //        type empty;
  //      }
  //      leaf mac-pinning {
  //        description "Enable MAC pinning";
  //        type empty;
  //      }
  //    }
  //    container traceoptions {
  //      description "Trace options for this bridge domain";
  //      // uses apply-advanced;
  //      leaf no-remote-trace {
  //        description "Disable remote tracing";
  //        type empty;
  //      }
  //      container file {
  //        description "Trace file information";
  //        leaf filename {
  //          description "Name of file in which to write trace information";
  //          type string {
  //            length "1 .. 1024";
  //          }
  //        }
  //        leaf size {
  //          description "Maximum trace file size";
  //          type string;
  //        }
  //        leaf files {
  //          description "Maximum number of trace files";
  //          default "3";
  //          type union {
  //            type string {
  //              pattern "<.*>|$.*";
  //            }
  //            type uint32 {
  //              range "2 .. 1000";
  //            }
  //          }
  //        }
  //        choice world-readable-choice {
  //          leaf world-readable {
  //            description "Allow any user to read the log file";
  //            type empty;
  //          }
  //          leaf no-world-readable {
  //            description "Don't allow any user to read the log file";
  //            type empty;
  //          }
  //        }
  //        leaf match {
  //          description "Regular expression for lines to be logged";
  //          type jt:regular-expression;
  //        }
  //      }
  //      leaf level {
  //        description "Level of debugging output";
  //        default "error";
  //        type enumeration {
  //          enum "error" {
  //            description "Match error conditions";
  //          }
  //          enum "warning" {
  //            description "Match warning messages";
  //          }
  //          enum "notice" {
  //            description "Match conditions that should be handled specially";
  //          }
  //          enum "info" {
  //            description "Match informational messages";
  //          }
  //          enum "verbose" {
  //            description "Match verbose messages";
  //          }
  //          enum "all" {
  //            description "Match all levels";
  //          }
  //        }
  //      }
  //      list flag {
  //        key name;
  //        ordered-by user;
  //        description "Type of operation or event to include in trace";
  //        leaf name {
  //          type enumeration {
  //            enum "configuration" {
  //              description "Configuration operations";
  //            }
  //            enum "routing-socket" {
  //              description "Routing socket operations";
  //            }
  //            enum "interface-device" {
  //              description "Interface device operations";
  //            }
  //            enum "interface-logical" {
  //              description "Logical interface operations";
  //            }
  //            enum "interface-family" {
  //              description "Interface family operations";
  //            }
  //            enum "learning-domain" {
  //              description "Learning domain operations";
  //            }
  //            enum "ipc" {
  //              description "Inter-process communications operations";
  //            }
  //            enum "mac-learning" {
  //              description "MAC address learning operations";
  //            }
  //            enum "initialization" {
  //              description "Initialization operations";
  //            }
  //            enum "flood-next-hop" {
  //              description "Flood next hop operations";
  //            }
  //            enum "storm-control" {
  //              description "Storm-control";
  //            }
  //            enum "unknown-unicast-forwarding" {
  //              description "Trace unknown unicast forwarding events";
  //            }
  //            enum "all" {
  //              description "All operations";
  //            }
  //          }
  //        }
  //      }
  //    }
  //  }
  //  grouping write-option-82-type {
  //    // uses apply-advanced;
  //  }
 }
