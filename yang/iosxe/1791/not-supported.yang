module Cisco-IOS-XE-skip {
  namespace "http://cisco.com/ns/yang/Cisco-IOS-XE-skip";
  prefix ios-skip;

  import cisco-semver {
    prefix cisco-semver;
  }
  import Cisco-IOS-XE-native {
    prefix ios;
  }
  import Cisco-IOS-XE-ntp {
    prefix ios-ntp;
  }
  import Cisco-IOS-XE-bgp {
    prefix ios-bgp;
  }
  import Cisco-IOS-XE-acl {
    prefix ios-acl;
  }
  import Cisco-IOS-XE-snmp {
    prefix ios-snmp;
  }
  import Cisco-IOS-XE-object-group {
    prefix ios-og;
  }
  import Cisco-IOS-XE-multicast {
    prefix ios-mc;
  }
  import Cisco-IOS-XE-nat {
    prefix ios-nat;
  }
  import Cisco-IOS-XE-igmp {
    prefix ios-igmp;
  }  

  organization
    "Bloomberg LP";

  revision 2025-06-06 {
    description
      "First not-supported list";
    cisco-semver:module-version "0.2.0";
  }

  //============================= Interfaces ==================================


  deviation "/ios:native/ios:interface/ios:AppGigabitEthernet" {
    deviate not-supported;
  }

  deviation "/ios:native/ios:interface/ios:AppNav-Compress" {
    deviate not-supported;
  }

  deviation "/ios:native/ios:interface/ios:AppNav-UnCompress" {
    deviate not-supported;
  }

  deviation "/ios:native/ios:interface/ios:ATM" {
    deviate not-supported;
  }

  deviation "/ios:native/ios:interface/ios:ATM-subinterface" {
    deviate not-supported;
  }

  deviation "/ios:native/ios:interface/ios:ATM-ACR" {
    deviate not-supported;
  }

  deviation "/ios:native/ios:interface/ios:ATM-ACRsubinterface" {
    deviate not-supported;
  }

  deviation "/ios:native/ios:interface/ios:Async" {
    deviate not-supported;
  }

  deviation "/ios:native/ios:interface/ios:BD-VIF" {
    deviate not-supported;
  }

  deviation "/ios:native/ios:interface/ios:BDI" {
    deviate not-supported;
  }

  deviation "/ios:native/ios:interface/ios:CEM" {
    deviate not-supported;
  }

  deviation "/ios:native/ios:interface/ios:CEM-ACR" {
    deviate not-supported;
  }

  deviation "/ios:native/ios:interface/ios:Cellular" {
    deviate not-supported;
  }

  deviation "/ios:native/ios:interface/ios:Dialer" {
    deviate not-supported;
  }  

  deviation "/ios:native/ios:interface/ios:Embedded-Service-Engine" {
    deviate not-supported;
  }

  deviation "/ios:native/ios:interface/ios:Ethernet" {
    deviate not-supported;
  }

  deviation "/ios:native/ios:interface/ios:Ethernet-Internal" {
    deviate not-supported;
  }

  deviation "/ios:native/ios:interface/ios:FastEthernet" {
    deviate not-supported;
  }

  deviation "/ios:native/ios:interface/ios:FiftyGigabitEthernet" {
    deviate not-supported;
  }

  deviation "/ios:native/ios:interface/ios:FiveGigabitEthernet" {
    deviate not-supported;
  }

  deviation "/ios:native/ios:interface/ios:FourHundredGigE" {
    deviate not-supported;
  }

  deviation "/ios:native/ios:interface/ios:FortyGigabitEthernet" {
    deviate not-supported;
  }

  deviation "/ios:native/ios:interface/ios:GMPLS" {
    deviate not-supported;
  }

  deviation "/ios:native/ios:interface/ios:Group-Async" {
    deviate not-supported;
  }

  deviation "/ios:native/ios:interface/ios:LISP" {
    deviate not-supported;
  }

  deviation "/ios:native/ios:interface/ios:LISP-subinterface" {
    deviate not-supported;
  }

  deviation "/ios:native/ios:interface/ios:L2LISP" {
    deviate not-supported;
  }

  deviation "/ios:native/ios:interface/ios:L2LISP-subinterface" {
    deviate not-supported;
  }

  deviation "/ios:native/ios:interface/ios:MFR" {
    deviate not-supported;
  }

  deviation "/ios:native/ios:interface/ios:MFR-subinterface" {
    deviate not-supported;
  }

  deviation "/ios:native/ios:interface/ios:Multilink" {
    deviate not-supported;
  }

  deviation "/ios:native/ios:interface/ios:nve" {
    deviate not-supported;
  }

  deviation "/ios:native/ios:interface/ios:overlay" {
    deviate not-supported;
  }

  deviation "/ios:native/ios:interface/ios:Port-channel" {
    deviate not-supported;
  }

  deviation "/ios:native/ios:interface/ios:Port-channel-subinterface" {
    deviate not-supported;
  }

  deviation "/ios:native/ios:interface/ios:pseudowire" {
    deviate not-supported;
  }

  deviation "/ios:native/ios:interface/ios:PRP-channel" {
    deviate not-supported;
  }

  deviation "/ios:native/ios:interface/ios:SM" {
    deviate not-supported;
  }

  deviation "/ios:native/ios:interface/ios:Serial" {
    deviate not-supported;
  }

  deviation "/ios:native/ios:interface/ios:Serial-subinterface" {
    deviate not-supported;
  }

  deviation "/ios:native/ios:interface/ios:Service-Engine" {
    deviate not-supported;
  }

  deviation "/ios:native/ios:interface/ios:Tunnel" {
    deviate not-supported;
  }  

  deviation "/ios:native/ios:interface/ios:TwentyFiveGigabitEthernet" {
    deviate not-supported;
  }

  deviation "/ios:native/ios:interface/ios:TwoGigabitEthernet" {
    deviate not-supported;
  }

  deviation "/ios:native/ios:interface/ios:TwoHundredGigE" {
    deviate not-supported;
  }
  
  deviation "/ios:native/ios:interface/ios:ucse" {
    deviate not-supported;
  }

  deviation "/ios:native/ios:interface/ios:vasileft" {
    deviate not-supported;
  }

  deviation "/ios:native/ios:interface/ios:vasiright" {
    deviate not-supported;
  }

  deviation "/ios:native/ios:interface/ios:Vif" {
    deviate not-supported;
  }

  deviation "/ios:native/ios:interface/ios:vmi" {
    deviate not-supported;
  }

  deviation "/ios:native/ios:interface/ios:Virtual-PPP" {
    deviate not-supported;
  }

  deviation "/ios:native/ios:interface/ios:VirtualPortGroup" {
    deviate not-supported;
  }

  deviation "/ios:native/ios:interface/ios:Virtual-Template" {
    deviate not-supported;
  }

  deviation "/ios:native/ios:interface/ios:Wlan-GigabitEthernet" {
    deviate not-supported;
  }

  deviation "/ios:native/ios:interface/ios:TwentyFiveGigE/ios:arp" {
    deviate not-supported;
  }

  deviation "/ios:native/ios:interface/ios:GigabitEthernet/ios:arp" {
    deviate not-supported;
  }

  deviation "/ios:native/ios:interface/ios:HundredGigE/ios:arp" {
    deviate not-supported;
  }

  deviation "/ios:native/ios:interface/ios:TenGigabitEthernet/ios:arp" {
    deviate not-supported;
  }

  deviation "/ios:native/ios:interface/ios:Vlan/ios:arp" {
    deviate not-supported;
  }

  deviation "/ios:native/ios:interface/ios:TwentyFiveGigE/ios:backup" {
    deviate not-supported;
  }

  deviation "/ios:native/ios:interface/ios:GigabitEthernet/ios:backup" {
    deviate not-supported;
  }

  deviation "/ios:native/ios:interface/ios:HundredGigE/ios:backup" {
    deviate not-supported;
  }

  deviation "/ios:native/ios:interface/ios:TenGigabitEthernet/ios:backup" {
    deviate not-supported;
  }

  deviation "/ios:native/ios:interface/ios:Vlan/ios:backup" {
    deviate not-supported;
  }

  deviation "/ios:native/ios:interface/ios:TwentyFiveGigE/ios:bandwidth" {
    deviate not-supported;
  }

  deviation "/ios:native/ios:interface/ios:GigabitEthernet/ios:bandwidth" {
    deviate not-supported;
  }

  deviation "/ios:native/ios:interface/ios:HundredGigE/ios:bandwidth" {
    deviate not-supported;
  }

  deviation "/ios:native/ios:interface/ios:TenGigabitEthernet/ios:bandwidth" {
    deviate not-supported;
  }

  deviation "/ios:native/ios:interface/ios:Vlan/ios:bandwidth" {
    deviate not-supported;
  }

  deviation "/ios:native/ios:interface/ios:TwentyFiveGigE/ios:l2protocol" {
    deviate not-supported;
  }

  deviation "/ios:native/ios:interface/ios:GigabitEthernet/ios:l2protocol" {
    deviate not-supported;
  }

  deviation "/ios:native/ios:interface/ios:HundredGigE/ios:l2protocol" {
    deviate not-supported;
  }

  deviation "/ios:native/ios:interface/ios:TenGigabitEthernet/ios:l2protocol" {
    deviate not-supported;
  }

  deviation "/ios:native/ios:interface/ios:Vlan/ios:l2protocol" {
    deviate not-supported;
  }

  deviation "/ios:native/ios:interface/ios:TwentyFiveGigE/ios:l2protocol-tunnel" {
    deviate not-supported;
  }

  deviation "/ios:native/ios:interface/ios:GigabitEthernet/ios:l2protocol-tunnel" {
    deviate not-supported;
  }

  deviation "/ios:native/ios:interface/ios:HundredGigE/ios:l2protocol-tunnel" {
    deviate not-supported;
  }

  deviation "/ios:native/ios:interface/ios:TenGigabitEthernet/ios:l2protocol-tunnel" {
    deviate not-supported;
  }

  deviation "/ios:native/ios:interface/ios:Vlan/ios:l2protocol-tunnel" {
    deviate not-supported;
  }

  deviation "/ios:native/ios:interface/ios:TwentyFiveGigE/ios:logging" {
    deviate not-supported;
  }

  deviation "/ios:native/ios:interface/ios:GigabitEthernet/ios:logging" {
    deviate not-supported;
  }

  deviation "/ios:native/ios:interface/ios:HundredGigE/ios:logging" {
    deviate not-supported;
  }

  deviation "/ios:native/ios:interface/ios:TenGigabitEthernet/ios:logging" {
    deviate not-supported;
  }

  deviation "/ios:native/ios:interface/ios:Vlan/ios:logging" {
    deviate not-supported;
  }

  deviation "/ios:native/ios:interface/ios:TwentyFiveGigE/ios:peer" {
    deviate not-supported;
  }

  deviation "/ios:native/ios:interface/ios:GigabitEthernet/ios:peer" {
    deviate not-supported;
  }

  deviation "/ios:native/ios:interface/ios:HundredGigE/ios:peer" {
    deviate not-supported;
  }

  deviation "/ios:native/ios:interface/ios:TenGigabitEthernet/ios:peer" {
    deviate not-supported;
  }

  deviation "/ios:native/ios:interface/ios:Vlan/ios:peer" {
    deviate not-supported;
  }

  deviation "/ios:native/ios:interface/ios:TwentyFiveGigE/ios:redundancy" {
    deviate not-supported;
  }

  deviation "/ios:native/ios:interface/ios:GigabitEthernet/ios:redundancy" {
    deviate not-supported;
  }

  deviation "/ios:native/ios:interface/ios:HundredGigE/ios:redundancy" {
    deviate not-supported;
  }

  deviation "/ios:native/ios:interface/ios:TenGigabitEthernet/ios:redundancy" {
    deviate not-supported;
  }

  deviation "/ios:native/ios:interface/ios:Vlan/ios:redundancy" {
    deviate not-supported;
  }

  deviation "/ios:native/ios:interface/ios:TwentyFiveGigE/ios:standby" {
    deviate not-supported;
  }

  deviation "/ios:native/ios:interface/ios:GigabitEthernet/ios:standby" {
    deviate not-supported;
  }

  deviation "/ios:native/ios:interface/ios:HundredGigE/ios:standby" {
    deviate not-supported;
  }

  deviation "/ios:native/ios:interface/ios:TenGigabitEthernet/ios:standby" {
    deviate not-supported;
  }

  deviation "/ios:native/ios:interface/ios:Vlan/ios:standby" {
    deviate not-supported;
  }

  deviation "/ios:native/ios:interface/ios:TwentyFiveGigE/ios:storm-control" {
    deviate not-supported;
  }

  deviation "/ios:native/ios:interface/ios:GigabitEthernet/ios:storm-control" {
    deviate not-supported;
  }

  deviation "/ios:native/ios:interface/ios:HundredGigE/ios:storm-control" {
    deviate not-supported;
  }

  deviation "/ios:native/ios:interface/ios:TenGigabitEthernet/ios:storm-control" {
    deviate not-supported;
  }

  deviation "/ios:native/ios:interface/ios:Vlan/ios:storm-control" {
    deviate not-supported;
  }

  deviation "/ios:native/ios:interface/ios:TwentyFiveGigE/ios:subscriber" {
    deviate not-supported;
  }

  deviation "/ios:native/ios:interface/ios:GigabitEthernet/ios:subscriber" {
    deviate not-supported;
  }

  deviation "/ios:native/ios:interface/ios:HundredGigE/ios:subscriber" {
    deviate not-supported;
  }

  deviation "/ios:native/ios:interface/ios:TenGigabitEthernet/ios:subscriber" {
    deviate not-supported;
  }

  deviation "/ios:native/ios:interface/ios:Vlan/ios:subscriber" {
    deviate not-supported;
  }

  deviation "/ios:native/ios:interface/ios:TwentyFiveGigE/ios:ip/ios:arp" {
    deviate not-supported;
  }

  deviation "/ios:native/ios:interface/ios:GigabitEthernet/ios:ip/ios:arp" {
    deviate not-supported;
  }

  deviation "/ios:native/ios:interface/ios:HundredGigE/ios:ip/ios:arp" {
    deviate not-supported;
  }

  deviation "/ios:native/ios:interface/ios:TenGigabitEthernet/ios:ip/ios:arp" {
    deviate not-supported;
  }

  deviation "/ios:native/ios:interface/ios:Vlan/ios:ip/ios:arp" {
    deviate not-supported;
  }

  deviation "/ios:native/ios:interface/ios:TwentyFiveGigE/ios:ip/ios:authentication" {
    deviate not-supported;
  }

  deviation "/ios:native/ios:interface/ios:GigabitEthernet/ios:ip/ios:authentication" {
    deviate not-supported;
  }

  deviation "/ios:native/ios:interface/ios:HundredGigE/ios:ip/ios:authentication" {
    deviate not-supported;
  }

  deviation "/ios:native/ios:interface/ios:TenGigabitEthernet/ios:ip/ios:authentication" {
    deviate not-supported;
  }

  deviation "/ios:native/ios:interface/ios:Vlan/ios:ip/ios:authentication" {
    deviate not-supported;
  }

  deviation "/ios:native/ios:interface/ios:TwentyFiveGigE/ios:ip/ios:rip" {
    deviate not-supported;
  }

  deviation "/ios:native/ios:interface/ios:GigabitEthernet/ios:ip/ios:rip" {
    deviate not-supported;
  }

  deviation "/ios:native/ios:interface/ios:HundredGigE/ios:ip/ios:rip" {
    deviate not-supported;
  }

  deviation "/ios:native/ios:interface/ios:TenGigabitEthernet/ios:ip/ios:rip" {
    deviate not-supported;
  }

  deviation "/ios:native/ios:interface/ios:Vlan/ios:ip/ios:rip" {
    deviate not-supported;
  }

  deviation "/ios:native/ios:interface/ios:TwentyFiveGigE/ios:ip/ios:verify" {
    deviate not-supported;
  }

  deviation "/ios:native/ios:interface/ios:GigabitEthernet/ios:ip/ios:verify" {
    deviate not-supported;
  }

  deviation "/ios:native/ios:interface/ios:HundredGigE/ios:ip/ios:verify" {
    deviate not-supported;
  }

  deviation "/ios:native/ios:interface/ios:TenGigabitEthernet/ios:ip/ios:verify" {
    deviate not-supported;
  }

  deviation "/ios:native/ios:interface/ios:Vlan/ios:ip/ios:verify" {
    deviate not-supported;
  }

  //============================= NTP ==================================
  deviation "/ios:native/ios:ntp/ios-ntp:access-group/ios-ntp:ipv6" {
    deviate not-supported;
  }

  deviation "/ios:native/ios:ntp/ios-ntp:source" {
    deviate not-supported;
  }

  deviation "/ios:native/ios:ntp/ios-ntp:peer" {
    deviate not-supported;
  }

  //============================= BGP ==================================
  deviation "/ios:native/ios:router/ios-bgp:bgp/ios-bgp:bmp" {
    deviate not-supported;
  }

  deviation "/ios:native/ios:router/ios-bgp:bgp/ios-bgp:bgp/ios-bgp:rpki" {
    deviate not-supported;
  }

  deviation "/ios:native/ios:router/ios-bgp:bgp/ios-bgp:template" {
    deviate not-supported;
  }

  deviation "/ios:native/ios:router/ios-bgp:bgp/ios-bgp:address-family/ios-bgp:with-vrf" {
    deviate not-supported;
  }

  deviation "/ios:native/ios:router/ios-bgp:bgp/ios-bgp:address-family/ios-bgp:no-vrf/ios-bgp:vpnv4" {
    deviate not-supported;
  }

  deviation "/ios:native/ios:router/ios-bgp:bgp/ios-bgp:address-family/ios-bgp:no-vrf/ios-bgp:nsap" {
    deviate not-supported;
  } 

  deviation "/ios:native/ios:router/ios-bgp:bgp/ios-bgp:address-family/ios-bgp:no-vrf/ios-bgp:link-state" {
    deviate not-supported;
  }

  deviation "/ios:native/ios:router/ios-bgp:bgp/ios-bgp:address-family/ios-bgp:no-vrf/ios-bgp:rtfilter" {
    deviate not-supported;
  }

  deviation "/ios:native/ios:router/ios-bgp:bgp/ios-bgp:address-family/ios-bgp:no-vrf/ios-bgp:l2vpn" {
    deviate not-supported;
  }

  deviation "/ios:native/ios:router/ios-bgp:bgp/ios-bgp:address-family/ios-bgp:no-vrf/ios-bgp:ipv6" {
    deviate not-supported;
  }

  deviation "/ios:native/ios:router/ios-bgp:bgp/ios-bgp:address-family/ios-bgp:no-vrf/ios-bgp:vpnv6" {
    deviate not-supported;
  }  

  //============================= NAT ==================================
  deviation "/ios:native/ios:nat64" {
    deviate not-supported;
  }

  deviation "/ios:native/ios:nat66" {
    deviate not-supported;
  }

  deviation "/ios:native/ios:ip/ios-nat:nat/ios-nat:inside/ios-nat:source/ios-nat:list-interface" {
    deviate not-supported;
  }

  deviation "/ios:native/ios:ip/ios-nat:nat/ios-nat:inside/ios-nat:source/ios-nat:list-pool" {
    deviate not-supported;
  }

  deviation "/ios:native/ios:ip/ios-nat:nat/ios-nat:inside/ios-nat:source/ios-nat:static/ios-nat:nat-static-transport-interface-list" {
    deviate not-supported;
  }

  deviation "/ios:native/ios:ip/ios-nat:nat/ios-nat:inside/ios-nat:source/ios-nat:static/ios-nat:nat-static-transport-list-port-fwd" {
    deviate not-supported;
  }

  deviation "/ios:native/ios:ip/ios-nat:nat/ios-nat:inside/ios-nat:source/ios-nat:static/ios-nat:nat-static-transport-list-with-vrf-port-fwd" {
    deviate not-supported;
  }

  deviation "/ios:native/ios:ip/ios-nat:nat/ios-nat:inside/ios-nat:source/ios-nat:static/ios-nat:nat-static-transport-list-with-vrf" {
    deviate not-supported;
  }  

  deviation "/ios:native/ios:ip/ios-nat:nat/ios-nat:inside/ios-nat:source/ios-nat:static/ios-nat:nat-static-proto-transport-interface-list" {
    deviate not-supported;
  }  

  deviation "/ios:native/ios:ip/ios-nat:nat/ios-nat:inside/ios-nat:source/ios-nat:static/ios-nat:nat-static-transport-list/ios-nat:egress-interface" {
    deviate not-supported;
  }  

  deviation "/ios:native/ios:ip/ios-nat:nat/ios-nat:log" {
    deviate not-supported;
  }  

  //============================= Object Group ==================================
  deviation "/ios:native/ios:object-group/ios-og:fqdn/ios-og:group-object" {
    deviate not-supported;
  }

  deviation "/ios:native/ios:object-group/ios-og:fqdn/ios-og:pattern" {
    deviate not-supported;
  }

  deviation "/ios:native/ios:object-group/ios-og:security" {
    deviate not-supported;
  }

  deviation "/ios:native/ios:object-group/ios-og:service/ios-og:group-objects" {
    deviate not-supported;
  }

  deviation "/ios:native/ios:object-group/ios-og:service/ios-og:icmp-conf" {
    deviate not-supported;
  }

  deviation "/ios:native/ios:object-group/ios-og:service/ios-og:tcp-conf" {
    deviate not-supported;
  }

  deviation "/ios:native/ios:object-group/ios-og:service/ios-og:udp-conf" {
    deviate not-supported;
  }

  deviation "/ios:native/ios:object-group/ios-og:service/ios-og:tcp-udp" {
    deviate not-supported;
  }

  deviation "/ios:native/ios:object-group/ios-og:geo/ios-og:continents" {
    deviate not-supported;
  }

  deviation "/ios:native/ios:object-group/ios-og:geo/ios-og:countries" {
    deviate not-supported;
  }

  deviation "/ios:native/ios:object-group/ios-og:geo/ios-og:group-object" {
    deviate not-supported;
  }

  deviation "/ios:native/ios:object-group/ios-og:network/ios-og:obj-Mode-config-network-group" {
    deviate not-supported;
  }

  deviation "/ios:native/ios:object-group/ios-og:v6-network" {
    deviate not-supported;
  }

  //============================= ACL ==================================
  deviation "/ios:native/ios:ipv6/ios:access-list" {
    deviate not-supported;
  }

  deviation "/ios:native/ios-acl:access-list/ios-acl:acl-limit" {
    deviate not-supported;
  }
  
  deviation "/ios:native/ios:ip/ios-acl:access-list/ios-acl:fqdn" {
    deviate not-supported;
  }

  deviation "/ios:native/ios:ip/ios-acl:access-list/ios-acl:role-based" {
    deviate not-supported;
  }

  deviation "/ios:native/ios:ip/ios-acl:access-list/ios-acl:helper" {
    deviate not-supported;
  }

  //============================= IPv6 ==================================
  deviation "/ios:native/ios:ipv6" {
    deviate not-supported;
  }

  deviation "/ios:native/ios:interface/ios:TwentyFiveGigE/ios:ipv6" {
    deviate not-supported;
  }

  deviation "/ios:native/ios:interface/ios:GigabitEthernet/ios:ipv6" {
    deviate not-supported;
  }

  deviation "/ios:native/ios:interface/ios:HundredGigE/ios:ipv6" {
    deviate not-supported;
  }

  deviation "/ios:native/ios:interface/ios:TenGigabitEthernet/ios:ipv6" {
    deviate not-supported;
  }

  deviation "/ios:native/ios:interface/ios:Vlan/ios:ipv6" {
    deviate not-supported;
  }

  //============================= MAC ==================================
  deviation "/ios:native/ios:mac" {
    deviate not-supported;
  } 

  //============================= Root ==================================
  deviation "/ios:native/ios:alarm-contact" {
    deviate not-supported;
  }

   deviation "/ios:native/ios:alias" {
    deviate not-supported;
  } 

  deviation "/ios:native/ios:archive" {
    deviate not-supported;
  }

  deviation "/ios:native/ios:aqm-register-fnf" {
    deviate not-supported;
  }

  deviation "/ios:native/ios:avb" {
    deviate not-supported;
  }

  deviation "/ios:native/ios:avc" {
    deviate not-supported;
  }

  deviation "/ios:native/ios:bfd-template" {
    deviate not-supported;
  }

  deviation "/ios:native/ios:bridge-domain" {
    deviate not-supported;
  }

  deviation "/ios:native/ios:call-home" {
    deviate not-supported;
  }

  deviation "/ios:native/ios:captive-portal-bypass" {
    deviate not-supported;
  }

  deviation "/ios:native/ios:card" {
    deviate not-supported;
  } 

   deviation "/ios:native/ios:cisp" {
    deviate not-supported;
  } 

  deviation "/ios:native/ios:clock" {
    deviate not-supported;
  }

  deviation "/ios:native/ios:control-plane" {
    deviate not-supported;
  }  

  deviation "/ios:native/ios:control-plane-host" {
    deviate not-supported;
  } 
  deviation "/ios:native/ios:controller" {
    deviate not-supported;
  } 

  deviation "/ios:native/ios:cts" {
    deviate not-supported;
  } 

  deviation "/ios:native/ios:device-tracking" {
    deviate not-supported;
  }     
  
  deviation "/ios:native/ios:domain" {
    deviate not-supported;
  } 

  deviation "/ios:native/ios:eap" {
    deviate not-supported;
  } 

  deviation "/ios:native/ios:disable-eadi" {
    deviate not-supported;
  } 

  deviation "/ios:native/ios:dot1x" {
    deviate not-supported;
  } 
  
  deviation "/ios:native/ios:endpoint-tracker" {
    deviate not-supported;
  } 
  
  deviation "/ios:native/ios:epm" {
    deviate not-supported;
  } 

  deviation "/ios:native/ios:event" {
    deviate not-supported;
  }  

  deviation "/ios:native/ios:errdisable" {
    deviate not-supported;
  } 

  deviation "/ios:native/ios:exception" {
    deviate not-supported;
  } 

  deviation "/ios:native/ios:fabric" {
    deviate not-supported;
  } 

  deviation "/ios:native/ios:facility-alarm" {
    deviate not-supported;
  }

  deviation "/ios:native/ios:fallback" {
    deviate not-supported;
  }

  deviation "/ios:native/ios:flow" {
    deviate not-supported;
  }

  deviation "/ios:native/ios:frame-relay" {
    deviate not-supported;
  }

  deviation "/ios:native/ios:global-address-family" {
    deviate not-supported;
  }

  deviation "/ios:native/ios:hw-module" {
    deviate not-supported;
  } 

  deviation "/ios:native/ios:identity" {
    deviate not-supported;
  } 

  deviation "/ios:native/ios:iox" {
    deviate not-supported;
  }

  deviation "/ios:native/ios:l2" {
    deviate not-supported;
  }

  deviation "/ios:native/ios:l2tp-class" {
    deviate not-supported;
  }

  deviation "/ios:native/ios:l2vpn" {
    deviate not-supported;
  }

  deviation "/ios:native/ios:l2vpn-config" {
    deviate not-supported;
  }

  deviation "/ios:native/ios:l3vpn" {
    deviate not-supported;
  }

  deviation "/ios:native/ios:lacp" {
    deviate not-supported;
  }

  deviation "/ios:native/ios:ldap" {
    deviate not-supported;
  }  

  deviation "/ios:native/ios:license" {
    deviate not-supported;
  } 

  deviation "/ios:native/ios:location" {
    deviate not-supported;
  } 

  deviation "/ios:native/ios:mab" {
    deviate not-supported;
  } 

  deviation "/ios:native/ios:mac-address-table" {
    deviate not-supported;
  } 

  deviation "/ios:native/ios:macro" {
    deviate not-supported;
  }

  deviation "/ios:native/ios:management" {
    deviate not-supported;
  }

  deviation "/ios:native/ios:md-list" {
    deviate not-supported;
  }

  deviation "/ios:native/ios:memory" {
    deviate not-supported;
  } 

  deviation "/ios:native/ios:memory-size" {
    deviate not-supported;
  } 

  deviation "/ios:native/ios:metadata" {
    deviate not-supported;
  }

  deviation "/ios:native/ios:mka" {
    deviate not-supported;
  }

  deviation "/ios:native/ios:mls" {
    deviate not-supported;
  }

  deviation "/ios:native/ios:module" {
    deviate not-supported;
  }

  deviation "/ios:native/ios:monitor" {
    deviate not-supported;
  } 

  deviation "/ios:native/ios:mpls" {
    deviate not-supported;
  } 

  deviation "/ios:native/ios:multilink" {
    deviate not-supported;
  }

  deviation "/ios:native/ios:mvrp" {
    deviate not-supported;
  } 

  deviation "/ios:native/ios:named-ordering-route-map" {
    deviate not-supported;
  } 

  deviation "/ios:native/ios:network-clock" {
    deviate not-supported;
  }

  deviation "/ios:native/ios:otv" {
    deviate not-supported;
  }

  deviation "/ios:native/ios:parameter-map" {
    deviate not-supported;
  }

  deviation "/ios:native/ios:parser" {
    deviate not-supported;
  } 

  deviation "/ios:native/ios:performance" {
    deviate not-supported;
  }

  deviation "/ios:native/ios:performance-measurement" {
    deviate not-supported;
  }

  deviation "/ios:native/ios:pfr" {
    deviate not-supported;
  } 

  deviation "/ios:native/ios:pfr-map" {
    deviate not-supported;
  }

  deviation "/ios:native/ios:platform" {
    deviate not-supported;
  }

  deviation "/ios:native/ios:policy" {
    deviate not-supported;
  }

  deviation "/ios:native/ios:port-channel" {
    deviate not-supported;
  }

  deviation "/ios:native/ios:ppp" {
    deviate not-supported;
  }

  deviation "/ios:native/ios:process" {
    deviate not-supported;
  }

  deviation "/ios:native/ios:profile" {
    deviate not-supported;
  }

  deviation "/ios:native/ios:pseudowire-class" {
    deviate not-supported;
  }

  deviation "/ios:native/ios:ptp" {
    deviate not-supported;
  }

  deviation "/ios:native/ios:radius" {
    deviate not-supported;
  }

  deviation "/ios:native/ios:radius-server" {
    deviate not-supported;
  }

  deviation "/ios:native/ios:redun-management" {
    deviate not-supported;
  }

  deviation "/ios:native/ios:redundancy" {
    deviate not-supported;
  }

  deviation "/ios:native/ios:remote-management" {
    deviate not-supported;
  }

  deviation "/ios:native/ios:sampler" {
    deviate not-supported;
  }

  deviation "/ios:native/ios:scada-gw" {
    deviate not-supported;
  }

  deviation "/ios:native/ios:scheduler" {
    deviate not-supported;
  }

  deviation "/ios:native/ios:sdm" {
    deviate not-supported;
  }

  deviation "/ios:native/ios:segment-routing" {
    deviate not-supported;
  }

  deviation "/ios:native/ios:service/ios:alignment" {
    deviate not-supported;
  }

  deviation "/ios:native/ios:service/ios:heartbeat" {
    deviate not-supported;
  }

  deviation "/ios:native/ios:service/ios:pad" {
    deviate not-supported;
  }

  deviation "/ios:native/ios:service/ios:timestamps/ios:debug" {
    deviate not-supported;
  }

  deviation "/ios:native/ios:service-chain" {
    deviate not-supported;
  }

  deviation "/ios:native/ios:service-insertion" {
    deviate not-supported;
  }

  deviation "/ios:native/ios:setup" {
    deviate not-supported;
  }

  deviation "/ios:native/ios:software" {
    deviate not-supported;
  }

  deviation "/ios:native/ios:stackwise-virtual" {
    deviate not-supported;
  }

  deviation "/ios:native/ios:standby" {
    deviate not-supported;
  }

  deviation "/ios:native/ios:subscriber" {
    deviate not-supported;
  }

  deviation "/ios:native/ios:system" {
    deviate not-supported;
  }

  deviation "/ios:native/ios:table-map" {
    deviate not-supported;
  }

  deviation "/ios:native/ios:tacacs" {
    deviate not-supported;
  }

  deviation "/ios:native/ios:tacacs-server" {
    deviate not-supported;
  }

  deviation "/ios:native/ios:template" {
    deviate not-supported;
  }

  deviation "/ios:native/ios:tftp-server" {
    deviate not-supported;
  }

  deviation "/ios:native/ios:tftp-server-config" {
    deviate not-supported;
  }

  deviation "/ios:native/ios:time-range" {
    deviate not-supported;
  }

  deviation "/ios:native/ios:tod-clock" {
    deviate not-supported;
  }

  deviation "/ios:native/ios:track" {
    deviate not-supported;
  }
 
  deviation "/ios:native/ios:transceiver" {
    deviate not-supported;
  } 

  deviation "/ios:native/ios:transport-map" {
    deviate not-supported;
  } 

  deviation "/ios:native/ios:udld" {
    deviate not-supported;
  }

  deviation "/ios:native/ios:upgrade" {
    deviate not-supported;
  }

  deviation "/ios:native/ios:user-name" {
    deviate not-supported;
  }

  deviation "/ios:native/ios:virtual-service" {
    deviate not-supported;
  }

  deviation "/ios:native/ios:vrf" {
    deviate not-supported;
  }

  deviation "/ios:native/ios:vtp" {
    deviate not-supported;
  }

  deviation "/ios:native/ios:vxlan" {
    deviate not-supported;
  }

  deviation "/ios:native/ios:wsma" {
    deviate not-supported;
  }

  deviation "/ios:native/ios:xconnect" {
    deviate not-supported;
  }

  deviation "/ios:native/ios:zone" {
    deviate not-supported;
  }

  deviation "/ios:native/ios:zone-pair" {
    deviate not-supported;
  }

  //============================= LINE ==================================
  deviation "/ios:native/ios:line/ios:aux" {
    deviate not-supported;
  } 

  deviation "/ios:native/ios:line/ios:line-list" {
    deviate not-supported;
  } 

  deviation "/ios:native/ios:line/ios:async-line" {
    deviate not-supported;
  } 

  deviation "/ios:native/ios:line/ios:async-line-single" {
    deviate not-supported;
  } 

  deviation "/ios:native/ios:line/ios:async-line-range" {
    deviate not-supported;
  } 

  //============================= Multicast ==================================
  deviation "/ios:native/ios:ip/ios-mc:mroute" {
    deviate not-supported;
  } 

  deviation "/ios:native/ios:ip/ios-mc:msdp" {
    deviate not-supported;
  }

  deviation "/ios:native/ios:ip/ios-mc:pim/ios-mc:mpls" {
    deviate not-supported;
  } 

  deviation "/ios:native/ios:ip/ios-mc:pim/ios-mc:bsr-candidate" {
    deviate not-supported;
  } 

  deviation "/ios:native/ios:ip/ios-mc:pim/ios-mc:register-source" {
    deviate not-supported;
  } 

  deviation "/ios:native/ios:ip/ios-mc:pim/ios-mc:send-rp-discovery" {
    deviate not-supported;
  } 
  
  deviation "/ios:native/ios:ip/ios-mc:pim/ios-mc:vrf" {
    deviate not-supported;
  }

  deviation "/ios:native/ios:ip/ios-igmp:igmp" {
    deviate not-supported;
  }

  deviation "/ios:native/ios:interface/ios:TwentyFiveGigE/ios:ip/ios-igmp:igmp/ios-igmp:mroute-proxy" {
    deviate not-supported;
  }

  deviation "/ios:native/ios:interface/ios:GigabitEthernet/ios:ip/ios-igmp:igmp/ios-igmp:mroute-proxy" {
    deviate not-supported;
  }

  deviation "/ios:native/ios:interface/ios:HundredGigE/ios:ip/ios-igmp:igmp/ios-igmp:mroute-proxy" {
    deviate not-supported;
  }

  deviation "/ios:native/ios:interface/ios:TenGigabitEthernet/ios:ip/ios-igmp:igmp/ios-igmp:mroute-proxy" {
    deviate not-supported;
  }

  deviation "/ios:native/ios:interface/ios:Vlan/ios:ip/ios-igmp:igmp/ios-igmp:mroute-proxy" {
    deviate not-supported;
  }

  deviation "/ios:native/ios:interface/ios:TwentyFiveGigE/ios:ip/ios-igmp:igmp/ios-igmp:helper-address" {
    deviate not-supported;
  }

  deviation "/ios:native/ios:interface/ios:GigabitEthernet/ios:ip/ios-igmp:igmp/ios-igmp:helper-address" {
    deviate not-supported;
  }

  deviation "/ios:native/ios:interface/ios:HundredGigE/ios:ip/ios-igmp:igmp/ios-igmp:helper-address" {
    deviate not-supported;
  }

  deviation "/ios:native/ios:interface/ios:TenGigabitEthernet/ios:ip/ios-igmp:igmp/ios-igmp:helper-address" {
    deviate not-supported;
  }

  deviation "/ios:native/ios:interface/ios:Vlan/ios:ip/ios-igmp:igmp/ios-igmp:helper-address" {
    deviate not-supported;
  }

  deviation "/ios:native/ios:interface/ios:TwentyFiveGigE/ios:ip/ios-igmp:igmp/ios-igmp:static-group" {
    deviate not-supported;
  }

  deviation "/ios:native/ios:interface/ios:GigabitEthernet/ios:ip/ios-igmp:igmp/ios-igmp:static-group" {
    deviate not-supported;
  }

  deviation "/ios:native/ios:interface/ios:HundredGigE/ios:ip/ios-igmp:igmp/ios-igmp:static-group" {
    deviate not-supported;
  }

  deviation "/ios:native/ios:interface/ios:TenGigabitEthernet/ios:ip/ios-igmp:igmp/ios-igmp:static-group" {
    deviate not-supported;
  }

  deviation "/ios:native/ios:interface/ios:Vlan/ios:ip/ios-igmp:igmp/ios-igmp:static-group" {
    deviate not-supported;
  }

  //============================= IP ==================================
  deviation "/ios:native/ios:ip/ios:domain/ios:lookup-settings" {
    deviate not-supported;
  }

  deviation "/ios:native/ios:ip/ios:domain-lookup/ios:source-interface" {
    deviate not-supported;
  }

  deviation "/ios:native/ios:ip/ios:explicit-path" {
    deviate not-supported;
  } 

  deviation "/ios:native/ios:ip/ios:forward-protocol" {
    deviate not-supported;
  }

  deviation "/ios:native/ios:ip/ios:sdwan" {
    deviate not-supported;
  }

  deviation "/ios:native/ios:ip/ios:arp" {
    deviate not-supported;
  }

  deviation "/ios:native/ios:ip/ios:prefix-list" {
    deviate not-supported;
  }

  deviation "/ios:native/ios:ip/ios:admission" {
    deviate not-supported;
  }

  deviation "/ios:native/ios:ip/ios:ftp" {
    deviate not-supported;
  }

  deviation "/ios:native/ios:ip/ios:tftp" {
    deviate not-supported;
  }

  deviation "/ios:native/ios:ip/ios:local" {
    deviate not-supported;
  }

  deviation "/ios:native/ios:ip/ios:ssh/ios:source-interface-config" {
    deviate not-supported;
  }

  //============================= RMON ==================================
  deviation "/ios:native/ios:rmon" {
    deviate not-supported;
  }

  //============================= SNMP ==================================
  deviation "/ios:native/ios:snmp" {
    deviate not-supported;
  }

  deviation "/ios:native/ios:snmp-server/ios-snmp:engineID" {
    deviate not-supported;
  }

  deviation "/ios:native/ios:snmp-server/ios-snmp:group" {
    deviate not-supported;
  }

  deviation "/ios:native/ios:snmp-server/ios-snmp:source-interface" {
    deviate not-supported;
  }

  deviation "/ios:native/ios:snmp-server/ios-snmp:user" {
    deviate not-supported;
  }

  deviation "/ios:native/ios:snmp-server/ios-snmp:trap" {
    deviate not-supported;
  }

  deviation "/ios:native/ios:snmp-server/ios-snmp:trap-source" {
    deviate not-supported;
  }

  //============================= ROUTE-MAP ==================================
  deviation "/ios:native/ios-route-map:route-map/ios-route-map:route-map-without-order-seq" {
    deviate not-supported;
  } 

  deviation "/ios:native/ios-route-map:route-map/ios-route-map:route-map-seq/ios-route-map:match/ios-route-map:additional-paths" {
    deviate not-supported;
  }

  deviation "/ios:native/ios-route-map:route-map/ios-route-map:route-map-seq/ios-route-map:match/ios-route-map:as-path" {
    deviate not-supported;
  }

  deviation "/ios:native/ios-route-map:route-map/ios-route-map:route-map-seq/ios-route-map:match/ios-route-map:community" {
    deviate not-supported;
  }

  deviation "/ios:native/ios-route-map:route-map/ios-route-map:route-map-seq/ios-route-map:match/ios-route-map:extcommunity" {
    deviate not-supported;
  }

  deviation "/ios:native/ios-route-map:route-map/ios-route-map:route-map-seq/ios-route-map:match/ios-route-map:ipv6" {
    deviate not-supported;
  }

  deviation "/ios:native/ios-route-map:route-map/ios-route-map:route-map-seq/ios-route-map:match/ios-route-map:rpki" {
    deviate not-supported;
  }

  deviation "/ios:native/ios-route-map:route-map/ios-route-map:route-map-seq/ios-route-map:match/ios-route-map:source-protocol" {
    deviate not-supported;
  }

  deviation "/ios:native/ios-route-map:route-map/ios-route-map:route-map-seq/ios-route-map:match/ios-route-map:route-type" {
    deviate not-supported;
  }

  deviation "/ios:native/ios-route-map:route-map/ios-route-map:route-map-seq/ios-route-map:set/ios-route-map:as-path" {
    deviate not-supported;
  } 

  deviation "/ios:native/ios-route-map:route-map/ios-route-map:route-map-seq/ios-route-map:set/ios-route-map:comm-list" {
    deviate not-supported;
  }

  deviation "/ios:native/ios-route-map:route-map/ios-route-map:route-map-seq/ios-route-map:set/ios-route-map:community" {
    deviate not-supported;
  }

  deviation "/ios:native/ios-route-map:route-map/ios-route-map:route-map-seq/ios-route-map:set/ios-route-map:extcomm-list" {
    deviate not-supported;
  }

  deviation "/ios:native/ios-route-map:route-map/ios-route-map:route-map-seq/ios-route-map:set/ios-route-map:extcommunity" {
    deviate not-supported;
  }

  deviation "/ios:native/ios-route-map:route-map/ios-route-map:route-map-seq/ios-route-map:set/ios-route-map:interface" {
    deviate not-supported;
  }

  deviation "/ios:native/ios-route-map:route-map/ios-route-map:route-map-seq/ios-route-map:set/ios-route-map:ipv6" {
    deviate not-supported;
  }

  deviation "/ios:native/ios-route-map:route-map/ios-route-map:route-map-seq/ios-route-map:set/ios-route-map:dampening" {
    deviate not-supported;
  }

  deviation "/ios:native/ios-route-map:route-map/ios-route-map:route-map-seq/ios-route-map:set/ios-route-map:default" {
    deviate not-supported;
  }
}
