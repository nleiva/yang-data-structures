/*
 * Copyright (c) 2024 Juniper Networks, Inc.
 * All rights reserved.
 */
 module junos-conf-interfaces {
   namespace "http://yang.juniper.net/junos/conf/interfaces";

   prefix jc-interfaces;

   import junos-common-types {
     prefix jt;
     revision-date 2023-01-01;
   }

   import junos-conf-root {
     prefix jc;
     revision-date 2023-01-01;
   }

   organization "Juniper Networks, Inc.";

   contact "yang-support@juniper.net";

   description "Junos interfaces configuration module";

   revision 2023-01-01 {
     description "Junos: 23.4R2.13";
   }

   augment /jc:configuration {
     uses interfaces-group;
   }
  //  augment /jc:configuration/jc:groups {
  //    uses interfaces-group;
  //  }
   grouping interfaces-group {
     container interfaces {
       description "Interface configuration";
       // uses apply-advanced;
       list interface-set {
         key name;
         description "Logical interface set configuration";
         leaf name {
           type string;
         }
         // uses apply-advanced;
        //  container load-balance {
        //    description "Load-balance weight per subscriber interface-set";
        //    // uses apply-advanced;
        //    leaf weight {
        //      description "Load-balance weight";
        //      type union {
        //        type string {
        //          pattern "<.*>|$.*";
        //        }
        //        type uint32 {
        //          range "1 .. 1000";
        //        }
        //      }
        //    }
        //  }
        //  leaf targeted-distribution {
        //    description "Interface participates in targeted-distribution";
        //    type empty;
        //  }
        //  container targeted-options {
        //    presence "enable targeted-options";
        //    description "Targeting specific options";
        //    // uses apply-advanced;
        //    leaf weight {
        //      description "Targeting weight for interface set";
        //      type string;
        //    }
        //  }
         list interface {
           key name;
           description "One or more interfaces that belong to interface set";
           leaf name {
             description "Interface name";
             type union {
               type jt:interface-device;
               type string {
                 pattern "<.*>|$.*";
               }
             }
           }
           // uses apply-advanced;
           list unit {
             key name;
             description "One or more logical interface unit numbers";
             leaf name {
               description "Unit number";
               type union {
                 type string {
                   pattern "<.*>|$.*";
                 }
                 type uint32 {
                   range "0 .. 1073741823";
                 }
               }
             }
             // uses apply-advanced;
           }
           list vlan-tags-outer {
             key name;
             description "One or more outer VLAN tags";
             leaf name {
               description "VLAN tag ID";
               type union {
                 type string {
                   pattern "<.*>|$.*";
                 }
                 type uint32 {
                   range "0 .. 4094";
                 }
               }
             }
             // uses apply-advanced;
           }
         }
        //  container pppoe-underlying-options {
        //    description "PPP over Ethernet underlying interface-specific options";
        //    uses pppoe_underlying_options_type;
        //  }
       }
      //  container stacked-interface-set {
      //    presence "enable stacked-interface-set";
      //    description "Stacked interface set configuration";
      //    // uses apply-advanced;
      //    list interface-set {
      //      key name;
      //      ordered-by user;
      //      description "Stacked parent interface set configuration";
      //      leaf name {
      //        type string;
      //      }
      //      // uses apply-advanced;
      //      list interface-set {
      //        key name;
      //        ordered-by user;
      //        description "Stacked child interface set configuration";
      //        leaf name {
      //          type string;
      //        }
      //        // uses apply-advanced;
      //      }
      //    }
      //  }
      //  container traceoptions {
      //    description "Interface trace options";
      //    // uses apply-advanced;
      //    leaf no-remote-trace {
      //      description "Disable remote tracing";
      //      type empty;
      //    }
      //    container file {
      //      description "Trace file information";
      //      leaf filename {
      //        description "Name of file in which to write trace information";
      //        type string {
      //          length "1 .. 1024";
      //        }
      //      }
      //      leaf size {
      //        description "Maximum trace file size";
      //        type string;
      //      }
      //      leaf files {
      //        description "Maximum number of trace files";
      //        default "3";
      //        type union {
      //          type string {
      //            pattern "<.*>|$.*";
      //          }
      //          type uint32 {
      //            range "2 .. 1000";
      //          }
      //        }
      //      }
      //      choice world-readable-choice {
      //        leaf world-readable {
      //          description "Allow any user to read the log file";
      //          type empty;
      //        }
      //        leaf no-world-readable {
      //          description "Don't allow any user to read the log file";
      //          type empty;
      //        }
      //      }
      //      leaf match {
      //        description "Regular expression for lines to be logged";
      //        type jt:regular-expression;
      //      }
      //    }
      //    list flag {
      //      key name;
      //      description "Tracing parameters";
      //      leaf name {
      //        type enumeration {
      //          enum "all" {
      //            description "Enable all configuration logging";
      //          }
      //          enum "kernel" {
      //            description "Log configuration IPC messages to kernel";
      //          }
      //          enum "change-events" {
      //            description "Log changes that produce configuration events";
      //          }
      //          enum "kernel-detail" {
      //            description "Log details of configuration messages to kernel";
      //          }
      //          enum "config-states" {
      //            description "Log the configuration state machine changes";
      //          }
      //          enum "resource-usage" {
      //            description "Log the resource usage for different states";
      //          }
      //          enum "gres-events" {
      //            description "Log the events related to GRES ";
      //          }
      //          enum "select-events" {
      //            description "Log the events on select state machine ";
      //          }
      //          enum "bfd-events" {
      //            description "Log BFD related events";
      //          }
      //          enum "lib-events" {
      //            description "Log DCD library related events";
      //          }
      //          enum "reserved" {
      //            description "Reserved DCD logs";
      //          }
      //          enum "emergency" {
      //            description "Log DCD emergency events";
      //          }
      //          enum "alert" {
      //            description "Log DCD alert events";
      //          }
      //          enum "critical" {
      //            description "Log DCD critical events";
      //          }
      //          enum "error" {
      //            description "Log DCD error events";
      //          }
      //          enum "warning" {
      //            description "Log DCD warning events";
      //          }
      //          enum "notice" {
      //            description "Log DCD notification events";
      //          }
      //          enum "informational" {
      //            description "Log DCD informations";
      //          }
      //          enum "debugging" {
      //            description "Log DCD debug events";
      //          }
      //          enum "verbose" {
      //            description "Log DCD debug all events";
      //          }
      //          enum "japi" {
      //            description "Log DCD JAPI events";
      //          }
      //        }
      //      }
      //      leaf disable {
      //        description "Disable this trace flag";
      //        type empty;
      //      }
      //    }
      //  }
       list interface-range {
         key name;
         ordered-by user;
         description "Interface ranges configuration";
         leaf name {
           description "Interface-range name";
           type string {
             length "1 .. 128";
           }
         }
         list member {
           key name;
           ordered-by user;
           description "Interfaces belonging to the interface range";
           leaf name {
             description "Member interface name";
             type union {
               type jt:interface-range-wild;
               type string {
                 pattern "<.*>|$.*";
               }
             }
           }
           // uses apply-advanced;
         }
         list member-range {
           key name;
           ordered-by user;
           description "Interfaces range in <start-range> to <end-range> format";
           leaf name {
             type union {
               type jt:interface-device;
               type string {
                 pattern "<.*>|$.*";
               }
             }
           }
           leaf end-range {
             type union {
               type jt:interface-device;
               type string {
                 pattern "<.*>|$.*";
               }
             }
           }
         }
         // uses apply-advanced;
         leaf description {
           description "Text description of interface";
           type string;
         }
        //  leaf external-model-name {
        //    description "Name for interface as configured using 3rd-party model";
        //    type string;
        //  }
        //  container management-ethernet-redundancy {
        //    presence "enable management-ethernet-redundancy";
        //    description "Management Interface Redundancy";
        //    // uses apply-advanced;
        //    choice enable_choice {
        //      case case_1 {
        //        leaf redundancy-enable {
        //          description "Enable Managment Ethernet Redundancy";
        //          type empty;
        //        }
        //      }
        //      case case_2 {
        //        leaf redundancy-disable {
        //          description "Disable  Managment Ethernet Redundancy";
        //          type empty;
        //        }
        //      }
        //    }
        //    leaf connectivity-test-interval {
        //      description "Connectivity test interval";
        //      default "5";
        //      units "seconds";
        //      type union {
        //        type string {
        //          pattern "<.*>|$.*";
        //        }
        //        type uint32 {
        //          range "1 .. 10";
        //        }
        //      }
        //    }
        //    leaf connectivity-test-response-interval {
        //      description "Connectivity test response wait time";
        //      default "5";
        //      units "seconds";
        //      type union {
        //        type string {
        //          pattern "<.*>|$.*";
        //        }
        //        type uint32 {
        //          range "1 .. 10";
        //        }
        //      }
        //    }
        //    leaf remote-ipv4-address {
        //      description "Destination IPV4 address to reach remote ";
        //      default "nil";
        //      type jt:ipv4addr;
        //    }
        //    leaf remote-ipv6-address {
        //      description "Destination IPV6 address to reach remote";
        //      default "nil";
        //      type jt:ipv6addr;
        //    }
        //    leaf number-of-connectivity-retries {
        //      description "Number of Connectivity retries ";
        //      default "2";
        //      type union {
        //        type string {
        //          pattern "<.*>|$.*";
        //        }
        //        type uint32 {
        //          range "1 .. 8";
        //        }
        //      }
        //    }
        //  }
        //  choice enable-disable {
        //    case case_1 {
        //      leaf disable {
        //        description "Disable this interface";
        //        type empty;
        //      }
        //    }
        //  }
        //  leaf promiscuous-mode {
        //    description "Enable promiscuous mode for L3 interface";
        //    type empty;
        //  }
        //  leaf multicast-statistics {
        //    description "Enable multicast statistics";
        //    type empty;
        //  }
        //  leaf oam-on-svlan {
        //    description "Propagate SVLAN OAM state to CVLANs";
        //    type empty;
        //  }
        //  container fabric-options {
        //    description "Fabric interface specific options";
        //    // uses apply-advanced;
        //    list member-interfaces {
        //      key name;
        //      description "Member interface for the fabric interface";
        //      leaf name {
        //        description "Interface name of member";
        //        type union {
        //          type jt:interface-device;
        //          type string {
        //            pattern "<.*>|$.*";
        //          }
        //        }
        //      }
        //      // uses apply-advanced;
        //    }
        //    container remote-chassis {
        //      presence "enable remote-chassis";
        //      description "Remote chassis reachability";
        //      // uses apply-advanced;
        //      leaf destination {
        //        description "Destination IP address to reach remote chassis";
        //        type jt:ipv4addr;
        //      }
        //    }
        //  }
        //  container traceoptions {
        //    presence "enable traceoptions";
        //    description "Interface trace options";
        //    // uses apply-advanced;
        //    list flag {
        //      key name;
        //      ordered-by user;
        //      description "Tracing parameters";
        //      leaf name {
        //        type enumeration {
        //          enum "ipc" {
        //            description "Trace interface IPC messages";
        //          }
        //          enum "event" {
        //            description "Trace interface events";
        //          }
        //          enum "media" {
        //            description "Trace interface media changes";
        //          }
        //          enum "all" {
        //            description "Enable all interface trace flags";
        //          }
        //        }
        //      }
        //    }
        //  }
        //  leaf passive-monitor-mode {
        //    description "Use interface to tap packets from another router";
        //    type empty;
        //  }
        //  choice keepalive_choices {
        //    case case_1 {
        //      container keepalives {
        //        description "Send or demand keepalive messages";
        //        presence "enable keepalives";
        //        uses keepalives_type;
        //      }
        //    }
        //    case case_2 {
        //      leaf no-keepalives {
        //        description "Do not send keepalive messages";
        //        type empty;
        //      }
        //    }
        //  }
        //  choice traps-choice {
        //    leaf traps {
        //      description "Enable SNMP notifications on state changes";
        //      type empty;
        //    }
        //    leaf no-traps {
        //      description "Don't enable SNMP notifications on state changes";
        //      type empty;
        //    }
        //  }
         choice interface-mib-choice {
           leaf interface-mib {
             description "Enable interface-related MIBs";
             type empty;
           }
           leaf no-interface-mib {
             description "Don't enable interface-related MIBs";
             type empty;
           }
         }
        //  leaf accounting-profile {
        //    description "Accounting profile name";
        //    type string;
        //  }
        //  container anchor-point {
        //    description "Anchor point";
        //    // uses apply-advanced;
        //    leaf interface-name {
        //      description "Interface name";
        //      type union {
        //        type jt:interface-device;
        //        type string {
        //          pattern "<.*>|$.*";
        //        }
        //      }
        //    }
        //  }
        //  container targeted-options {
        //    description "Targeting specific options for PS/RLT active-active mode";
        //    // uses apply-advanced;
        //    leaf type {
        //      description "Targeting type of PS";
        //      type enumeration {
        //        enum "manual" {
        //          description "Targeting type is Manual";
        //        }
        //      }
        //    }
        //    choice redundancy_choice {
        //      case case_1 {
        //        leaf logical-interface-fpc-redundancy {
        //          description "Enable FPC redundancy for logical interfaces";
        //          type empty;
        //        }
        //      }
        //      case case_2 {
        //        leaf logical-interface-chassis-redundancy {
        //          description "Enable CHASSIS redundancy for logical interfaces";
        //          type empty;
        //        }
        //      }
        //    }
        //    container rebalance-periodic {
        //      presence "enable rebalance-periodic";
        //      // uses apply-advanced;
        //      leaf start-time {
        //        description "Start time of the rebalance operation ( Wall clock time )";
        //        type jt:time-of-day;
        //      }
        //      leaf interval {
        //        description "Interval of the rebalance operation in hrs";
        //        type union {
        //          type string {
        //            pattern "<.*>|$.*";
        //          }
        //          type uint32 {
        //            range "1 .. 24";
        //          }
        //        }
        //      }
        //    }
        //    leaf rebalance-subscriber-granularity {
        //      description "Max subscriber aggregate weight";
        //      type union {
        //        type string {
        //          pattern "<.*>|$.*";
        //        }
        //        type uint32 {
        //          range "1 .. 65535";
        //        }
        //      }
        //    }
        //  }
        //  choice bypass-queueing-chip-choice {
        //    leaf bypass-queueing-chip {
        //      description "Enable to bypass queueing chip";
        //      type empty;
        //    }
        //    leaf no-bypass-queueing-chip {
        //      description "Don't enable to bypass queueing chip";
        //      type empty;
        //    }
        //  }
        //  choice scheduler_type {
        //    case case_1 {
        //      choice per-unit-scheduler-choice {
        //        leaf per-unit-scheduler {
        //          description "Enable subunit queuing on Frame Relay or VLAN IQ interface";
        //          type empty;
        //        }
        //        leaf no-per-unit-scheduler {
        //          description "Don't enable subunit queuing on Frame Relay or VLAN IQ interface";
        //          type empty;
        //        }
        //      }
        //    }
        //    case case_2 {
        //      leaf shared-scheduler {
        //        description "Enabled shared queuing on an IQ2 interface";
        //        type empty;
        //      }
        //    }
        //    case case_3 {
        //      container hierarchical-scheduler {
        //        presence "enable hierarchical-scheduler";
        //        description "Enable hierarchical scheduling";
        //        leaf maximum-hierarchy-levels {
        //          description "Maximum hierarchy levels";
        //          type union {
        //            type string {
        //              pattern "<.*>|$.*";
        //            }
        //            type uint32;
        //          }
        //        }
        //        leaf maximum-l2-nodes {
        //          description "Maximum l2 nodes, allowed numbers are power of 2 between 1 and 16k (needs FPC reboot)";
        //          default "1";
        //          type union {
        //            type string {
        //              pattern "<.*>|$.*";
        //            }
        //            type uint32 {
        //              range "1 .. 16384";
        //            }
        //          }
        //        }
        //        leaf maximum-l3-nodes {
        //          description "Maximum l3 nodes, allowed numbers are power of 2 between 2 and 32k (needs FPC reboot)";
        //          default "16384";
        //          type union {
        //            type string {
        //              pattern "<.*>|$.*";
        //            }
        //            type uint32 {
        //              range "2 .. 32768";
        //            }
        //          }
        //        }
        //        leaf implicit-hierarchy {
        //          description "Implicit hierarchy (follows interface hierarchy)";
        //          type empty;
        //        }
        //      }
        //    }
        //  }
        //  leaf l2tp-maximum-session {
        //    description "Maximum L2TP session";
        //    type union {
        //      type string {
        //        pattern "<.*>|$.*";
        //      }
        //      type uint32 {
        //        range "0 .. 64000";
        //      }
        //    }
        //  }
        //  leaf schedulers {
        //    description "Number of schedulers to allocate for interface";
        //    type union {
        //      type uint32;
        //      type string {
        //        pattern "<.*>|$.*";
        //      }
        //    }
        //  }
        //  leaf interface-transmit-statistics {
        //    description "Interface statistics based on the transmitted packets";
        //    type empty;
        //  }
        //  leaf cascade-port {
        //    description "Cascade port";
        //    type empty;
        //  }
        //  leaf dce {
        //    description "Respond to Frame Relay status enquiry messages";
        //    type empty;
        //  }
        //  choice vlan_tag_mode {
        //    case case_1 {
        //      leaf vlan-tagging {
        //        description "802.1q VLAN tagging support";
        //        type empty;
        //      }
        //    }
        //    case case_2 {
        //      leaf stacked-vlan-tagging {
        //        description "Stacked 802.1q VLAN tagging support";
        //        type empty;
        //      }
        //    }
        //    case case_3 {
        //      leaf flexible-vlan-tagging {
        //        description "Support for no tagging, or single and double 802.1q VLAN tagging";
        //        type empty;
        //      }
        //    }
        //    case case_4 {
        //      leaf vlan-vci-tagging {
        //        description "CCC for VLAN Q-in-Q and ATM VPI/VCI interworking";
        //        type empty;
        //      }
        //    }
        //  }
        //  leaf native-vlan-id {
        //    description "Virtual LAN identifier for untagged frames";
        //    type union {
        //      type string {
        //        pattern "<.*>|$.*";
        //      }
        //      type uint32 {
        //        range "0 .. 4094";
        //      }
        //    }
        //  }
        //  leaf no-native-vlan-insert {
        //    description "Disable native-vlan-id insertion to untagged frames";
        //    type empty;
        //  }
        //  leaf vlan-offload {
        //    description "Offload VLAN filtering to NIC HW";
        //    type empty;
        //  }
        //  leaf input-native-vlan-push {
        //    description "Control native-vlan-id insertion to untagged frames when input-vlan-map push is configured";
        //    type enumeration {
        //      enum "disable" {
        //        description "Disable input-native-vlan-push";
        //      }
        //      enum "enable" {
        //        description "Enable input-native-vlan-push";
        //      }
        //    }
        //  }
        //  leaf no-pseudowire-down-on-core-isolation {
        //    description "Do not bring the pseudowire down in the event of EVPN Core isolation";
        //    type empty;
        //  }
         leaf number-of-sub-ports {
           description "Number of channels to create for a port";
           type union {
             type string {
               pattern "<.*>|$.*";
             }
             type uint32 {
               range "1 .. 8";
             }
           }
         }
         leaf unused {
           description "Disable physical port";
           type empty;
         }
         leaf speed {
           description "Link speed";
           type enumeration {
             enum "auto" {
               description "Enable auto negotiation of interface speed";
             }
             enum "auto-10m-100m" {
               description "Enable auto negotiation of limiting interface speed to 10m/100m";
             }
             enum "10m" {
             }
             enum "100m" {
             }
             enum "1g" {
             }
             enum "2.5g" {
             }
             enum "5g" {
             }
             enum "10g" {
             }
             enum "25g" {
             }
             enum "40g" {
             }
             enum "50g" {
             }
             enum "100g" {
             }
             enum "200g" {
             }
             enum "400g" {
             }
             enum "800g" {
             }
             enum "oc3" {
             }
             enum "oc12" {
             }
             enum "oc48" {
             }
           }
         }
        //  container forwarding-class-accounting {
        //    presence "enable forwarding-class-accounting";
        //    description "Configure Forwarding-class-accounting parameters";
        //    // uses apply-advanced;
        //    leaf direction {
        //      description "Direction of the traffic to be accounted for IFD";
        //      type enumeration {
        //        enum "ingress" {
        //          description "Enable forwarding-class-accounting for ingress traffic";
        //        }
        //        enum "egress" {
        //          description "Enable forwarding-class-accounting for egress traffic";
        //        }
        //        enum "both" {
        //          description "Enable forwarding-class-accounting for both directions";
        //        }
        //      }
        //    }
        //    container enhanced {
        //      presence "enable enhanced";
        //      // uses apply-advanced;
        //      leaf traffic-type {
        //        description "Traffic-type to be accounted for forwarding-class-accounting";
        //        type enumeration {
        //          enum "unicast-statistics" {
        //            description "Count only unicast traffic for forwarding-class-accounting";
        //          }
        //          enum "multicast-statistics" {
        //            description "Count only multicast traffic for forwarding-class-accounting";
        //          }
        //        }
        //      }
        //      leaf family {
        //        description "Protocol traffic to be accounted for forwarding-class-accounting";
        //        type enumeration {
        //          enum "inet" {
        //            description "Enable forwarding-class-accounting for IPv4 family only";
        //          }
        //          enum "inet6" {
        //            description "Enable forwarding-class-accounting for IPv6 family only";
        //          }
        //          enum "both" {
        //            description "Enable forwarding-class-accounting for both IPv4 and IPv6 family only";
        //          }
        //        }
        //      }
        //      leaf direction {
        //        description "Direction of the traffic to be accounted for forwarding-class-accounting";
        //        type enumeration {
        //          enum "ingress" {
        //            description "Enable forwarding-class-accounting for ingress traffic";
        //          }
        //          enum "egress" {
        //            description "Enable forwarding-class-accounting for egress traffic";
        //          }
        //          enum "both" {
        //            description "Enable forwarding-class-accounting for both ingress and egress traffic";
        //          }
        //        }
        //      }
        //      leaf overhead-bytes {
        //        description "Per octet overhead bytes to be accounted for forwarding-class-accounting";
        //        default "0";
        //        type union {
        //          type string {
        //            pattern "<.*>|$.*";
        //          }
        //          type uint32 {
        //            range "0 .. 255";
        //          }
        //        }
        //      }
        //    }
        //  }
        //  container auto-configure {
        //    description "Auto configuration";
        //    uses auto_configure_vlan_type;
        //  }
         leaf mtu {
           description "Maximum transmit packet size";
           type union {
             type string {
               pattern "<.*>|$.*";
             }
             type uint32;
           }
         }
         container hold-time {
           description "Hold time for link up and link down";
           leaf up {
             description "Link up hold time";
             units "milliseconds";
             type union {
               type uint32;
               type string {
                 pattern "<.*>|$.*";
               }
             }
           }
           leaf down {
             description "Link down hold time";
             units "milliseconds";
             type union {
               type uint32;
               type string {
                 pattern "<.*>|$.*";
               }
             }
           }
         }
         container damping {
           description "Interface damping parameters";
           // uses apply-advanced;
           leaf half-life {
             description "Damping half life time";
             default "5";
             units "seconds";
             type union {
               type string {
                 pattern "<.*>|$.*";
               }
               type uint32 {
                 range "1 .. 30";
               }
             }
           }
           leaf max-suppress {
             description "Maximum suppress time";
             default "20";
             units "seconds";
             type union {
               type string {
                 pattern "<.*>|$.*";
               }
               type uint32 {
                 range "1 .. 20000";
               }
             }
           }
           leaf reuse {
             description "Reuse threshold";
             default "1000";
             type union {
               type string {
                 pattern "<.*>|$.*";
               }
               type uint32 {
                 range "1 .. 20000";
               }
             }
           }
           leaf suppress {
             description "Suppress threshold";
             default "2000";
             type union {
               type string {
                 pattern "<.*>|$.*";
               }
               type uint32 {
                 range "1 .. 20000";
               }
             }
           }
           leaf enable {
             description "Enable interface damping";
             type empty;
           }
         }
        //  container link-degrade-monitor {
        //    presence "enable link-degrade-monitor";
        //    description "Enable link degrade monitoring";
        //    // uses apply-advanced;
        //    choice enable_choice {
        //      case case_1 {
        //        leaf link-degrade-monitor-enable {
        //          description "Enable Link Degrade Monitoring";
        //          type empty;
        //        }
        //      }
        //      case case_2 {
        //        leaf no-link-degrade-monitor-enable {
        //          description "Disable Link Degrade Monitoring";
        //          type empty;
        //        }
        //      }
        //    }
        //    container actions {
        //      description "Action upon link degrade event";
        //      // uses apply-advanced;
        //      choice action_choice {
        //        case case_1 {
        //          leaf media-based {
        //            description "Media based";
        //            type empty;
        //          }
        //        }
        //      }
        //    }
        //    container recovery {
        //      description "Link degrade recovery mechanism";
        //      // uses apply-advanced;
        //      leaf timer {
        //        description "Auto recovery timer in seconds";
        //        default "1800";
        //        type union {
        //          type uint32;
        //          type string {
        //            pattern "<.*>|$.*";
        //          }
        //        }
        //      }
        //      choice receovery_choice {
        //        case case_1 {
        //          leaf auto {
        //            description "Automatic recovery";
        //            type empty;
        //          }
        //        }
        //        case case_2 {
        //          leaf manual {
        //            description "Manual recovery";
        //            type empty;
        //          }
        //        }
        //      }
        //    }
        //    container thresholds {
        //      description "Link degrade threshold parameters";
        //      // uses apply-advanced;
        //      leaf set {
        //        description "BER at which link considered degraded(1..16)";
        //        default "1e-7";
        //        type string {
        //        }
        //      }
        //      leaf clear {
        //        description "BER at which link considered improved(1..16)";
        //        default "1e-12";
        //        type string {
        //        }
        //      }
        //      leaf warning-set {
        //        description "BER at which link degrade warning raised(1..16)";
        //        default "1e-9";
        //        type string {
        //        }
        //      }
        //      leaf warning-clear {
        //        description "BER at which link degrade warning cleared(1..16)";
        //        default "1e-11";
        //        type string {
        //        }
        //      }
        //      leaf interval {
        //        description "Consecutive link degrade events";
        //        default "10";
        //        type union {
        //          type string {
        //            pattern "<.*>|$.*";
        //          }
        //          type uint32 {
        //            range "1 .. 256";
        //          }
        //        }
        //      }
        //    }
        //  }
        //  container satop-options {
        //    description "Structure-Agnostic TDM over Packet protocol options";
        //    // uses apply-advanced;
        //    leaf idle-pattern {
        //      description "An 8-bit hexadecimal pattern to replace TDM data in a lost packet";
        //      type union {
        //        type string {
        //          pattern "<.*>|$.*";
        //        }
        //        type uint32 {
        //          range "0 .. 255";
        //        }
        //      }
        //    }
        //    leaf payload-size {
        //      description "Number of payload bytes per packet";
        //      type union {
        //        type string {
        //          pattern "<.*>|$.*";
        //        }
        //        type uint32 {
        //          range "64 .. 1024";
        //        }
        //      }
        //    }
        //    container excessive-packet-loss-rate {
        //      description "Packet loss options";
        //      // uses apply-advanced;
        //      leaf threshold {
        //        description "Percentile designating the threshold of excessive packet loss rate";
        //        type union {
        //          type string {
        //            pattern "<.*>|$.*";
        //          }
        //          type uint8 {
        //            range "1 .. 100";
        //          }
        //        }
        //      }
        //      leaf sample-period {
        //        description "Number of milliseconds over which excessive packet loss rate is calculated";
        //        type union {
        //          type string {
        //            pattern "<.*>|$.*";
        //          }
        //          type uint32 {
        //            range "1000 .. 65535";
        //          }
        //        }
        //      }
        //    }
        //    choice jitter-buffer-size {
        //      case case_1 {
        //        leaf jitter-buffer-packets {
        //          description "Number of packets in jitter buffer before packet data is played out in the line";
        //          type union {
        //            type string {
        //              pattern "<.*>|$.*";
        //            }
        //            type uint32 {
        //              range "1 .. 64";
        //            }
        //          }
        //        }
        //      }
        //      case case_2 {
        //        leaf jitter-buffer-latency {
        //          description "Number of milliseconds delay in jitter buffer before packet data is played out in the line";
        //          units "milliseconds";
        //          type union {
        //            type string {
        //              pattern "<.*>|$.*";
        //            }
        //            type uint32 {
        //              range "1 .. 1000";
        //            }
        //          }
        //        }
        //      }
        //      case case_3 {
        //        leaf jitter-buffer-auto-adjust {
        //          description "Automatically adjust jitter buffer";
        //          type empty;
        //        }
        //      }
        //    }
        //    leaf bit-rate {
        //      description "In multiples of DS0";
        //      type union {
        //        type string {
        //          pattern "<.*>|$.*";
        //        }
        //        type uint32 {
        //          range "1 .. 10240";
        //        }
        //      }
        //    }
        //  }
        //  container cesopsn-options {
        //    description "Structure-Aware TDM over Packet protocol options";
        //    // uses apply-advanced;
        //    leaf idle-pattern {
        //      description "An 8-bit hexadecimal pattern to replace TDM data in a lost packet";
        //      type union {
        //        type string {
        //          pattern "<.*>|$.*";
        //        }
        //        type uint32 {
        //          range "0 .. 255";
        //        }
        //      }
        //    }
        //    leaf packetization-latency {
        //      description "Number of microseconds to create packets";
        //      units "microseconds";
        //      type union {
        //        type string {
        //          pattern "<.*>|$.*";
        //        }
        //        type uint32 {
        //          range "1000 .. 8000";
        //        }
        //      }
        //    }
        //    leaf payload-size {
        //      description "Number of payload bytes per packet";
        //      type union {
        //        type string {
        //          pattern "<.*>|$.*";
        //        }
        //        type uint32 {
        //          range "64 .. 1024";
        //        }
        //      }
        //    }
        //    container excessive-packet-loss-rate {
        //      description "Packet loss options";
        //      // uses apply-advanced;
        //      leaf threshold {
        //        description "Percentile designating the threshold of excessive packet loss rate";
        //        type union {
        //          type string {
        //            pattern "<.*>|$.*";
        //          }
        //          type uint8 {
        //            range "1 .. 100";
        //          }
        //        }
        //      }
        //      leaf sample-period {
        //        description "Number of milliseconds over which excessive packet loss rate is calculated";
        //        type union {
        //          type string {
        //            pattern "<.*>|$.*";
        //          }
        //          type uint32 {
        //            range "1000 .. 65535";
        //          }
        //        }
        //      }
        //    }
        //    choice jitter-buffer-size {
        //      case case_1 {
        //        leaf jitter-buffer-packets {
        //          description "Number of packets in jitter buffer before packet data is played out in the line";
        //          type union {
        //            type string {
        //              pattern "<.*>|$.*";
        //            }
        //            type uint32 {
        //              range "1 .. 64";
        //            }
        //          }
        //        }
        //      }
        //      case case_2 {
        //        leaf jitter-buffer-latency {
        //          description "Number of milliseconds delay in jitter buffer before packet data is played out in the line";
        //          units "milliseconds";
        //          type union {
        //            type string {
        //              pattern "<.*>|$.*";
        //            }
        //            type uint32 {
        //              range "1 .. 1000";
        //            }
        //          }
        //        }
        //      }
        //      case case_3 {
        //        leaf jitter-buffer-auto-adjust {
        //          description "Automatically adjust jitter buffer";
        //          type empty;
        //        }
        //      }
        //    }
        //    leaf bit-rate {
        //      description "In multiples of DS0";
        //      type union {
        //        type string {
        //          pattern "<.*>|$.*";
        //        }
        //        type uint32 {
        //          range "1 .. 10240";
        //        }
        //      }
        //    }
        //  }
        //  container ima-group-options {
        //    description "IMA group options";
        //    // uses apply-advanced;
        //    leaf frame-length {
        //      description "Frame length (cells)";
        //      type enumeration {
        //        enum "32" {
        //        }
        //        enum "64" {
        //        }
        //        enum "128" {
        //        }
        //        enum "256" {
        //        }
        //      }
        //    }
        //    leaf symmetry {
        //      description "Symmetry of IMA group";
        //      default "symmetrical-config-and-operation";
        //      type enumeration {
        //        enum "symmetrical-config-and-operation" {
        //        }
        //        enum "symmetrical-config-asymmetrical-operation" {
        //        }
        //      }
        //    }
        //    leaf transmit-clock {
        //      description "Transmit clock";
        //      type enumeration {
        //        enum "common" {
        //          description "Common transmit clock";
        //        }
        //        enum "independent" {
        //          description "Independent transmit clock";
        //        }
        //      }
        //    }
        //    leaf version {
        //      description "IMA specification version";
        //      type enumeration {
        //        enum "1.0" {
        //          description "Version 1.0";
        //        }
        //        enum "1.1" {
        //          description "Version 1.1";
        //        }
        //      }
        //    }
        //    container minimum-links {
        //      description "IMA group minimum active links";
        //      choice minimum_links_type {
        //        case case_1 {
        //          leaf symmetrical {
        //            description "Minimum active receive and transmit links";
        //            type union {
        //              type string {
        //                pattern "<.*>|$.*";
        //              }
        //              type uint32 {
        //                range "1 .. 32";
        //              }
        //            }
        //          }
        //        }
        //      }
        //    }
        //    container frame-synchronization {
        //      description "IMA group frame synchronization state parameters";
        //      // uses apply-advanced;
        //      leaf alpha {
        //        description "Consecutive invalid ICP cells";
        //        type union {
        //          type string {
        //            pattern "<.*>|$.*";
        //          }
        //          type uint32 {
        //            range "1 .. 2";
        //          }
        //        }
        //      }
        //      leaf beta {
        //        description "Consecutive errored ICP cells";
        //        type union {
        //          type string {
        //            pattern "<.*>|$.*";
        //          }
        //          type uint32 {
        //            range "1 .. 5";
        //          }
        //        }
        //      }
        //      leaf gamma {
        //        description "Consecutive valid ICP cells";
        //        type union {
        //          type string {
        //            pattern "<.*>|$.*";
        //          }
        //          type uint32 {
        //            range "1 .. 5";
        //          }
        //        }
        //      }
        //    }
        //    container test-procedure {
        //      description "IMA group test pattern procedure";
        //      // uses apply-advanced;
        //      leaf period {
        //        description "Length of IMA pattern test";
        //        units "seconds";
        //        type union {
        //          type string {
        //            pattern "<.*>|$.*";
        //          }
        //          type uint32 {
        //            range "1 .. 4294967294";
        //          }
        //        }
        //      }
        //      leaf interface {
        //        description "Interface name of the IMA link to test";
        //        type union {
        //          type jt:interface-device;
        //          type string {
        //            pattern "<.*>|$.*";
        //          }
        //        }
        //      }
        //      leaf pattern {
        //        description "IMA test pattern";
        //        type union {
        //          type string {
        //            pattern "<.*>|$.*";
        //          }
        //          type uint32 {
        //            range "1 .. 254";
        //          }
        //        }
        //      }
        //    }
        //    leaf differential-delay {
        //      description "Maximum differential delay among links in the IMA group";
        //      units "milliseconds";
        //      type union {
        //        type string {
        //          pattern "<.*>|$.*";
        //        }
        //        type uint32 {
        //          range "1 .. 56";
        //        }
        //      }
        //    }
        //  }
        //  container ima-link-options {
        //    description "IMA link options";
        //    // uses apply-advanced;
        //    leaf group-id {
        //      description "IMA group ID this IMA link belongs to";
        //      type union {
        //        type string {
        //          pattern "<.*>|$.*";
        //        }
        //        type uint32;
        //      }
        //    }
        //  }
        //  list multi-chassis-protection {
        //    key name;
        //    description "Inter-Chassis protection configuration";
        //    uses multi-chassis-protection-group;
        //  }
        //  container clocking {
        //    description "Interface clock source";
        //    choice clocking_choices {
        //      case case_1 {
        //        leaf internal {
        //          description "Clocking provided by local system";
        //          type empty;
        //        }
        //      }
        //      case case_2 {
        //        container external {
        //          presence "enable external";
        //          description "Clocking provided by DCE (loop timing)";
        //        }
        //      }
        //    }
        //  }
         leaf link-mode {
           description "Link operational mode";
           type enumeration {
             enum "automatic" {
               description "Automatically negotiate duplex";
             }
             enum "half-duplex" {
               description "Half-duplex operation";
             }
             enum "full-duplex" {
               description "Full-duplex operation";
             }
           }
         }
         leaf media-type {
           description "Interface media type (copper or fiber)";
           type enumeration {
             enum "copper" {
               description "Copper as media";
             }
             enum "fiber" {
               description "Fiber as media";
             }
           }
         }
         leaf encapsulation {
           description "Physical link-layer encapsulation";
           type enumeration {
             enum "ethernet" {
               description "Ethernet physical media";
             }
             enum "fddi" {
               description "FDDI physical media";
             }
             enum "token-ring" {
               description "Token Ring physical media";
             }
             enum "ppp" {
               description "Serial PPP device";
             }
             enum "ppp-ccc" {
               description "Serial PPP device for a cross-connect";
             }
             enum "ppp-tcc" {
               description "Serial PPP device for a translational cross-connect";
             }
             enum "ether-vpls-ppp" {
               description "Ethernet VPLS over PPP (bridging) device";
             }
             enum "frame-relay" {
               description "Frame Relay encapsulation";
             }
             enum "frame-relay-ccc" {
               description "Frame Relay for cross-connect";
             }
             enum "frame-relay-tcc" {
               description "Frame Relay for translational cross-connect";
             }
             enum "extended-frame-relay-ccc" {
               description "Any Frame Relay DLCI for cross-connect";
             }
             enum "extended-frame-relay-tcc" {
               description "Any Frame Relay DLCI for translational cross-connect";
             }
             enum "flexible-frame-relay" {
               description "Multiple Frame Relay encapsulations";
             }
             enum "frame-relay-port-ccc" {
               description "Frame Relay port encapsulation for a cross-connect";
             }
             enum "frame-relay-ether-type" {
               description "Cisco-compatible Frame Relay encapsulation";
             }
             enum "frame-relay-ether-type-tcc" {
               description "Cisco-compatible Frame Relay encapsulation for translational cross-connect";
             }
             enum "extended-frame-relay-ether-type-tcc" {
               description "Cisco-compatible Frame Relay encapsulation any DLCI for translational cross-connect";
             }
             enum "cisco-hdlc" {
               description "Cisco-compatible HDLC framing";
             }
             enum "cisco-hdlc-ccc" {
               description "Cisco-compatible HDLC framing for a cross-connect";
             }
             enum "cisco-hdlc-tcc" {
               description "Cisco-compatible HDLC framing for a translational cross-connect";
             }
            //  enum "vlan-ccc" {
            //    description "802.1q tagging for a cross-connect";
            //  }
            //  enum "extended-vlan-ccc" {
            //    description "Nonstandard TPID tagging for a cross-connect";
            //  }
            //  enum "ethernet-ccc" {
            //    description "Ethernet cross-connect";
            //  }
            //  enum "flexible-ethernet-services" {
            //    description "Allows per-unit Ethernet encapsulation configuration";
            //  }
            //  enum "smds-dxi" {
            //    description "SMDS DXI framing";
            //  }
            //  enum "atm-pvc" {
            //    description "ATM permanent virtual circuits";
            //  }
            //  enum "atm-ccc-cell-relay" {
            //    description "ATM cell relay encapsulation for cross-connect";
            //  }
            //  enum "ethernet-over-atm" {
            //    description "Ethernet over ATM encapsulation";
            //  }
            //  enum "ethernet-tcc" {
            //    description "Ethernet translational cross-connect";
            //  }
            //  enum "extended-vlan-tcc" {
            //    description "802.1q tagging for a translational cross-connect";
            //  }
            //  enum "multilink-frame-relay-uni-nni" {
            //    description "Multilink Frame Relay UNI NNI (FRF.16) encapsulation";
            //  }
            //  enum "satop" {
            //    description "Structure-Agnostic TDM over Packet encapsulation";
            //  }
            //  enum "cesopsn" {
            //    description "Structure-Agnostic TDM over Packet encapsulation";
            //  }
            //  enum "ima" {
            //    description "Inverse Multiplexing for ATM";
            //  }
            //  enum "ethernet-vpls" {
            //    description "Ethernet virtual private LAN service";
            //  }
            //  enum "ethernet-bridge" {
            //    description "Ethernet layer-2 bridging";
            //  }
            //  enum "vlan-vpls" {
            //    description "VLAN virtual private LAN service";
            //  }
            //  enum "vlan-vci-ccc" {
            //    description "CCC for VLAN Q-in-Q and ATM VPI/VCI interworking";
            //  }
            //  enum "extended-vlan-vpls" {
            //    description "Extended VLAN virtual private LAN service";
            //  }
             enum "extended-vlan-bridge" {
               description "VLAN layer-2 bridging";
             }
             enum "multilink-ppp" {
               description "Multilink PPP";
             }
             enum "generic-services" {
               description "Generic services";
             }
           }
         }
        //  leaf network-isolation-profile {
        //    description "Attach a network isolation profile on this interface";
        //    type string;
        //  }
        //  container esi {
        //    description "ESI configuration of multi-homed interface";
        //    // uses apply-advanced;
        //    container auto-derive {
        //      description "Auto-derive ESI value for the interface";
        //      // uses apply-advanced;
        //      choice esitype {
        //        case case_1 {
        //          leaf lacp-pe-system-id-and-admin-key {
        //            description "Auto-derive ESI from lacp pe system-id and admin key";
        //            type empty;
        //          }
        //        }
        //        case case_2 {
        //          leaf type-1-lacp {
        //            description "Auto-generate Type1 ESI LACP";
        //            type empty;
        //          }
        //        }
        //        case case_3 {
        //          container type-3-system-mac {
        //            description "Auto-generate Type3 ESI System-mac";
        //            // uses apply-advanced;
        //            leaf mac {
        //              description "System mac";
        //              type jt:mac-unicast;
        //            }
        //            leaf local-discriminator {
        //              description "Local-discriminator";
        //              type union {
        //                type string {
        //                  pattern "<.*>|$.*";
        //                }
        //                type int32 {
        //                  range "0 .. 16777215";
        //                }
        //              }
        //            }
        //          }
        //        }
        //      }
        //    }
        //    leaf identifier {
        //      description "ESI value for the interface";
        //      type jt:esi;
        //    }
        //    choice mode {
        //      case case_1 {
        //        leaf single-active {
        //          description "Single-active mode";
        //          type empty;
        //        }
        //      }
        //      case case_2 {
        //        leaf all-active {
        //          description "All-active mode";
        //          type empty;
        //        }
        //      }
        //    }
        //    container df-election-granularity {
        //      presence "enable df-election-granularity";
        //      description "DF Election Granularity Selection ";
        //      // uses apply-advanced;
        //      choice mode {
        //        case case_1 {
        //          container per-esi {
        //            presence "enable per-esi";
        //            description "DF Election Granularity Per Esi";
        //            // uses apply-advanced;
        //            leaf lacp-oos-on-ndf {
        //              description "Lacp Oos";
        //              type empty;
        //            }
        //          }
        //        }
        //        case case_2 {
        //          leaf per-esi-vlan {
        //            description "Per Esi Vlan";
        //            type empty;
        //          }
        //        }
        //      }
        //    }
        //    container df-election-type {
        //      presence "enable df-election-type";
        //      description "DF Election Type";
        //      // uses apply-advanced;
        //      choice pref_choice {
        //        case case_1 {
        //          container preference {
        //            presence "enable preference";
        //            description "Preference based DF election";
        //            // uses apply-advanced;
        //            leaf value {
        //              description "Preference value for EVPN Multihoming DF election";
        //              default "32767";
        //              type union {
        //                type string {
        //                  pattern "<.*>|$.*";
        //                }
        //                type uint32 {
        //                  range "0 .. 65535";
        //                }
        //              }
        //            }
        //          }
        //        }
        //      }
        //      choice mod_choice {
        //        case case_1 {
        //          container mod {
        //            presence "enable mod";
        //            description "MOD based DF election";
        //          }
        //        }
        //      }
        //    }
        //    leaf source-bmac {
        //      description "Unicast Source B-MAC address per ESI for PBB-EVPN";
        //      type jt:mac-unicast;
        //    }
        //  }
        //  container framing {
        //    description "Frame type";
        //    // uses apply-advanced;
        //    choice frame {
        //      case case_1 {
        //        leaf lan-phy {
        //          description "802.3ae 10-Gbps LAN-mode interface";
        //          type empty;
        //        }
        //      }
        //      case case_2 {
        //        leaf wan-phy {
        //          description "802.3ae 10-Gbps WAN-mode interface";
        //          type empty;
        //        }
        //      }
        //      case case_3 {
        //        leaf sonet {
        //          description "SONET framing";
        //          type empty;
        //        }
        //      }
        //      case case_4 {
        //        leaf sdh {
        //          description "SDH framing";
        //          type empty;
        //        }
        //      }
        //    }
        //    leaf precise-bandwidth {
        //      description "Use precise bandwidth for 10G wan-phy interface";
        //      type empty;
        //    }
        //  }
        //  leaf unidirectional {
        //    description "Unidirectional Mode";
        //    type empty;
        //  }
        //  container lmi {
        //    description "Local Management Interface settings";
        //    // uses apply-advanced;
        //    leaf n391dte {
        //      description "DTE full status polling interval";
        //      type union {
        //        type string {
        //          pattern "<.*>|$.*";
        //        }
        //        type uint16 {
        //          range "1 .. 255";
        //        }
        //      }
        //    }
        //    leaf n392dce {
        //      description "DCE error threshold";
        //      type union {
        //        type string {
        //          pattern "<.*>|$.*";
        //        }
        //        type uint16 {
        //          range "1 .. 10";
        //        }
        //      }
        //    }
        //    leaf n392dte {
        //      description "DTE error threshold";
        //      type union {
        //        type string {
        //          pattern "<.*>|$.*";
        //        }
        //        type uint16 {
        //          range "1 .. 10";
        //        }
        //      }
        //    }
        //    leaf n393dce {
        //      description "DCE monitored event count";
        //      type union {
        //        type string {
        //          pattern "<.*>|$.*";
        //        }
        //        type uint16 {
        //          range "1 .. 10";
        //        }
        //      }
        //    }
        //    leaf n393dte {
        //      description "DTE monitored event count";
        //      type union {
        //        type string {
        //          pattern "<.*>|$.*";
        //        }
        //        type uint16 {
        //          range "1 .. 10";
        //        }
        //      }
        //    }
        //    leaf t391dte {
        //      description "DTE polling timer";
        //      units "seconds";
        //      type union {
        //        type string {
        //          pattern "<.*>|$.*";
        //        }
        //        type uint16 {
        //          range "5 .. 30";
        //        }
        //      }
        //    }
        //    leaf t392dce {
        //      description "DCE polling verification timer";
        //      units "seconds";
        //      type union {
        //        type string {
        //          pattern "<.*>|$.*";
        //        }
        //        type uint16 {
        //          range "5 .. 30";
        //        }
        //      }
        //    }
        //    leaf lmi-type {
        //      description "Specify the Frame Relay LMI type";
        //      type enumeration {
        //        enum "ansi" {
        //          description "Use ANSI Annex D LMI";
        //        }
        //        enum "itu" {
        //          description "Use ITU Q933a Annex A LMI";
        //        }
        //        enum "c-lmi" {
        //          description "Use Consortium LMI";
        //        }
        //      }
        //    }
        //  }
        //  container mlfr-uni-nni-bundle-options {
        //    description "Multilink Frame Relay UNI NNI (FRF.16) management settings";
        //    // uses apply-advanced;
        //    container cisco-interoperability {
        //      description "FRF.16 Cisco interoperability settings";
        //      // uses apply-advanced;
        //      leaf send-lip-remove-link-for-link-reject {
        //        description "Send Link Integrity Protocol remove link on receiving add-link rejection";
        //        type empty;
        //      }
        //    }
        //    leaf mrru {
        //      description "Maximum received reconstructed unit";
        //      units "bytes";
        //      type union {
        //        type string {
        //          pattern "<.*>|$.*";
        //        }
        //        type uint16 {
        //          range "1500 .. 4500";
        //        }
        //      }
        //    }
        //    leaf yellow-differential-delay {
        //      description "Yellow differential delay among bundle links to give warning";
        //      units "milliseconds";
        //      type union {
        //        type string {
        //          pattern "<.*>|$.*";
        //        }
        //        type uint16 {
        //          range "3 .. 2000";
        //        }
        //      }
        //    }
        //    leaf red-differential-delay {
        //      description "Red differential delay among bundle links to take action";
        //      units "milliseconds";
        //      type union {
        //        type string {
        //          pattern "<.*>|$.*";
        //        }
        //        type uint16 {
        //          range "5 .. 2000";
        //        }
        //      }
        //    }
        //    leaf action-red-differential-delay {
        //      description "Type of actions when differential delay exceeds red limit";
        //      type enumeration {
        //        enum "remove-link" {
        //          description "Remove bundle link from service when exceeding red limit";
        //        }
        //        enum "disable-tx" {
        //          description "Disable transfer of bundle link when exceeding red limit";
        //        }
        //      }
        //    }
        //    leaf fragment-threshold {
        //      description "Fragmentation threshold";
        //      units "bytes";
        //      type union {
        //        type string {
        //          pattern "<.*>|$.*";
        //        }
        //        type uint32 {
        //          range "64 .. 16320";
        //        }
        //      }
        //    }
        //    leaf drop-timeout {
        //      description "Drop timeout";
        //      units "milliseconds";
        //      type union {
        //        type string {
        //          pattern "<.*>|$.*";
        //        }
        //        type uint16 {
        //          range "0 .. 2000";
        //        }
        //      }
        //    }
        //    leaf link-layer-overhead {
        //      description "Link layer bit stuffing overhead (0.0 .. 50.0 percent)";
        //      type jt:unsigned-float;
        //    }
        //    leaf lmi-type {
        //      description "Specify the multilink Frame Relay UNI NNI LMI type";
        //      type enumeration {
        //        enum "ansi" {
        //          description "Use ANSI Annex D LMI";
        //        }
        //        enum "itu" {
        //          description "Use ITU Q933a Annex A LMI";
        //        }
        //        enum "c-lmi" {
        //          description "Use Consortium LMI";
        //        }
        //      }
        //    }
        //    leaf minimum-links {
        //      description "Minimum number of links to sustain the bundle";
        //      type union {
        //        type string {
        //          pattern "<.*>|$.*";
        //        }
        //        type uint16 {
        //          range "1 .. 8";
        //        }
        //      }
        //    }
        //    leaf hello-timer {
        //      description "LIP hello timer";
        //      type union {
        //        type string {
        //          pattern "<.*>|$.*";
        //        }
        //        type uint16 {
        //          range "5 .. 180";
        //        }
        //      }
        //    }
        //    leaf acknowledge-timer {
        //      description "LIP ack timer";
        //      type union {
        //        type string {
        //          pattern "<.*>|$.*";
        //        }
        //        type uint16 {
        //          range "1 .. 10";
        //        }
        //      }
        //    }
        //    leaf acknowledge-retries {
        //      description "LIP ack retry times";
        //      type union {
        //        type string {
        //          pattern "<.*>|$.*";
        //        }
        //        type uint16 {
        //          range "1 .. 5";
        //        }
        //      }
        //    }
        //    leaf n391 {
        //      description "Multilink Frame Relay UNI NNI full status polling counter";
        //      type union {
        //        type string {
        //          pattern "<.*>|$.*";
        //        }
        //        type uint16 {
        //          range "1 .. 255";
        //        }
        //      }
        //    }
        //    leaf n392 {
        //      description "Multilink Frame Relay UNI NNI LMI error threshold";
        //      type union {
        //        type string {
        //          pattern "<.*>|$.*";
        //        }
        //        type uint16 {
        //          range "1 .. 10";
        //        }
        //      }
        //    }
        //    leaf n393 {
        //      description "Multilink Frame Relay UNI NNI LMI monitored event count";
        //      type union {
        //        type string {
        //          pattern "<.*>|$.*";
        //        }
        //        type uint16 {
        //          range "1 .. 10";
        //        }
        //      }
        //    }
        //    leaf t391 {
        //      description "Multilink Frame Relay UNI NNI link integrity verify polling timer";
        //      type union {
        //        type string {
        //          pattern "<.*>|$.*";
        //        }
        //        type uint16 {
        //          range "5 .. 30";
        //        }
        //      }
        //    }
        //    leaf t392 {
        //      description "Multilink Frame Relay UNI NNI polling verification timer";
        //      type union {
        //        type string {
        //          pattern "<.*>|$.*";
        //        }
        //        type uint16 {
        //          range "5 .. 30";
        //        }
        //      }
        //    }
        //  }
         leaf mac {
           description "Hardware MAC address";
           type jt:mac-unicast;
         }
        //  leaf no-forwarding-viable {
        //    description "Disable forwarding";
        //    type empty;
        //  }
         container p4rt {
           description "P4-runtime interfaces";
           // uses apply-advanced;
           leaf id {
             description "Port number";
             type union {
               type string {
                 pattern "<.*>|$.*";
               }
               type uint64 {
                 range "1 .. 4294967296";
               }
             }
           }
           leaf node-id {
             description "Device Id";
             type union {
               type string {
                 pattern "<.*>|$.*";
               }
               type uint64 {
                 range "1 .. 18446744073709551615";
               }
             }
           }
         }
        //  container receive-bucket {
        //    description "Set receive bucket parameters";
        //    uses dcd_rx_bucket_config;
        //  }
        //  container transmit-bucket {
        //    description "Set transmit bucket parameters";
        //    uses dcd_tx_bucket_config;
        //  }
        //  leaf shared-interface {
        //    description "Enable shared interface on the interface";
        //    type empty;
        //  }
        //  container sonet-options {
        //    description "SONET interface-specific options";
        //    uses sonet_options_type;
        //  }
        //  container logical-tunnel-options {
        //    description "Logical Tunnel interface-specific options";
        //    // uses apply-advanced;
        //    container link-protection {
        //      presence "enable link-protection";
        //      description "Enable link protection mode";
        //      // uses apply-advanced;
        //      leaf revertive {
        //        description "Revert back (Default mode) from active backup link to primary, if primary is UP";
        //        type empty;
        //      }
        //      leaf non-revertive {
        //        description "Do not revert back from active backup link to primary, if primary is UP";
        //        type empty;
        //      }
        //    }
        //    leaf per-unit-mac-disable {
        //      description "Disable the creation of per unit mac address on LT IFLs for VPLS/CCC encaps";
        //      type empty;
        //    }
        //    container load-balance {
        //      uses aggregate-load-balance;
        //    }
        //    leaf distribution-list {
        //      description "Distribution list to which interface belongs";
        //      type string {
        //        length "1 .. 20";
        //      }
        //    }
        //  }
        //  container aggregated-sonet-options {
        //    description "Aggregated SONET interface-specific options";
        //    // uses apply-advanced;
        //    leaf minimum-links {
        //      description "Minimum number of aggregated links";
        //      type union {
        //        type string {
        //          pattern "<.*>|$.*";
        //        }
        //        type uint16;
        //      }
        //    }
        //    leaf link-speed {
        //      description "Aggregated links speed";
        //      type enumeration {
        //        enum "oc3" {
        //          description "Links are OC-3c or STM-1c";
        //        }
        //        enum "oc12" {
        //          description "Links are OC-12c or STM-4c";
        //        }
        //        enum "oc48" {
        //          description "Links are OC-48c or STM-16c";
        //        }
        //        enum "oc192" {
        //          description "Links are OC-192c or STM-64c";
        //        }
        //        enum "oc768" {
        //          description "Links are OC-768c or STM-256c";
        //        }
        //        enum "mixed" {
        //          description "Links are various speeds";
        //        }
        //      }
        //    }
        //    leaf minimum-bandwidth {
        //      description "Minimum bandwidth necessary to sustain bundle";
        //      units "bps";
        //      type union {
        //        type string {
        //          pattern "<.*>|$.*";
        //        }
        //        type uint64 {
        //          range "0 .. 159232000000";
        //        }
        //      }
        //    }
        //  }
        //  container atm-options {
        //    description "ATM interface-specific options";
        //    // uses apply-advanced;
        //    leaf pic-type {
        //      description "Type of ATM PIC (ATM I, ATM II or ATM CE)";
        //      type enumeration {
        //        enum "atm-ce" {
        //          description "CE PIC";
        //        }
        //        enum "atm2" {
        //          description "ATM II IQ PIC";
        //        }
        //        enum "atm1" {
        //          description "ATM I PIC";
        //        }
        //      }
        //    }
        //    leaf cell-bundle-size {
        //      description "L2 circuit cell bundle size";
        //      units "cells";
        //      type union {
        //        type string {
        //          pattern "<.*>|$.*";
        //        }
        //        type uint32 {
        //          range "1 .. 176";
        //        }
        //      }
        //    }
        //    leaf cell-bundle-timeout {
        //      description "L2 circuit cell bundle timeout";
        //      units "microseconds";
        //      type union {
        //        type string {
        //          pattern "<.*>|$.*";
        //        }
        //        type uint32 {
        //          range "1 .. 512";
        //        }
        //      }
        //    }
        //    leaf plp-to-clp {
        //      description "Enable ATM2 PLP to CLP copy";
        //      type empty;
        //    }
        //    leaf use-null-cw {
        //      description "Always insert/strip null control words with cell-relay";
        //      type empty;
        //    }
        //    container promiscuous-mode {
        //      presence "enable promiscuous-mode";
        //      description "Set ATM interface to promiscuous mode";
        //      // uses apply-advanced;
        //      list vpi {
        //        key name;
        //        ordered-by user;
        //        description "Open this VPI in promiscuous mode";
        //        leaf name {
        //          description "Virtual path index";
        //          type union {
        //            type string {
        //              pattern "<.*>|$.*";
        //            }
        //            type uint32 {
        //              range "0 .. 255";
        //            }
        //          }
        //        }
        //      }
        //    }
        //    list vpi {
        //      key name;
        //      ordered-by user;
        //      description "Define a virtual path";
        //      leaf name {
        //        description "Virtual path index";
        //        type union {
        //          type string {
        //            pattern "<.*>|$.*";
        //          }
        //          type uint32 {
        //            range "0 .. 255";
        //          }
        //        }
        //      }
        //      // uses apply-advanced;
        //      leaf maximum-vcs {
        //        description "Maximum number of virtual circuits on this VP";
        //        type union {
        //          type uint32;
        //          type string {
        //            pattern "<.*>|$.*";
        //          }
        //        }
        //      }
        //      container shaping {
        //        description "Virtual path traffic-shaping options";
        //        uses dcd_shaping_config;
        //      }
        //      container oam-period {
        //        description "F4 OAM cell period";
        //        choice oam_period_choices {
        //          case case_1 {
        //            leaf oam-period {
        //              description "F4 OAM cell period";
        //              units "seconds";
        //              type union {
        //                type string {
        //                  pattern "<.*>|$.*";
        //                }
        //                type uint32 {
        //                  range "1 .. 900";
        //                }
        //              }
        //            }
        //          }
        //          case case_2 {
        //            container disable {
        //              presence "enable disable";
        //              description "Disable F4 OAM loopback";
        //            }
        //          }
        //        }
        //      }
        //      container oam-liveness {
        //        description "F4 OAM virtual path liveness parameters";
        //        // uses apply-advanced;
        //        leaf up-count {
        //          description "Number of F4 OAM cells to consider VP up";
        //          type union {
        //            type string {
        //              pattern "<.*>|$.*";
        //            }
        //            type uint32 {
        //              range "1 .. 255";
        //            }
        //          }
        //        }
        //        leaf down-count {
        //          description "Number of F4 OAM cells to consider VP down";
        //          type union {
        //            type string {
        //              pattern "<.*>|$.*";
        //            }
        //            type uint32 {
        //              range "1 .. 255";
        //            }
        //          }
        //        }
        //      }
        //    }
        //    container ilmi {
        //      presence "enable ilmi";
        //      description "Enable Interim Local Management Interface";
        //      // uses apply-advanced;
        //    }
        //    list linear-red-profiles {
        //      key name;
        //      ordered-by user;
        //      description "ATM2 CoS virtual circuit drop profiles";
        //      leaf name {
        //        description "Linear RED profile name";
        //        type string {
        //        }
        //      }
        //      leaf queue-depth {
        //        description "Maximum queue depth";
        //        units "cells";
        //        type string;
        //      }
        //      leaf high-plp-threshold {
        //        description "Fill level percentage when linear RED is applied for high PLP";
        //        type union {
        //          type string {
        //            pattern "<.*>|$.*";
        //          }
        //          type uint32 {
        //            range "0 .. 100";
        //          }
        //        }
        //      }
        //      leaf low-plp-threshold {
        //        description "Fill level percentage when linear RED is applied for low PLP";
        //        type union {
        //          type string {
        //            pattern "<.*>|$.*";
        //          }
        //          type uint32 {
        //            range "0 .. 100";
        //          }
        //        }
        //      }
        //      leaf high-plp-max-threshold {
        //        description "Fill level percentage with 100 percent packet drop for high PLP";
        //        type union {
        //          type string {
        //            pattern "<.*>|$.*";
        //          }
        //          type uint32 {
        //            range "0 .. 100";
        //          }
        //        }
        //      }
        //      leaf low-plp-max-threshold {
        //        description "Fill level percentage with 100 percent packet drop for low PLP";
        //        type union {
        //          type string {
        //            pattern "<.*>|$.*";
        //          }
        //          type uint32 {
        //            range "0 .. 100";
        //          }
        //        }
        //      }
        //    }
        //    list scheduler-maps {
        //      key name;
        //      ordered-by user;
        //      description "ATM2 CoS parameters assigned to forwarding classes";
        //      leaf name {
        //        description "ATM2 CoS scheduler map name";
        //        type string {
        //        }
        //      }
        //      // uses apply-advanced;
        //      leaf vc-cos-mode {
        //        description "ATM2 virtual circuit CoS mode";
        //        type enumeration {
        //          enum "strict" {
        //            description "Always schedule high priority queue first";
        //          }
        //          enum "alternate" {
        //            description "Every other packet from high priority queue (default)";
        //          }
        //        }
        //      }
        //      list forwarding-class {
        //        key name;
        //        ordered-by user;
        //        description "Scheduling parameters associated with forwarding class";
        //        leaf name {
        //          description "Forwarding class name";
        //          type string {
        //          }
        //        }
        //        // uses apply-advanced;
        //        leaf priority {
        //          description "Queuing priority assigned to forwarding class";
        //          type enumeration {
        //            enum "low" {
        //              description "Low priority queuing";
        //            }
        //            enum "high" {
        //              description "High priority queuing";
        //            }
        //          }
        //        }
        //        container transmit-weight {
        //          description "Transmit weight";
        //          choice weight-method {
        //            case case_1 {
        //              leaf percent {
        //                description "Transmit weight as percentage";
        //                type union {
        //                  type string {
        //                    pattern "<.*>|$.*";
        //                  }
        //                  type uint32 {
        //                    range "5 .. 100";
        //                  }
        //                }
        //              }
        //            }
        //            case case_2 {
        //              leaf cells {
        //                description "Transmit weight by cells count";
        //                type string;
        //              }
        //            }
        //          }
        //        }
        //        choice drop-profile-method {
        //          case case_1 {
        //            container epd-threshold {
        //              description "Early packet discard threshold for ATM2";
        //              uses epd_threshold_config;
        //            }
        //          }
        //          case case_2 {
        //            leaf linear-red-profile {
        //              description "Linear RED profile profile name";
        //              type string;
        //            }
        //          }
        //        }
        //      }
        //    }
        //    container mpls {
        //      description "MPLS options";
        //      uses mpls_ifd_options;
        //    }
        //    choice payload-scrambler-choice {
        //      leaf payload-scrambler {
        //        description "Enable payload scrambling";
        //        type empty;
        //      }
        //      leaf no-payload-scrambler {
        //        description "Don't enable payload scrambling";
        //        type empty;
        //      }
        //    }
        //  }
        //  container multiservice-options {
        //    description "Multiservice interface-specific options";
        //    // uses apply-advanced;
        //    choice syslog-choice {
        //      leaf syslog {
        //        description "Enable system logging on this interface";
        //        type empty;
        //      }
        //      leaf no-syslog {
        //        description "Don't enable system logging on this interface";
        //        type empty;
        //      }
        //    }
        //    choice core-dump-choice {
        //      leaf core-dump {
        //        description "Enable core dumping on this interface";
        //        type empty;
        //      }
        //      leaf no-core-dump {
        //        description "Don't enable core dumping on this interface";
        //        type empty;
        //      }
        //    }
        //    choice dump-on-flow-control-choice {
        //      leaf dump-on-flow-control {
        //        description "Enable dumping for this interface on prolonged flow-control";
        //        status deprecated;
        //        type empty;
        //      }
        //      leaf no-dump-on-flow-control {
        //        description "Don't enable dumping for this interface on prolonged flow-control";
        //        status deprecated;
        //        type empty;
        //      }
        //    }
        //    choice reset-on-flow-control-choice {
        //      leaf reset-on-flow-control {
        //        description "Enable resetting this interface on prolonged flow-control";
        //        status deprecated;
        //        type empty;
        //      }
        //      leaf no-reset-on-flow-control {
        //        description "Don't enable resetting this interface on prolonged flow-control";
        //        status deprecated;
        //        type empty;
        //      }
        //    }
        //    container flow-control-options {
        //      description "Flow control configuration";
        //      // uses apply-advanced;
        //      leaf dump-on-flow-control {
        //        description "Cause core dump during prolonged flow-control";
        //        type empty;
        //      }
        //      leaf reset-on-flow-control {
        //        description "Reset interface during prolonged flow-control";
        //        type empty;
        //      }
        //      leaf down-on-flow-control {
        //        description "Bring interface down during prolonged flow-control";
        //        type empty;
        //      }
        //      leaf up-on-flow-control {
        //        description "Keep interface up during prolonged flow-control";
        //        type empty;
        //      }
        //    }
        //  }
        //  container ggsn-options {
        //    description "GGSN interface-specific options";
        //    // uses apply-advanced;
        //    choice syslog-choice {
        //      leaf syslog {
        //        description "Enable system logging on this interface";
        //        type empty;
        //      }
        //      leaf no-syslog {
        //        description "Don't enable system logging on this interface";
        //        type empty;
        //      }
        //    }
        //    choice core-dump-choice {
        //      leaf core-dump {
        //        description "Enable core dumping on this interface";
        //        type empty;
        //      }
        //      leaf no-core-dump {
        //        description "Don't enable core dumping on this interface";
        //        type empty;
        //      }
        //    }
        //  }
        //  container ppp-options {
        //    description "Point-to-Point Protocol (PPP) interface-specific options";
        //    uses ppp_options_type;
        //  }
        //  container redundancy-options {
        //    description "Redundancy options";
        //    // uses apply-advanced;
        //    leaf primary {
        //      description "Specify the primary interface";
        //      type union {
        //        type jt:interface-device;
        //        type string {
        //          pattern "<.*>|$.*";
        //        }
        //      }
        //    }
        //    leaf secondary {
        //      description "Specify the secondary interface";
        //      type union {
        //        type jt:interface-device;
        //        type string {
        //          pattern "<.*>|$.*";
        //        }
        //      }
        //    }
        //    container redundancy-peer {
        //      description "Specify information for peer";
        //      // uses apply-advanced;
        //      leaf ipaddress {
        //        description "Specify the IP address";
        //        type jt:ipv4addr;
        //      }
        //    }
        //    container redundancy-local {
        //      description "Specify information for the local peer";
        //      // uses apply-advanced;
        //      leaf data-address {
        //        description "Specify the HA local data IP address";
        //        type jt:ipv4addr;
        //      }
        //    }
        //    leaf routing-instance {
        //      description "Specify routing-instance for the HA traffic";
        //      type string;
        //    }
        //    leaf replication-threshold {
        //      description "Duration for which flow should remain active for replication";
        //      default "180";
        //      units "seconds";
        //      type union {
        //        type string {
        //          pattern "<.*>|$.*";
        //        }
        //        type uint32 {
        //          range "60 .. 3600";
        //        }
        //      }
        //    }
        //    container replication-options {
        //      description "Specify state replication attributes";
        //      // uses apply-advanced;
        //      leaf mtu {
        //        description "Specify the maximal packet size for replicated data";
        //        default "1500";
        //        type union {
        //          type string {
        //            pattern "<.*>|$.*";
        //          }
        //          type uint32 {
        //            range "1500 .. 8000";
        //          }
        //        }
        //      }
        //    }
        //    container replicate-services {
        //      description "Replicate services state from active to backup";
        //      // uses apply-advanced;
        //      leaf pgcp {
        //        description "Replicate the PGCP service state";
        //        type empty;
        //      }
        //    }
        //  }
        //  container load-balancing-options {
        //    description "Load-balancing on services pics";
        //    // uses apply-advanced;
        //    list member-interface {
        //      key name;
        //      max-elements 36;
        //      leaf name {
        //        description "Interface name";
        //        type union {
        //          type jt:interface-device;
        //          type string {
        //            pattern "<.*>|$.*";
        //          }
        //        }
        //      }
        //      // uses apply-advanced;
        //      container redundancy-group {
        //        description "Group id to represent a pair of active-backup mams";
        //        leaf description {
        //          description "Text description mapping the redundancy group id";
        //          type string;
        //        }
        //        leaf group-id {
        //          description "Value for Redundancy-group";
        //          type union {
        //            type string {
        //              pattern "<.*>|$.*";
        //            }
        //            type uint32 {
        //              range "1 .. 18";
        //            }
        //          }
        //        }
        //      }
        //    }
        //    container member-failure-options {
        //      description "Load balancing member failure handling options";
        //      // uses apply-advanced;
        //      choice member-failure {
        //        case case_1 {
        //          container redistribute-all-traffic {
        //            presence "enable redistribute-all-traffic";
        //            description "On a member failure, redistribute traffic to ams";
        //            // uses apply-advanced;
        //            leaf enable-rejoin {
        //              description "Failed member can rejoin after recovery";
        //              type empty;
        //            }
        //          }
        //        }
        //        case case_2 {
        //          container drop-member-traffic {
        //            presence "enable drop-member-traffic";
        //            description "On a member failure, drop its traffic";
        //            // uses apply-advanced;
        //            leaf rejoin-timeout {
        //              description "Wait time(in seconds) for failed member to rejoin";
        //              default "120";
        //              type union {
        //                type string {
        //                  pattern "<.*>|$.*";
        //                }
        //                type uint32 {
        //                  range "0 .. 1000";
        //                }
        //              }
        //            }
        //            leaf enable-rejoin {
        //              description "Failed member can join after recovery";
        //              type empty;
        //            }
        //          }
        //        }
        //      }
        //    }
        //    leaf no-bundle-flap {
        //      description "No bundle flap on member addition - recommended only with IPSec services";
        //      type empty;
        //    }
        //    container high-availability-options {
        //      description "High Availability options for Load-balancing";
        //      // uses apply-advanced;
        //      choice ha-type {
        //        case case_1 {
        //          container many-to-one {
        //            description "N:1 High Availability model";
        //            // uses apply-advanced;
        //            leaf preferred-backup {
        //              description "Preferred backup Interface name";
        //              type union {
        //                type jt:interface-device;
        //                type string {
        //                  pattern "<.*>|$.*";
        //                }
        //              }
        //            }
        //          }
        //        }
        //        case case_2 {
        //          container one-to-one {
        //            description "1:1 High Availability model";
        //            // uses apply-advanced;
        //            list redundancy-group {
        //              key name;
        //              ordered-by user;
        //              description "Group number for linking HA member for intra-chassis";
        //              leaf name {
        //                description "Value for HA Redundancy-group";
        //                type union {
        //                  type string {
        //                    pattern "<.*>|$.*";
        //                  }
        //                  type uint32 {
        //                    range "1 .. 18";
        //                  }
        //                }
        //              }
        //              leaf preferred-backup {
        //                description "Preferred backup Interface name for Redundancy group";
        //                type union {
        //                  type jt:interface-device;
        //                  type string {
        //                    pattern "<.*>|$.*";
        //                  }
        //                }
        //              }
        //            }
        //            leaf preferred-backup {
        //              description "Preferred backup Interface name";
        //              type union {
        //                type jt:interface-device;
        //                type string {
        //                  pattern "<.*>|$.*";
        //                }
        //              }
        //            }
        //          }
        //        }
        //      }
        //    }
        //  }
        //  container aggregated-inline-services-options {
        //    description "Aggregated Inline Service interface specific options";
        //    // uses apply-advanced;
        //    leaf primary-interface {
        //      description "Specify the primary interface";
        //      type union {
        //        type jt:interface-device;
        //        type string {
        //          pattern "<.*>|$.*";
        //        }
        //      }
        //    }
        //    leaf secondary-interface {
        //      description "Specify the secondary interface";
        //      type union {
        //        type jt:interface-device;
        //        type string {
        //          pattern "<.*>|$.*";
        //        }
        //      }
        //    }
        //  }
        //  container anchoring-options {
        //    description "Groups anchoring PFEs or FPCs together.";
        //    // uses apply-advanced;
        //    leaf apfe-group-set {
        //      description "Ties up different anchoring groups to share similar fate";
        //      type string {
        //        length "1 .. 32";
        //      }
        //    }
        //    list primary-list {
        //      key name;
        //      description "Primary anchoring PFE name.";
        //      leaf name {
        //        description "Anchoring PFE name.";
        //        type string {
        //        }
        //      }
        //      // uses apply-advanced;
        //    }
        //    container secondary {
        //      presence "enable secondary";
        //      description "Secondary anchoring PFE name.";
        //      // uses apply-advanced;
        //      leaf anchoring-device-name {
        //        description "Anchoring PFE name.";
        //        type string {
        //        }
        //      }
        //    }
        //    choice mode {
        //      case case_1 {
        //        leaf warm-standby {
        //          description "Delayed failover to secondary when primary fails";
        //          type empty;
        //        }
        //      }
        //    }
        //  }
        //  container lsq-failure-options {
        //    description "Link services queuing failure options";
        //    // uses apply-advanced;
        //    list trigger-link-failure {
        //      key name;
        //      ordered-by user;
        //      description "Link on which to trigger failure";
        //      leaf name {
        //        description "Interface name";
        //        type union {
        //          type jt:interface-device;
        //          type string {
        //            pattern "<.*>|$.*";
        //          }
        //        }
        //      }
        //      // uses apply-advanced;
        //    }
        //    choice no-termination-request-choice {
        //      leaf no-termination-request {
        //        description "Do not send PPP termination requests";
        //        type empty;
        //      }
        //      leaf no-no-termination-request {
        //        description "Don't do not send PPP termination requests";
        //        type empty;
        //      }
        //    }
        //  }
        //  container redundancy-group {
        //    description "Redundancy group configuration";
        //    // uses apply-advanced;
        //    list member-interface {
        //      key name;
        //      description "Member interface for the redundancy group";
        //      leaf name {
        //        description "Interface name of member";
        //        type union {
        //          type jt:interface-device;
        //          type string {
        //            pattern "<.*>|$.*";
        //          }
        //        }
        //      }
        //      // uses apply-advanced;
        //      choice redundancy {
        //        case case_1 {
        //          leaf active {
        //            description "Active interface";
        //            type empty;
        //          }
        //        }
        //        case case_2 {
        //          leaf backup {
        //            description "Backup interface";
        //            type empty;
        //          }
        //        }
        //      }
        //    }
        //    leaf maximum-links {
        //      type union {
        //        type string {
        //          pattern "<.*>|$.*";
        //        }
        //        type uint32 {
        //          range "2 .. 32";
        //        }
        //      }
        //    }
        //  }
        //  container services-options {
        //    description "Services interface-specific options";
        //    // uses apply-advanced;
        //    container syslog {
        //      description "Define system log parameters";
        //      uses log-object;
        //    }
        //    container jflow-log {
        //      description "Define Jflow-log parameters.";
        //      // uses apply-advanced;
        //      leaf message-rate-limit {
        //        description "Maximum jflow-log NAT error events allowed per second from this interface";
        //        units "messages per second";
        //        type union {
        //          type string {
        //            pattern "<.*>|$.*";
        //          }
        //          type uint32 {
        //            range "1 .. 2147483647";
        //          }
        //        }
        //      }
        //    }
        //    container deterministic-nat-configuration-log-interval {
        //      presence "enable deterministic-nat-configuration-log-interval";
        //      description "Define Deterministic NAT parameters";
        //      // uses apply-advanced;
        //      leaf interval {
        //        description "Interval in which deterministic NAT logs are generated";
        //        units "seconds";
        //        type union {
        //          type string {
        //            pattern "<.*>|$.*";
        //          }
        //          type uint32 {
        //            range "1800 .. 86400";
        //          }
        //        }
        //      }
        //    }
        //    leaf open-timeout {
        //      description "Timeout period for TCP session establishment";
        //      units "seconds";
        //      type union {
        //        type string {
        //          pattern "<.*>|$.*";
        //        }
        //        type uint32 {
        //          range "4 .. 300";
        //        }
        //      }
        //    }
        //    leaf close-timeout {
        //      description "Timeout period for TCP session tear-down";
        //      units "seconds";
        //      type union {
        //        type string {
        //          pattern "<.*>|$.*";
        //        }
        //        type uint32 {
        //          range "2 .. 300";
        //        }
        //      }
        //    }
        //    leaf inactivity-timeout {
        //      description "Inactivity timeout period for established sessions (4..86400)";
        //      units "seconds";
        //      type union {
        //        type uint32;
        //        type string {
        //          pattern "<.*>|$.*";
        //        }
        //      }
        //    }
        //    leaf inactivity-tcp-timeout {
        //      description "Inactivity timeout period for TCP established sessions";
        //      units "seconds";
        //      type union {
        //        type string {
        //          pattern "<.*>|$.*";
        //        }
        //        type uint32 {
        //          range "4 .. 86400";
        //        }
        //      }
        //    }
        //    leaf inactivity-asymm-tcp-timeout {
        //      description "Inactivity timeout period for asymmetric TCP established sessions";
        //      units "seconds";
        //      type union {
        //        type string {
        //          pattern "<.*>|$.*";
        //        }
        //        type uint32 {
        //          range "4 .. 86400";
        //        }
        //      }
        //    }
        //    leaf inactivity-non-tcp-timeout {
        //      description "Inactivity timeout period for non-TCP established sessions";
        //      units "seconds";
        //      type union {
        //        type string {
        //          pattern "<.*>|$.*";
        //        }
        //        type uint32 {
        //          range "4 .. 86400";
        //        }
        //      }
        //    }
        //    leaf session-timeout {
        //      description "Session timeout period for established sessions";
        //      units "seconds";
        //      type union {
        //        type string {
        //          pattern "<.*>|$.*";
        //        }
        //        type uint32 {
        //          range "4 .. 86400";
        //        }
        //      }
        //    }
        //    leaf disable-global-timeout-override {
        //      description "Disallow overriding  global inactivity or session timeout";
        //      type empty;
        //    }
        //    leaf tcp-tickles {
        //      description "Number of TCP keep-alive packets to be sent for bi-directional TCP flows";
        //      default "4";
        //      type union {
        //        type string {
        //          pattern "<.*>|$.*";
        //        }
        //        type uint8 {
        //          range "0 .. 30";
        //        }
        //      }
        //    }
        //    container trio-flow-offload {
        //      presence "enable trio-flow-offload";
        //      description "Allow PIC to offload flows to Trio-based PFE";
        //      // uses apply-advanced;
        //      leaf minimum-bytes {
        //        description "Attempt flow offload after minimum bytes are seen on the flow";
        //        type union {
        //          type uint32;
        //          type string {
        //            pattern "<.*>|$.*";
        //          }
        //        }
        //      }
        //    }
        //    leaf fragment-limit {
        //      description "Maximum number of fragments allowed for a packet";
        //      default "64";
        //      type union {
        //        type string {
        //          pattern "<.*>|$.*";
        //        }
        //        type uint8 {
        //          range "1 .. 250";
        //        }
        //      }
        //    }
        //    leaf reassembly-timeout {
        //      description "Re-assembly timeout (seconds) for fragments of a packet";
        //      default "4";
        //      units "seconds";
        //      type union {
        //        type string {
        //          pattern "<.*>|$.*";
        //        }
        //        type uint8 {
        //          range "1 .. 60";
        //        }
        //      }
        //    }
        //    leaf cgn-pic {
        //      description "PIC will be used for Carrier Grade NAT configuration only";
        //      type empty;
        //    }
        //    leaf pba-interim-logging-interval {
        //      description "Interim logging interval in seconds";
        //      default "0";
        //      units "seconds";
        //      type union {
        //        type string {
        //          pattern "<.*>|$.*";
        //        }
        //        type uint32 {
        //          range "0 .. 86400";
        //        }
        //      }
        //    }
        //    container session-limit {
        //      presence "enable session-limit";
        //      description "Session limit";
        //      // uses apply-advanced;
        //      leaf maximum {
        //        description "Maximum number of sessions allowed simultaneously";
        //        type string;
        //      }
        //      leaf rate {
        //        description "Maximum number of new sessions allowed per second";
        //        type string;
        //      }
        //      leaf cpu-load-threshold {
        //        description "CPU limit in percentage for auto-tuning of session rate";
        //        units "percent";
        //        type union {
        //          type string {
        //            pattern "<.*>|$.*";
        //          }
        //          type uint8 {
        //            range "1 .. 100";
        //          }
        //        }
        //      }
        //    }
        //    leaf enable-subscriber-analysis {
        //      description "Enable subscriber analysis on the interface";
        //      type empty;
        //    }
        //    leaf disable-subscriber-analysis {
        //      description "Disable subscriber analysis on the interface";
        //      type empty;
        //    }
        //    leaf disable-usp-tracing {
        //      description "Disable usp tracing on this pic";
        //      type empty;
        //    }
        //    leaf disable-drop-flows {
        //      description "Disable drop flows on this pic";
        //      type empty;
        //    }
        //    container ignore-errors {
        //      presence "enable ignore-errors";
        //      description "Ignore anomalies or errors";
        //      leaf tcp {
        //        description "TCP protocol errors";
        //        type empty;
        //      }
        //      leaf alg {
        //        description "ALG anomalies or errors";
        //        type empty;
        //      }
        //    }
        //    container capture {
        //      description "Packet capture for SFW and NAT on the Services PIC";
        //      // uses apply-advanced;
        //      leaf capture-size {
        //        description "The number of packets to store";
        //        type union {
        //          type string {
        //            pattern "<.*>|$.*";
        //          }
        //          type uint32 {
        //            range "1 .. 344000";
        //          }
        //        }
        //      }
        //      leaf pkt-size {
        //        description "Number of bytes to be saved from each packet";
        //        type union {
        //          type string {
        //            pattern "<.*>|$.*";
        //          }
        //          type uint16 {
        //            range "64 .. 15000";
        //          }
        //        }
        //      }
        //      leaf logs-per-packet {
        //        description "The number of trace messages stored for each packet";
        //        type union {
        //          type string {
        //            pattern "<.*>|$.*";
        //          }
        //          type uint16 {
        //            range "0 .. 500";
        //          }
        //        }
        //      }
        //      leaf max-log-line-size {
        //        description "The maximum length of a stored trace message";
        //        type union {
        //          type uint8;
        //          type string {
        //            pattern "<.*>|$.*";
        //          }
        //        }
        //      }
        //      container filter {
        //        presence "enable filter";
        //        description "Filtering options for the packet capture";
        //        // uses apply-advanced;
        //        container source-ip {
        //          description "Filter based on source-ip (and wildcard)";
        //          leaf ip {
        //            description "Source IP";
        //            type jt:ipaddr;
        //          }
        //          leaf wildcard {
        //            description "Source IP wildcard";
        //            type jt:ipaddr;
        //          }
        //        }
        //        container dest-ip {
        //          description "Filter based on dest-ip (and wildcard)";
        //          leaf ip {
        //            description "Dest IP";
        //            type jt:ipaddr;
        //          }
        //          leaf wildcard {
        //            description "Dest IP wildcard";
        //            type jt:ipaddr;
        //          }
        //        }
        //        container sw-sip {
        //          description "Filter based on source softwire ip (and wildcard)";
        //          leaf ip {
        //            description "Source softwire IP";
        //            type jt:ipv6addr;
        //          }
        //          leaf wildcard {
        //            description "Source IP wildcard";
        //            type jt:ipv6addr;
        //          }
        //        }
        //        container sw-dip {
        //          description "Filter based on destination softwire ip (and wildcard)";
        //          leaf ip {
        //            description "Destination softwire IP";
        //            type jt:ipaddr;
        //          }
        //          leaf wildcard {
        //            description "Destination IP wildcard";
        //            type jt:ipaddr;
        //          }
        //        }
        //        container sport-range {
        //          description "Filter based on source port";
        //          leaf low {
        //            description "Source port range start";
        //            type union {
        //              type uint16;
        //              type string {
        //                pattern "<.*>|$.*";
        //              }
        //            }
        //          }
        //          leaf high {
        //            description "Source port range end";
        //            type union {
        //              type uint16;
        //              type string {
        //                pattern "<.*>|$.*";
        //              }
        //            }
        //          }
        //        }
        //        container dport-range {
        //          description "Filter based on destination port";
        //          leaf low {
        //            description "Destination port range start";
        //            type union {
        //              type uint16;
        //              type string {
        //                pattern "<.*>|$.*";
        //              }
        //            }
        //          }
        //          leaf high {
        //            description "Destination port range end";
        //            type union {
        //              type uint16;
        //              type string {
        //                pattern "<.*>|$.*";
        //              }
        //            }
        //          }
        //        }
        //        leaf proto {
        //          description "Filter based on L4 protocol";
        //          type enumeration {
        //            enum "icmp" {
        //            }
        //            enum "tcp" {
        //            }
        //            enum "udp" {
        //            }
        //          }
        //        }
        //      }
        //    }
        //    container flow {
        //      description "Define flow parameters";
        //      // uses apply-advanced;
        //      container traceoptions {
        //        description "Trace options for flow services";
        //      }
        //    }
        //    leaf fpc-pic-information {
        //      description "Include FPC and PIC slot number in the syslogs";
        //      type empty;
        //    }
        //    leaf utc-timestamp {
        //      description "Use UTC time for security log timestamps";
        //      type empty;
        //    }
        //    leaf syslog-local-system-timestamp {
        //      description "Use local system time for services syslog timestamp";
        //      type empty;
        //    }
        //  }
        //  container t3-options {
        //    description "T3 interface-specific options";
        //    // uses apply-advanced;
        //    leaf loopback {
        //      description "Loopback mode";
        //      type enumeration {
        //        enum "local" {
        //          description "Local loopback";
        //        }
        //        enum "remote" {
        //          description "Remote loopback";
        //        }
        //        enum "payload" {
        //          description "Payload loopback";
        //        }
        //      }
        //    }
        //    choice long-buildout-choice {
        //      leaf long-buildout {
        //        description "Set hardware to drive line longer than 255 feet";
        //        type empty;
        //      }
        //      leaf no-long-buildout {
        //        description "Don't set hardware to drive line longer than 255 feet";
        //        type empty;
        //      }
        //    }
        //    choice loop-timing-choice {
        //      leaf loop-timing {
        //        description "Set loop timing for T3";
        //        type empty;
        //      }
        //      leaf no-loop-timing {
        //        description "Don't set loop timing for T3";
        //        type empty;
        //      }
        //    }
        //    container compatibility-mode {
        //      description "Set CSU compatibility mode";
        //      choice vendor {
        //        case case_1 {
        //          container larscom {
        //            presence "enable larscom";
        //            description "Compatible with Larscom CSU";
        //            leaf subrate {
        //              description "Set subrate value";
        //              type union {
        //                type string {
        //                  pattern "<.*>|$.*";
        //                }
        //                type uint32 {
        //                  range "1 .. 14";
        //                }
        //              }
        //            }
        //          }
        //        }
        //        case case_2 {
        //          container verilink {
        //            presence "enable verilink";
        //            description "Compatible with Verilink CSU (not on 2/4-port T3 PIC)";
        //            leaf subrate {
        //              description "Set subrate value";
        //              type union {
        //                type string {
        //                  pattern "<.*>|$.*";
        //                }
        //                type uint32 {
        //                  range "1 .. 28";
        //                }
        //              }
        //            }
        //          }
        //        }
        //        case case_3 {
        //          container adtran {
        //            presence "enable adtran";
        //            description "Compatible with Adtran CSU (not on 2/4-port T3 PIC)";
        //            leaf subrate {
        //              description "Set subrate value";
        //              type union {
        //                type string {
        //                  pattern "<.*>|$.*";
        //                }
        //                type uint32 {
        //                  range "1 .. 588";
        //                }
        //              }
        //            }
        //          }
        //        }
        //        case case_4 {
        //          container kentrox {
        //            presence "enable kentrox";
        //            description "Compatible with Kentrox CSU";
        //            leaf subrate {
        //              description "Set subrate value (not on 2/4-port T3 PIC)";
        //              type union {
        //                type string {
        //                  pattern "<.*>|$.*";
        //                }
        //                type uint32 {
        //                  range "1 .. 69";
        //                }
        //              }
        //            }
        //          }
        //        }
        //        case case_5 {
        //          container digital-link {
        //            presence "enable digital-link";
        //            description "Compatible with Digital Link CSU";
        //            leaf subrate {
        //              description "Set subrate value";
        //              type enumeration {
        //                enum "301Kb" {
        //                  description "301 Kbps";
        //                }
        //                enum "601Kb" {
        //                  description "601 Kbps";
        //                }
        //                enum "902Kb" {
        //                  description "902 Kbps";
        //                }
        //                enum "1.2Mb" {
        //                  description "1.2 Mbps";
        //                }
        //                enum "1.5Mb" {
        //                  description "1.5 Mbps";
        //                }
        //                enum "1.8Mb" {
        //                  description "1.8 Mbps";
        //                }
        //                enum "2.1Mb" {
        //                  description "2.1 Mbps";
        //                }
        //                enum "2.4Mb" {
        //                  description "2.4 Mbps";
        //                }
        //                enum "2.7Mb" {
        //                  description "2.7 Mbps";
        //                }
        //                enum "3.0Mb" {
        //                  description "3.0 Mbps";
        //                }
        //                enum "3.3Mb" {
        //                  description "3.3 Mbps";
        //                }
        //                enum "3.6Mb" {
        //                  description "3.6 Mbps";
        //                }
        //                enum "3.9Mb" {
        //                  description "3.9 Mbps";
        //                }
        //                enum "4.2Mb" {
        //                  description "4.2 Mbps";
        //                }
        //                enum "4.5Mb" {
        //                  description "4.5 Mbps";
        //                }
        //                enum "4.8Mb" {
        //                  description "4.8 Mbps";
        //                }
        //                enum "5.1Mb" {
        //                  description "5.1 Mbps";
        //                }
        //                enum "5.4Mb" {
        //                  description "5.4 Mbps";
        //                }
        //                enum "5.7Mb" {
        //                  description "5.7 Mbps";
        //                }
        //                enum "6.0Mb" {
        //                  description "6.0 Mbps";
        //                }
        //                enum "6.3Mb" {
        //                  description "6.3 Mbps";
        //                }
        //                enum "6.6Mb" {
        //                  description "6.6 Mbps";
        //                }
        //                enum "6.9Mb" {
        //                  description "6.9 Mbps";
        //                }
        //                enum "7.2Mb" {
        //                  description "7.2 Mbps";
        //                }
        //                enum "7.5Mb" {
        //                  description "7.5 Mbps";
        //                }
        //                enum "7.8Mb" {
        //                  description "7.8 Mbps";
        //                }
        //                enum "8.1Mb" {
        //                  description "8.1 Mbps";
        //                }
        //                enum "8.4Mb" {
        //                  description "8.4 Mbps";
        //                }
        //                enum "8.7Mb" {
        //                  description "8.7 Mbps";
        //                }
        //                enum "9.0Mb" {
        //                  description "9.0 Mbps";
        //                }
        //                enum "9.3Mb" {
        //                  description "9.3 Mbps";
        //                }
        //                enum "9.6Mb" {
        //                  description "9.6 Mbps";
        //                }
        //                enum "9.9Mb" {
        //                  description "9.9 Mbps";
        //                }
        //                enum "10.2Mb" {
        //                  description "10.2 Mbps";
        //                }
        //                enum "10.5Mb" {
        //                  description "10.5 Mbps";
        //                }
        //                enum "10.8Mb" {
        //                  description "10.8 Mbps";
        //                }
        //                enum "11.1Mb" {
        //                  description "11.1 Mbps";
        //                }
        //                enum "11.4Mb" {
        //                  description "11.4 Mbps";
        //                }
        //                enum "11.7Mb" {
        //                  description "11.7 Mbps";
        //                }
        //                enum "12.0Mb" {
        //                  description "12.0 Mbps";
        //                }
        //                enum "12.3Mb" {
        //                  description "12.3 Mbps";
        //                }
        //                enum "12.6Mb" {
        //                  description "12.6 Mbps";
        //                }
        //                enum "12.9Mb" {
        //                  description "12.9 Mbps";
        //                }
        //                enum "13.2Mb" {
        //                  description "13.2 Mbps";
        //                }
        //                enum "13.5Mb" {
        //                  description "13.5 Mbps";
        //                }
        //                enum "13.8Mb" {
        //                  description "13.8 Mbps";
        //                }
        //                enum "14.1Mb" {
        //                  description "14.1 Mbps";
        //                }
        //                enum "14.4Mb" {
        //                  description "14.4 Mbps";
        //                }
        //                enum "14.7Mb" {
        //                  description "14.7 Mbps";
        //                }
        //                enum "15.0Mb" {
        //                  description "15.0 Mbps";
        //                }
        //                enum "15.3Mb" {
        //                  description "15.3 Mbps";
        //                }
        //                enum "15.6Mb" {
        //                  description "15.6 Mbps";
        //                }
        //                enum "15.9Mb" {
        //                  description "15.9 Mbps";
        //                }
        //                enum "16.2Mb" {
        //                  description "16.2 Mbps";
        //                }
        //                enum "16.5Mb" {
        //                  description "16.5 Mbps";
        //                }
        //                enum "16.8Mb" {
        //                  description "16.8 Mbps";
        //                }
        //                enum "17.1Mb" {
        //                  description "17.1 Mbps";
        //                }
        //                enum "17.4Mb" {
        //                  description "17.4 Mbps";
        //                }
        //                enum "17.7Mb" {
        //                  description "17.7 Mbps";
        //                }
        //                enum "18.0Mb" {
        //                  description "18.0 Mbps";
        //                }
        //                enum "18.3Mb" {
        //                  description "18.3 Mbps";
        //                }
        //                enum "18.6Mb" {
        //                  description "18.6 Mbps";
        //                }
        //                enum "18.9Mb" {
        //                  description "18.9 Mbps";
        //                }
        //                enum "19.2Mb" {
        //                  description "19.2 Mbps";
        //                }
        //                enum "19.5Mb" {
        //                  description "19.5 Mbps";
        //                }
        //                enum "19.8Mb" {
        //                  description "19.8 Mbps";
        //                }
        //                enum "20.1Mb" {
        //                  description "20.1 Mbps";
        //                }
        //                enum "20.5Mb" {
        //                  description "20.5 Mbps";
        //                }
        //                enum "20.8Mb" {
        //                  description "20.8 Mbps";
        //                }
        //                enum "21.1Mb" {
        //                  description "21.1 Mbps";
        //                }
        //                enum "21.4Mb" {
        //                  description "21.4 Mbps";
        //                }
        //                enum "21.7Mb" {
        //                  description "21.7 Mbps";
        //                }
        //                enum "22.0Mb" {
        //                  description "22.0 Mbps";
        //                }
        //                enum "22.3Mb" {
        //                  description "22.3 Mbps";
        //                }
        //                enum "22.6Mb" {
        //                  description "22.6 Mbps";
        //                }
        //                enum "22.9Mb" {
        //                  description "22.9 Mbps";
        //                }
        //                enum "23.2Mb" {
        //                  description "23.2 Mbps";
        //                }
        //                enum "23.5Mb" {
        //                  description "23.5 Mbps";
        //                }
        //                enum "23.8Mb" {
        //                  description "23.8 Mbps";
        //                }
        //                enum "24.1Mb" {
        //                  description "24.1 Mbps";
        //                }
        //                enum "24.4Mb" {
        //                  description "24.4 Mbps";
        //                }
        //                enum "24.7Mb" {
        //                  description "24.7 Mbps";
        //                }
        //                enum "25.0Mb" {
        //                  description "25.0 Mbps";
        //                }
        //                enum "25.3Mb" {
        //                  description "25.3 Mbps";
        //                }
        //                enum "25.6Mb" {
        //                  description "25.6 Mbps";
        //                }
        //                enum "25.9Mb" {
        //                  description "25.9 Mbps";
        //                }
        //                enum "26.2Mb" {
        //                  description "26.2 Mbps";
        //                }
        //                enum "26.5Mb" {
        //                  description "26.5 Mbps";
        //                }
        //                enum "26.8Mb" {
        //                  description "26.8 Mbps";
        //                }
        //                enum "27.1Mb" {
        //                  description "27.1 Mbps";
        //                }
        //                enum "27.4Mb" {
        //                  description "27.4 Mbps";
        //                }
        //                enum "27.7Mb" {
        //                  description "27.7 Mbps";
        //                }
        //                enum "28.0Mb" {
        //                  description "28.0 Mbps";
        //                }
        //                enum "28.3Mb" {
        //                  description "28.3 Mbps";
        //                }
        //                enum "28.6Mb" {
        //                  description "28.6 Mbps";
        //                }
        //                enum "28.9Mb" {
        //                  description "28.9 Mbps";
        //                }
        //                enum "29.2Mb" {
        //                  description "29.2 Mbps";
        //                }
        //                enum "29.5Mb" {
        //                  description "29.5 Mbps";
        //                }
        //                enum "29.8Mb" {
        //                  description "29.8 Mbps";
        //                }
        //                enum "30.1Mb" {
        //                  description "30.1 Mbps";
        //                }
        //                enum "30.4Mb" {
        //                  description "30.4 Mbps";
        //                }
        //                enum "30.7Mb" {
        //                  description "30.7 Mbps";
        //                }
        //                enum "31.0Mb" {
        //                  description "31.0 Mbps";
        //                }
        //                enum "31.3Mb" {
        //                  description "31.3 Mbps";
        //                }
        //                enum "31.6Mb" {
        //                  description "31.6 Mbps";
        //                }
        //                enum "31.9Mb" {
        //                  description "31.9 Mbps";
        //                }
        //                enum "32.2Mb" {
        //                  description "32.2 Mbps";
        //                }
        //                enum "32.5Mb" {
        //                  description "32.5 Mbps";
        //                }
        //                enum "32.8Mb" {
        //                  description "32.8 Mbps";
        //                }
        //                enum "33.1Mb" {
        //                  description "33.1 Mbps";
        //                }
        //                enum "33.4Mb" {
        //                  description "33.4 Mbps";
        //                }
        //                enum "33.7Mb" {
        //                  description "33.7 Mbps";
        //                }
        //                enum "34.0Mb" {
        //                  description "34.0 Mbps";
        //                }
        //                enum "34.3Mb" {
        //                  description "34.3 Mbps";
        //                }
        //                enum "34.6Mb" {
        //                  description "34.6 Mbps";
        //                }
        //                enum "34.9Mb" {
        //                  description "34.9 Mbps";
        //                }
        //                enum "35.2Mb" {
        //                  description "35.2 Mbps";
        //                }
        //                enum "35.5Mb" {
        //                  description "35.5 Mbps";
        //                }
        //                enum "35.8Mb" {
        //                  description "35.8 Mbps";
        //                }
        //                enum "36.1Mb" {
        //                  description "36.1 Mbps";
        //                }
        //                enum "36.4Mb" {
        //                  description "36.4 Mbps";
        //                }
        //                enum "36.7Mb" {
        //                  description "36.7 Mbps";
        //                }
        //                enum "37.0Mb" {
        //                  description "37.0 Mbps";
        //                }
        //                enum "37.3Mb" {
        //                  description "37.3 Mbps";
        //                }
        //                enum "37.6Mb" {
        //                  description "37.6 Mbps";
        //                }
        //                enum "37.9Mb" {
        //                  description "37.9 Mbps";
        //                }
        //                enum "38.2Mb" {
        //                  description "38.2 Mbps";
        //                }
        //                enum "38.5Mb" {
        //                  description "38.5 Mbps";
        //                }
        //                enum "38.8Mb" {
        //                  description "38.8 Mbps";
        //                }
        //                enum "39.1Mb" {
        //                  description "39.1 Mbps";
        //                }
        //                enum "39.4Mb" {
        //                  description "39.4 Mbps";
        //                }
        //                enum "39.7Mb" {
        //                  description "39.7 Mbps";
        //                }
        //                enum "40.0Mb" {
        //                  description "40.0 Mbps";
        //                }
        //                enum "40.3Mb" {
        //                  description "40.3 Mbps";
        //                }
        //                enum "40.6Mb" {
        //                  description "40.6 Mbps";
        //                }
        //                enum "40.9Mb" {
        //                  description "40.9 Mbps";
        //                }
        //                enum "41.2Mb" {
        //                  description "41.2 Mbps";
        //                }
        //                enum "41.5Mb" {
        //                  description "41.5 Mbps";
        //                }
        //                enum "41.8Mb" {
        //                  description "41.8 Mbps";
        //                }
        //                enum "42.1Mb" {
        //                  description "42.1 Mbps";
        //                }
        //                enum "42.4Mb" {
        //                  description "42.4 Mbps";
        //                }
        //                enum "42.7Mb" {
        //                  description "42.7 Mbps";
        //                }
        //                enum "43.0Mb" {
        //                  description "43.0 Mbps";
        //                }
        //                enum "43.3Mb" {
        //                  description "43.3 Mbps";
        //                }
        //                enum "43.6Mb" {
        //                  description "43.6 Mbps";
        //                }
        //                enum "43.9Mb" {
        //                  description "43.9 Mbps";
        //                }
        //                enum "44.2Mb" {
        //                  description "44.2 Mbps";
        //                }
        //              }
        //            }
        //          }
        //        }
        //      }
        //    }
        //    choice payload-scrambler-choice {
        //      leaf payload-scrambler {
        //        description "Enable payload scrambling";
        //        type empty;
        //      }
        //      leaf no-payload-scrambler {
        //        description "Don't enable payload scrambling";
        //        type empty;
        //      }
        //    }
        //    choice cbit-parity-choice {
        //      leaf cbit-parity {
        //        description "Enable C-bit parity mode";
        //        type empty;
        //      }
        //      leaf no-cbit-parity {
        //        description "Don't enable C-bit parity mode";
        //        type empty;
        //      }
        //    }
        //    leaf fcs {
        //      description "Frame checksum";
        //      type enumeration {
        //        enum "32" {
        //          description "32-bit mode";
        //        }
        //        enum "16" {
        //          description "16-bit mode";
        //        }
        //      }
        //    }
        //    leaf idle-cycle-flag {
        //      description "Value to transmit in idle cycles";
        //      type enumeration {
        //        enum "flags" {
        //          description "Transmit 0x7E in idle cycles";
        //        }
        //        enum "ones" {
        //          description "Transmit 0xFF (all ones) in idle cycles";
        //        }
        //      }
        //    }
        //    leaf start-end-flag {
        //      description "Set start/end flags on transmission";
        //      type enumeration {
        //        enum "shared" {
        //          description "Share start/end flags on transmit";
        //        }
        //        enum "filler" {
        //          description "Send two idle cycles between start/end flags";
        //        }
        //      }
        //    }
        //    choice feac-loop-respond-choice {
        //      leaf feac-loop-respond {
        //        description "Respond to FEAC loop requests";
        //        type empty;
        //      }
        //      leaf no-feac-loop-respond {
        //        description "Don't respond to FEAC loop requests";
        //        type empty;
        //      }
        //    }
        //    leaf bert-algorithm {
        //      description "Set BERT algorithm";
        //      type enumeration {
        //        enum "pseudo-2e3" {
        //          description "Pattern is 2^3 - 1";
        //        }
        //        enum "pseudo-2e4" {
        //          description "Pattern is 2^4 - 1";
        //        }
        //        enum "pseudo-2e5" {
        //          description "Pattern is 2^5 - 1";
        //        }
        //        enum "pseudo-2e6" {
        //          description "Pattern is 2^6 - 1";
        //        }
        //        enum "pseudo-2e7" {
        //          description "Pattern is 2^7 - 1";
        //        }
        //        enum "pseudo-2e9-o153" {
        //          description "Pattern is 2^9 - 1 (per O.153 standard)";
        //        }
        //        enum "pseudo-2e10" {
        //          description "Pattern is 2^10 - 1";
        //        }
        //        enum "pseudo-2e11-o152" {
        //          description "Pattern is 2^11 -1 (per O.152 standard)";
        //        }
        //        enum "pseudo-2e15-o151" {
        //          description "Pattern is 2^15 - 1 (per O.151 standard)";
        //        }
        //        enum "pseudo-2e17" {
        //          description "Pattern is 2^17 - 1";
        //        }
        //        enum "pseudo-2e18" {
        //          description "Pattern is 2^18 - 1";
        //        }
        //        enum "pseudo-2e20-o153" {
        //          description "Pattern is 2^20 - 1 (per O.153 standard)";
        //        }
        //        enum "pseudo-2e20-o151" {
        //          description "Pattern is 2^20 - 1 (per O.151 standard)";
        //        }
        //        enum "pseudo-2e21" {
        //          description "Pattern is 2^21 - 1";
        //        }
        //        enum "pseudo-2e22" {
        //          description "Pattern is 2^22 - 1";
        //        }
        //        enum "pseudo-2e23-o151" {
        //          description "Pattern is 2^23 (per O.151 standard)";
        //        }
        //        enum "pseudo-2e25" {
        //          description "Pattern is 2^25 - 1";
        //        }
        //        enum "pseudo-2e28" {
        //          description "Pattern is 2^28 - 1";
        //        }
        //        enum "pseudo-2e29" {
        //          description "Pattern is 2^29 - 1";
        //        }
        //        enum "pseudo-2e31" {
        //          description "Pattern is 2^31 - 1";
        //        }
        //        enum "pseudo-2e32" {
        //          description "Pattern is 2^32 - 1";
        //        }
        //        enum "all-ones-repeating" {
        //          description "Repeating one bits";
        //        }
        //        enum "all-zeros-repeating" {
        //          description "Repeating zero bits";
        //        }
        //        enum "alternating-ones-zeros" {
        //          description "Alternating ones and zeros";
        //        }
        //        enum "alternating-double-ones-zeros" {
        //          description "Alternating pairs of ones and zeros";
        //        }
        //        enum "repeating-3-in-24" {
        //          description "3 bits in 24 are set";
        //        }
        //        enum "repeating-1-in-8" {
        //          description "1 bit in 8 is set";
        //        }
        //        enum "repeating-1-in-4" {
        //          description "1 bit in 4 is set";
        //        }
        //      }
        //    }
        //    leaf bert-error-rate {
        //      description "Bit error rate (10^-n for n > 0, and zero for n = 0)";
        //      type union {
        //        type string {
        //          pattern "<.*>|$.*";
        //        }
        //        type uint32 {
        //          range "0 .. 7";
        //        }
        //      }
        //    }
        //    leaf bert-period {
        //      description "Length of BERT test";
        //      units "seconds";
        //      type union {
        //        type string {
        //          pattern "<.*>|$.*";
        //        }
        //        type uint32 {
        //          range "1 .. 240";
        //        }
        //      }
        //    }
        //    leaf buildout {
        //      description "Line buildout";
        //      units "feet";
        //      type union {
        //        type string {
        //          pattern "<.*>|$.*";
        //        }
        //        type uint32 {
        //          range "0 .. 450";
        //        }
        //      }
        //    }
        //    leaf atm-encapsulation {
        //      description "DS-3 interface encapsulation";
        //      type enumeration {
        //        enum "plcp" {
        //          description "PLCP encapsulation";
        //        }
        //        enum "direct" {
        //          description "ATM direct mapping";
        //        }
        //      }
        //    }
        //  }
        //  container e3-options {
        //    description "E3 interface-specific options";
        //    // uses apply-advanced;
        //    leaf loopback {
        //      description "Loopback mode";
        //      type enumeration {
        //        enum "local" {
        //          description "Local loopback";
        //        }
        //        enum "remote" {
        //          description "Remote loopback";
        //        }
        //      }
        //    }
        //    choice unframed-choice {
        //      leaf unframed {
        //        description "Enable unframed mode";
        //        type empty;
        //      }
        //      leaf no-unframed {
        //        description "Don't enable unframed mode";
        //        type empty;
        //      }
        //    }
        //    container compatibility-mode {
        //      description "Set CSU compatibility mode";
        //      choice vendor {
        //        case case_1 {
        //          leaf larscom {
        //            description "Compatible with Larscom CSU (only non IQ E3 interfaces)";
        //            type empty;
        //          }
        //        }
        //        case case_2 {
        //          container digital-link {
        //            presence "enable digital-link";
        //            description "Compatible with Digital Link CSU";
        //            leaf subrate {
        //              description "Set subrate value";
        //              type enumeration {
        //                enum "358Kb" {
        //                  description "358 Kbps";
        //                }
        //                enum "716Kb" {
        //                  description "716 Kbps";
        //                }
        //                enum "1.1Mb" {
        //                  description "1.1 Mbps";
        //                }
        //                enum "1.4Mb" {
        //                  description "1.4 Mbps";
        //                }
        //                enum "1.8Mb" {
        //                  description "1.8 Mbps";
        //                }
        //                enum "2.1Mb" {
        //                  description "2.1 Mbps";
        //                }
        //                enum "2.5Mb" {
        //                  description "2.5 Mbps";
        //                }
        //                enum "2.9Mb" {
        //                  description "2.9 Mbps";
        //                }
        //                enum "3.2Mb" {
        //                  description "3.2 Mbps";
        //                }
        //                enum "3.6Mb" {
        //                  description "3.6 Mbps";
        //                }
        //                enum "3.9Mb" {
        //                  description "3.9 Mbps";
        //                }
        //                enum "4.3Mb" {
        //                  description "4.3 Mbps";
        //                }
        //                enum "4.7Mb" {
        //                  description "4.7 Mbps";
        //                }
        //                enum "5.0Mb" {
        //                  description "5.0 Mbps";
        //                }
        //                enum "5.4Mb" {
        //                  description "5.4 Mbps";
        //                }
        //                enum "5.7Mb" {
        //                  description "5.7 Mbps";
        //                }
        //                enum "6.1Mb" {
        //                  description "6.1 Mbps";
        //                }
        //                enum "6.4Mb" {
        //                  description "6.4 Mbps";
        //                }
        //                enum "6.8Mb" {
        //                  description "6.8 Mbps";
        //                }
        //                enum "7.2Mb" {
        //                  description "7.2 Mbps";
        //                }
        //                enum "7.5Mb" {
        //                  description "7.5 Mbps";
        //                }
        //                enum "7.9Mb" {
        //                  description "7.9 Mbps";
        //                }
        //                enum "8.2Mb" {
        //                  description "8.2 Mbps";
        //                }
        //                enum "8.6Mb" {
        //                  description "8.6 Mbps";
        //                }
        //                enum "9.0Mb" {
        //                  description "9.0 Mbps";
        //                }
        //                enum "9.3Mb" {
        //                  description "9.3 Mbps";
        //                }
        //                enum "9.7Mb" {
        //                  description "9.7 Mbps";
        //                }
        //                enum "10.0Mb" {
        //                  description "10.0 Mbps";
        //                }
        //                enum "10.4Mb" {
        //                  description "10.4 Mbps";
        //                }
        //                enum "10.7Mb" {
        //                  description "10.7 Mbps";
        //                }
        //                enum "11.1Mb" {
        //                  description "11.1 Mbps";
        //                }
        //                enum "11.5Mb" {
        //                  description "11.5 Mbps";
        //                }
        //                enum "11.8Mb" {
        //                  description "11.8 Mbps";
        //                }
        //                enum "12.2Mb" {
        //                  description "12.2 Mbps";
        //                }
        //                enum "12.5Mb" {
        //                  description "12.5 Mbps";
        //                }
        //                enum "12.9Mb" {
        //                  description "12.9 Mbps";
        //                }
        //                enum "13.2Mb" {
        //                  description "13.2 Mbps";
        //                }
        //                enum "13.6Mb" {
        //                  description "13.6 Mbps";
        //                }
        //                enum "14.0Mb" {
        //                  description "14.0 Mbps";
        //                }
        //                enum "14.3Mb" {
        //                  description "14.3 Mbps";
        //                }
        //                enum "14.7Mb" {
        //                  description "14.7 Mbps";
        //                }
        //                enum "15.0Mb" {
        //                  description "15.0 Mbps";
        //                }
        //                enum "15.4Mb" {
        //                  description "15.4 Mbps";
        //                }
        //                enum "15.8Mb" {
        //                  description "15.8 Mbps";
        //                }
        //                enum "16.1Mb" {
        //                  description "16.1 Mbps";
        //                }
        //                enum "16.5Mb" {
        //                  description "16.5 Mbps";
        //                }
        //                enum "16.8Mb" {
        //                  description "16.8 Mbps";
        //                }
        //                enum "17.2Mb" {
        //                  description "17.2 Mbps";
        //                }
        //                enum "17.5Mb" {
        //                  description "17.5 Mbps";
        //                }
        //                enum "17.9Mb" {
        //                  description "17.9 Mbps";
        //                }
        //                enum "18.3Mb" {
        //                  description "18.3 Mbps";
        //                }
        //                enum "18.6Mb" {
        //                  description "18.6 Mbps";
        //                }
        //                enum "19.0Mb" {
        //                  description "19.0 Mbps";
        //                }
        //                enum "19.3Mb" {
        //                  description "19.3 Mbps";
        //                }
        //                enum "19.7Mb" {
        //                  description "19.7 Mbps";
        //                }
        //                enum "20.0Mb" {
        //                  description "20.0 Mbps";
        //                }
        //                enum "20.4Mb" {
        //                  description "20.4 Mbps";
        //                }
        //                enum "20.8Mb" {
        //                  description "20.8 Mbps";
        //                }
        //                enum "21.1Mb" {
        //                  description "21.1 Mbps";
        //                }
        //                enum "21.5Mb" {
        //                  description "21.5 Mbps";
        //                }
        //                enum "21.8Mb" {
        //                  description "21.8 Mbps";
        //                }
        //                enum "22.2Mb" {
        //                  description "22.2 Mbps";
        //                }
        //                enum "22.6Mb" {
        //                  description "22.6 Mbps";
        //                }
        //                enum "22.9Mb" {
        //                  description "22.9 Mbps";
        //                }
        //                enum "23.3Mb" {
        //                  description "23.3 Mbps";
        //                }
        //                enum "23.6Mb" {
        //                  description "23.6 Mbps";
        //                }
        //                enum "24.0Mb" {
        //                  description "24.0 Mbps";
        //                }
        //                enum "24.3Mb" {
        //                  description "24.3 Mbps";
        //                }
        //                enum "24.7Mb" {
        //                  description "24.7 Mbps";
        //                }
        //                enum "25.1Mb" {
        //                  description "25.1 Mbps";
        //                }
        //                enum "25.4Mb" {
        //                  description "25.4 Mbps";
        //                }
        //                enum "25.8Mb" {
        //                  description "25.8 Mbps";
        //                }
        //                enum "26.1Mb" {
        //                  description "26.1 Mbps";
        //                }
        //                enum "26.5Mb" {
        //                  description "26.5 Mbps";
        //                }
        //                enum "26.9Mb" {
        //                  description "26.9 Mbps";
        //                }
        //                enum "27.2Mb" {
        //                  description "27.2 Mbps";
        //                }
        //                enum "27.6Mb" {
        //                  description "27.6 Mbps";
        //                }
        //                enum "27.9Mb" {
        //                  description "27.9 Mbps";
        //                }
        //                enum "28.3Mb" {
        //                  description "28.3 Mbps";
        //                }
        //                enum "28.6Mb" {
        //                  description "28.6 Mbps";
        //                }
        //                enum "29.0Mb" {
        //                  description "29.0 Mbps";
        //                }
        //                enum "29.4Mb" {
        //                  description "29.4 Mbps";
        //                }
        //                enum "29.7Mb" {
        //                  description "29.7 Mbps";
        //                }
        //                enum "30.1Mb" {
        //                  description "30.1 Mbps";
        //                }
        //                enum "30.4Mb" {
        //                  description "30.4 Mbps";
        //                }
        //                enum "30.8Mb" {
        //                  description "30.8 Mbps";
        //                }
        //                enum "31.1Mb" {
        //                  description "31.1 Mbps";
        //                }
        //                enum "31.5Mb" {
        //                  description "31.5 Mbps";
        //                }
        //                enum "31.9Mb" {
        //                  description "31.9 Mbps";
        //                }
        //                enum "32.2Mb" {
        //                  description "32.2 Mbps";
        //                }
        //                enum "32.6Mb" {
        //                  description "32.6 Mbps";
        //                }
        //                enum "32.9Mb" {
        //                  description "32.9 Mbps";
        //                }
        //                enum "33.3Mb" {
        //                  description "33.3 Mbps";
        //                }
        //                enum "33.7Mb" {
        //                  description "33.7 Mbps";
        //                }
        //                enum "34.0Mb" {
        //                  description "34.0 Mbps";
        //                }
        //              }
        //            }
        //          }
        //        }
        //        case case_3 {
        //          container kentrox {
        //            presence "enable kentrox";
        //            description "Compatible with Kentrox CSU";
        //            leaf subrate {
        //              description "Set subrate value (only for E3 IQ interfaces)";
        //              type union {
        //                type string {
        //                  pattern "<.*>|$.*";
        //                }
        //                type uint32 {
        //                  range "1 .. 48";
        //                }
        //              }
        //            }
        //          }
        //        }
        //      }
        //    }
        //    choice payload-scrambler-choice {
        //      leaf payload-scrambler {
        //        description "Enable payload scrambling";
        //        type empty;
        //      }
        //      leaf no-payload-scrambler {
        //        description "Don't enable payload scrambling";
        //        type empty;
        //      }
        //    }
        //    leaf fcs {
        //      description "Frame checksum";
        //      type enumeration {
        //        enum "32" {
        //          description "32-bit mode";
        //        }
        //        enum "16" {
        //          description "16-bit mode";
        //        }
        //      }
        //    }
        //    leaf idle-cycle-flag {
        //      description "Value to transmit in idle cycles";
        //      type enumeration {
        //        enum "flags" {
        //          description "Transmit 0x7E in idle cycles";
        //        }
        //        enum "ones" {
        //          description "Transmit 0xFF (all ones) in idle cycles";
        //        }
        //      }
        //    }
        //    leaf invert-data {
        //      description "Invert data";
        //      type empty;
        //    }
        //    leaf start-end-flag {
        //      description "Set start/end flags on transmission";
        //      type enumeration {
        //        enum "shared" {
        //          description "Share start/end flags on transmit";
        //        }
        //        enum "filler" {
        //          description "Send two idle cycles between start/end flags";
        //        }
        //      }
        //    }
        //    leaf bert-algorithm {
        //      description "Set BERT algorithm";
        //      type enumeration {
        //        enum "pseudo-2e3" {
        //          description "Pattern is 2^3 - 1";
        //        }
        //        enum "pseudo-2e4" {
        //          description "Pattern is 2^4 - 1";
        //        }
        //        enum "pseudo-2e5" {
        //          description "Pattern is 2^5 - 1";
        //        }
        //        enum "pseudo-2e6" {
        //          description "Pattern is 2^6 - 1";
        //        }
        //        enum "pseudo-2e7" {
        //          description "Pattern is 2^7 - 1";
        //        }
        //        enum "pseudo-2e9-o153" {
        //          description "Pattern is 2^9 - 1 (per O.153 standard)";
        //        }
        //        enum "pseudo-2e10" {
        //          description "Pattern is 2^10 - 1";
        //        }
        //        enum "pseudo-2e11-o152" {
        //          description "Pattern is 2^11 -1 (per O.152 standard)";
        //        }
        //        enum "pseudo-2e15-o151" {
        //          description "Pattern is 2^15 - 1 (per O.151 standard)";
        //        }
        //        enum "pseudo-2e17" {
        //          description "Pattern is 2^17 - 1";
        //        }
        //        enum "pseudo-2e18" {
        //          description "Pattern is 2^18 - 1";
        //        }
        //        enum "pseudo-2e20-o153" {
        //          description "Pattern is 2^20 - 1 (per O.153 standard)";
        //        }
        //        enum "pseudo-2e20-o151" {
        //          description "Pattern is 2^20 - 1 (per O.151 standard)";
        //        }
        //        enum "pseudo-2e21" {
        //          description "Pattern is 2^21 - 1";
        //        }
        //        enum "pseudo-2e22" {
        //          description "Pattern is 2^22 - 1";
        //        }
        //        enum "pseudo-2e23-o151" {
        //          description "Pattern is 2^23 (per O.151 standard)";
        //        }
        //        enum "pseudo-2e25" {
        //          description "Pattern is 2^25 - 1";
        //        }
        //        enum "pseudo-2e28" {
        //          description "Pattern is 2^28 - 1";
        //        }
        //        enum "pseudo-2e29" {
        //          description "Pattern is 2^29 - 1";
        //        }
        //        enum "pseudo-2e31" {
        //          description "Pattern is 2^31 - 1";
        //        }
        //        enum "pseudo-2e32" {
        //          description "Pattern is 2^32 - 1";
        //        }
        //        enum "all-ones-repeating" {
        //          description "Repeating one bits";
        //        }
        //        enum "all-zeros-repeating" {
        //          description "Repeating zero bits";
        //        }
        //        enum "alternating-ones-zeros" {
        //          description "Alternating ones and zeros";
        //        }
        //        enum "alternating-double-ones-zeros" {
        //          description "Alternating pairs of ones and zeros";
        //        }
        //        enum "repeating-3-in-24" {
        //          description "3 bits in 24 are set";
        //        }
        //        enum "repeating-1-in-8" {
        //          description "1 bit in 8 is set";
        //        }
        //        enum "repeating-1-in-4" {
        //          description "1 bit in 4 is set";
        //        }
        //      }
        //    }
        //    leaf bert-error-rate {
        //      description "Bit error rate (10^-n for n > 0, and zero for n = 0)";
        //      type union {
        //        type string {
        //          pattern "<.*>|$.*";
        //        }
        //        type uint32 {
        //          range "0 .. 7";
        //        }
        //      }
        //    }
        //    leaf bert-period {
        //      description "Length of BERT test";
        //      units "seconds";
        //      type union {
        //        type string {
        //          pattern "<.*>|$.*";
        //        }
        //        type uint32 {
        //          range "1 .. 240";
        //        }
        //      }
        //    }
        //    leaf buildout {
        //      description "Line buildout";
        //      units "feet";
        //      type union {
        //        type string {
        //          pattern "<.*>|$.*";
        //        }
        //        type uint32 {
        //          range "0 .. 450";
        //        }
        //      }
        //    }
        //    leaf atm-encapsulation {
        //      description "E3 interface encapsulation";
        //      type enumeration {
        //        enum "plcp" {
        //          description "PLCP encapsulation";
        //        }
        //        enum "direct" {
        //          description "ATM direct mapping";
        //        }
        //      }
        //    }
        //    leaf framing {
        //      description "E3 line format";
        //      type enumeration {
        //        enum "g.751" {
        //          description "G.751 format";
        //        }
        //        enum "g.832" {
        //          description "G.832 format";
        //        }
        //      }
        //    }
        //  }
        //  container e1-options {
        //    description "E1 interface-specific options";
        //    // uses apply-advanced;
        //    leaf timeslots {
        //      description "Timeslots (1..32); for example, 1-4,6,9-11,32 (no space)";
        //      type string;
        //    }
        //    leaf loopback {
        //      description "Loopback mode";
        //      type enumeration {
        //        enum "local" {
        //          description "Local loopback";
        //        }
        //        enum "remote" {
        //          description "Remote loopback";
        //        }
        //      }
        //    }
        //    leaf framing {
        //      description "Framing mode";
        //      type enumeration {
        //        enum "g704" {
        //          description "G704 mode with CRC4";
        //        }
        //        enum "unframed" {
        //          description "Unframed mode";
        //        }
        //        enum "g704-no-crc4" {
        //          description "G704 mode without CRC4";
        //        }
        //      }
        //    }
        //    leaf fcs {
        //      description "Frame checksum";
        //      type enumeration {
        //        enum "32" {
        //          description "32-bit mode";
        //        }
        //        enum "16" {
        //          description "16-bit mode";
        //        }
        //      }
        //    }
        //    leaf invert-data {
        //      description "Invert data";
        //      type empty;
        //    }
        //    leaf idle-cycle-flag {
        //      description "Value to transmit in idle cycles";
        //      type enumeration {
        //        enum "flags" {
        //          description "Transmit 0x7E in idle cycles";
        //        }
        //        enum "ones" {
        //          description "Transmit 0xFF (all ones) in idle cycles";
        //        }
        //      }
        //    }
        //    leaf start-end-flag {
        //      description "Set start/end flags on transmission";
        //      type enumeration {
        //        enum "shared" {
        //          description "Share start/end flags on transmit";
        //        }
        //        enum "filler" {
        //          description "Send two idle cycles between start/end flags";
        //        }
        //      }
        //    }
        //    leaf bert-algorithm {
        //      description "Set BERT algorithm";
        //      type enumeration {
        //        enum "pseudo-2e3" {
        //          description "Pattern is 2^3 - 1";
        //        }
        //        enum "pseudo-2e4" {
        //          description "Pattern is 2^4 - 1";
        //        }
        //        enum "pseudo-2e5" {
        //          description "Pattern is 2^5 - 1";
        //        }
        //        enum "pseudo-2e6" {
        //          description "Pattern is 2^6 - 1";
        //        }
        //        enum "pseudo-2e7" {
        //          description "Pattern is 2^7 - 1";
        //        }
        //        enum "pseudo-2e9-o153" {
        //          description "Pattern is 2^9 - 1 (per O.153 standard)";
        //        }
        //        enum "pseudo-2e10" {
        //          description "Pattern is 2^10 - 1";
        //        }
        //        enum "pseudo-2e11-o152" {
        //          description "Pattern is 2^11 -1 (per O.152 standard)";
        //        }
        //        enum "pseudo-2e15-o151" {
        //          description "Pattern is 2^15 - 1 (per O.151 standard)";
        //        }
        //        enum "pseudo-2e17" {
        //          description "Pattern is 2^17 - 1";
        //        }
        //        enum "pseudo-2e18" {
        //          description "Pattern is 2^18 - 1";
        //        }
        //        enum "pseudo-2e20-o153" {
        //          description "Pattern is 2^20 - 1 (per O.153 standard)";
        //        }
        //        enum "pseudo-2e20-o151" {
        //          description "Pattern is 2^20 - 1 (per O.151 standard)";
        //        }
        //        enum "pseudo-2e21" {
        //          description "Pattern is 2^21 - 1";
        //        }
        //        enum "pseudo-2e22" {
        //          description "Pattern is 2^22 - 1";
        //        }
        //        enum "pseudo-2e23-o151" {
        //          description "Pattern is 2^23 (per O.151 standard)";
        //        }
        //        enum "pseudo-2e25" {
        //          description "Pattern is 2^25 - 1";
        //        }
        //        enum "pseudo-2e28" {
        //          description "Pattern is 2^28 - 1";
        //        }
        //        enum "pseudo-2e29" {
        //          description "Pattern is 2^29 - 1";
        //        }
        //        enum "pseudo-2e31" {
        //          description "Pattern is 2^31 - 1";
        //        }
        //        enum "pseudo-2e32" {
        //          description "Pattern is 2^32 - 1";
        //        }
        //        enum "all-ones-repeating" {
        //          description "Repeating one bits";
        //        }
        //        enum "all-zeros-repeating" {
        //          description "Repeating zero bits";
        //        }
        //        enum "alternating-ones-zeros" {
        //          description "Alternating ones and zeros";
        //        }
        //        enum "alternating-double-ones-zeros" {
        //          description "Alternating pairs of ones and zeros";
        //        }
        //        enum "repeating-3-in-24" {
        //          description "3 bits in 24 are set";
        //        }
        //        enum "repeating-1-in-8" {
        //          description "1 bit in 8 is set";
        //        }
        //        enum "repeating-1-in-4" {
        //          description "1 bit in 4 is set";
        //        }
        //      }
        //    }
        //    leaf bert-error-rate {
        //      description "Bit error rate (10^-n for n > 0, and zero for n = 0)";
        //      type union {
        //        type string {
        //          pattern "<.*>|$.*";
        //        }
        //        type uint32 {
        //          range "0 .. 7";
        //        }
        //      }
        //    }
        //    leaf bert-period {
        //      description "Length of BERT test";
        //      units "seconds";
        //      type union {
        //        type string {
        //          pattern "<.*>|$.*";
        //        }
        //        type uint32 {
        //          range "1 .. 86400";
        //        }
        //      }
        //    }
        //  }
        //  container t1-options {
        //    description "T1 interface-specific options";
        //    // uses apply-advanced;
        //    leaf timeslots {
        //      description "Timeslots (1..24; for example, 1-3,4,9,22-24 (no space)";
        //      type string;
        //    }
        //    leaf disable-remote-alarm-detection {
        //      description "Disable detection of a remote alarm";
        //      type enumeration {
        //        enum "yellow" {
        //          description "Disable yellow alarm detection";
        //        }
        //      }
        //    }
        //    leaf loopback {
        //      description "Loopback mode";
        //      type enumeration {
        //        enum "local" {
        //          description "Local loopback";
        //        }
        //        enum "remote" {
        //          description "Remote loopback";
        //        }
        //        enum "payload" {
        //          description "Payload loopback";
        //        }
        //      }
        //    }
        //    leaf buildout {
        //      description "Line buildout";
        //      type enumeration {
        //        enum "0-132" {
        //          description "Line buildout is between 0-132 feet";
        //        }
        //        enum "133-265" {
        //          description "Line buildout is between 133-265 feet";
        //        }
        //        enum "266-398" {
        //          description "Line buildout is between 266-398 feet";
        //        }
        //        enum "399-531" {
        //          description "Line buildout is between 399-531 feet";
        //        }
        //        enum "532-655" {
        //          description "Line buildout is between 532-655 feet";
        //        }
        //        enum "long-0db" {
        //          description "Long buildout with 0 dB transmit attenuation";
        //        }
        //        enum "long-7.5db" {
        //          description "Long buildout with 7.5 dB transmit attenuation";
        //        }
        //        enum "long-15db" {
        //          description "Long buildout with 15 dB transmit attenuation";
        //        }
        //        enum "long-22.5db" {
        //          description "Long buildout with 22.5 dB transmit attenuation";
        //        }
        //      }
        //    }
        //    leaf byte-encoding {
        //      description "Byte encoding";
        //      type enumeration {
        //        enum "nx64" {
        //          description "8 bits per byte";
        //        }
        //        enum "nx56" {
        //          description "7 bits per byte";
        //        }
        //      }
        //    }
        //    leaf line-encoding {
        //      description "Line encoding";
        //      type enumeration {
        //        enum "ami" {
        //          description "Automatic mark inversion";
        //        }
        //        enum "b8zs" {
        //          description "8-bit zero suppression";
        //        }
        //      }
        //    }
        //    leaf invert-data {
        //      description "Invert data";
        //      type empty;
        //    }
        //    leaf framing {
        //      description "Framing mode";
        //      type enumeration {
        //        enum "sf" {
        //          description "Super frame";
        //        }
        //        enum "esf" {
        //          description "Extended super frame";
        //        }
        //      }
        //    }
        //    leaf fcs {
        //      description "Frame checksum";
        //      type enumeration {
        //        enum "32" {
        //          description "32-bit mode";
        //        }
        //        enum "16" {
        //          description "16-bit mode";
        //        }
        //      }
        //    }
        //    leaf idle-cycle-flag {
        //      description "Value to transmit in idle cycles";
        //      type enumeration {
        //        enum "flags" {
        //          description "Transmit 0x7E in idle cycles";
        //        }
        //        enum "ones" {
        //          description "Transmit 0xFF (all ones) in idle cycles";
        //        }
        //      }
        //    }
        //    leaf start-end-flag {
        //      description "Set start/end flags on transmission";
        //      type enumeration {
        //        enum "shared" {
        //          description "Share start/end flags on transmit";
        //        }
        //        enum "filler" {
        //          description "Send two idle cycles between start/end flags";
        //        }
        //      }
        //    }
        //    leaf bert-algorithm {
        //      description "Set BERT algorithm";
        //      type enumeration {
        //        enum "pseudo-2e3" {
        //          description "Pattern is 2^3 - 1";
        //        }
        //        enum "pseudo-2e4" {
        //          description "Pattern is 2^4 - 1";
        //        }
        //        enum "pseudo-2e5" {
        //          description "Pattern is 2^5 - 1";
        //        }
        //        enum "pseudo-2e6" {
        //          description "Pattern is 2^6 - 1";
        //        }
        //        enum "pseudo-2e7" {
        //          description "Pattern is 2^7 - 1";
        //        }
        //        enum "pseudo-2e9-o153" {
        //          description "Pattern is 2^9 - 1 (per O.153 standard)";
        //        }
        //        enum "pseudo-2e10" {
        //          description "Pattern is 2^10 - 1";
        //        }
        //        enum "pseudo-2e11-o152" {
        //          description "Pattern is 2^11 -1 (per O.152 standard)";
        //        }
        //        enum "pseudo-2e15-o151" {
        //          description "Pattern is 2^15 - 1 (per O.151 standard)";
        //        }
        //        enum "pseudo-2e17" {
        //          description "Pattern is 2^17 - 1";
        //        }
        //        enum "pseudo-2e18" {
        //          description "Pattern is 2^18 - 1";
        //        }
        //        enum "pseudo-2e20-o153" {
        //          description "Pattern is 2^20 - 1 (per O.153 standard)";
        //        }
        //        enum "pseudo-2e20-o151" {
        //          description "Pattern is 2^20 - 1 (per O.151 standard)";
        //        }
        //        enum "pseudo-2e21" {
        //          description "Pattern is 2^21 - 1";
        //        }
        //        enum "pseudo-2e22" {
        //          description "Pattern is 2^22 - 1";
        //        }
        //        enum "pseudo-2e23-o151" {
        //          description "Pattern is 2^23 (per O.151 standard)";
        //        }
        //        enum "pseudo-2e25" {
        //          description "Pattern is 2^25 - 1";
        //        }
        //        enum "pseudo-2e28" {
        //          description "Pattern is 2^28 - 1";
        //        }
        //        enum "pseudo-2e29" {
        //          description "Pattern is 2^29 - 1";
        //        }
        //        enum "pseudo-2e31" {
        //          description "Pattern is 2^31 - 1";
        //        }
        //        enum "pseudo-2e32" {
        //          description "Pattern is 2^32 - 1";
        //        }
        //        enum "all-ones-repeating" {
        //          description "Repeating one bits";
        //        }
        //        enum "all-zeros-repeating" {
        //          description "Repeating zero bits";
        //        }
        //        enum "alternating-ones-zeros" {
        //          description "Alternating ones and zeros";
        //        }
        //        enum "alternating-double-ones-zeros" {
        //          description "Alternating pairs of ones and zeros";
        //        }
        //        enum "repeating-3-in-24" {
        //          description "3 bits in 24 are set";
        //        }
        //        enum "repeating-1-in-8" {
        //          description "1 bit in 8 is set";
        //        }
        //        enum "repeating-1-in-4" {
        //          description "1 bit in 4 is set";
        //        }
        //      }
        //    }
        //    leaf bert-error-rate {
        //      description "Bit error rate (10^-n for n > 0, and zero for n = 0)";
        //      type union {
        //        type string {
        //          pattern "<.*>|$.*";
        //        }
        //        type uint32 {
        //          range "0 .. 7";
        //        }
        //      }
        //    }
        //    leaf bert-period {
        //      description "Length of BERT test";
        //      units "seconds";
        //      type union {
        //        type string {
        //          pattern "<.*>|$.*";
        //        }
        //        type uint32 {
        //          range "1 .. 86400";
        //        }
        //      }
        //    }
        //    leaf remote-loopback-respond {
        //      description "Respond to loop requests from remote end";
        //      type empty;
        //    }
        //    leaf crc-major-alarm-threshold {
        //      description "CRC Major alarm threshold value";
        //      default "5e-5";
        //      type enumeration {
        //        enum "1e-3" {
        //          description "1 crc error in 10^3 bits";
        //        }
        //        enum "5e-4" {
        //          description "5 crc errors in 10^4 bits";
        //        }
        //        enum "1e-4" {
        //          description "1 crc error in 10^4 bits";
        //        }
        //        enum "5e-5" {
        //          description "5 crc errors in 10^5 bits";
        //        }
        //        enum "1e-5" {
        //          description "1 crc error in 10^5 bits";
        //        }
        //      }
        //    }
        //    leaf crc-minor-alarm-threshold {
        //      description "CRC Minor alarm threshold value";
        //      default "5e-6";
        //      type enumeration {
        //        enum "1e-3" {
        //          description "1 crc error in 10^3 bits";
        //        }
        //        enum "5e-4" {
        //          description "5 crc errors in 10^4 bits";
        //        }
        //        enum "1e-4" {
        //          description "1 crc error in 10^4 bits";
        //        }
        //        enum "5e-5" {
        //          description "5 crc errors in 10^5 bits";
        //        }
        //        enum "1e-5" {
        //          description "1 crc error in 10^5 bits";
        //        }
        //        enum "5e-6" {
        //          description "5 crc errors in 10^6 bits";
        //        }
        //        enum "1e-6" {
        //          description "1 crc error in 10^6 bits";
        //        }
        //      }
        //    }
        //  }
        //  container ds0-options {
        //    description "DS-0 interface-specific options";
        //    // uses apply-advanced;
        //    leaf loopback {
        //      description "Loopback mode";
        //      type enumeration {
        //        enum "payload" {
        //          description "Payload loopback";
        //        }
        //      }
        //    }
        //    leaf byte-encoding {
        //      description "Byte encoding";
        //      type enumeration {
        //        enum "nx64" {
        //          description "8 bits per byte";
        //        }
        //        enum "nx56" {
        //          description "7 bits per byte";
        //        }
        //      }
        //    }
        //    leaf invert-data {
        //      description "Invert data";
        //      type empty;
        //    }
        //    leaf fcs {
        //      description "Frame checksum";
        //      type enumeration {
        //        enum "32" {
        //          description "32-bit mode";
        //        }
        //        enum "16" {
        //          description "16-bit mode";
        //        }
        //      }
        //    }
        //    leaf idle-cycle-flag {
        //      description "Value to transmit in idle cycles";
        //      type enumeration {
        //        enum "flags" {
        //          description "Transmit 0x7E in idle cycles";
        //        }
        //        enum "ones" {
        //          description "Transmit 0xFF (all ones) in idle cycles";
        //        }
        //      }
        //    }
        //    leaf start-end-flag {
        //      description "Set start/end flags on transmission";
        //      type enumeration {
        //        enum "shared" {
        //          description "Share start/end flags on transmit";
        //        }
        //        enum "filler" {
        //          description "Send two idle cycles between start/end flags";
        //        }
        //      }
        //    }
        //    leaf bert-algorithm {
        //      description "Set BERT algorithm";
        //      type enumeration {
        //        enum "pseudo-2e11-o152" {
        //          description "Pattern is 2^11 -1 (per O.152 standard)";
        //        }
        //        enum "pseudo-2e15-o151" {
        //          description "Pattern is 2^15 - 1 (per O.151 standard)";
        //        }
        //        enum "pseudo-2e20-o153" {
        //          description "Pattern is 2^20 - 1 (per O.153 standard)";
        //        }
        //        enum "pseudo-2e20-o151" {
        //          description "Pattern is 2^20 - 1 (per O.151 standard)";
        //        }
        //        enum "all-ones-repeating" {
        //          description "Repeating one bits";
        //        }
        //        enum "all-zeros-repeating" {
        //          description "Repeating zero bits";
        //        }
        //        enum "alternating-ones-zeros" {
        //          description "Alternating ones and zeros";
        //        }
        //        enum "alternating-double-ones-zeros" {
        //          description "Alternating pairs of ones and zeros";
        //        }
        //        enum "repeating-3-in-24" {
        //          description "3 bits in 24 are set";
        //        }
        //        enum "repeating-1-in-8" {
        //          description "1 bit in 8 is set";
        //        }
        //        enum "repeating-1-in-4" {
        //          description "1 bit in 4 is set";
        //        }
        //        enum "repeating-1-in-16" {
        //          description "1 bit in 16 is set";
        //        }
        //      }
        //    }
        //    leaf bert-error-rate {
        //      description "Bit error rate (10^-n for n > 0, and zero for n = 0)";
        //      type union {
        //        type string {
        //          pattern "<.*>|$.*";
        //        }
        //        type uint32 {
        //          range "0 .. 7";
        //        }
        //      }
        //    }
        //    leaf bert-period {
        //      description "Length of BERT test";
        //      units "seconds";
        //      type union {
        //        type string {
        //          pattern "<.*>|$.*";
        //        }
        //        type uint32 {
        //          range "1 .. 240";
        //        }
        //      }
        //    }
        //  }
        //  container serial-options {
        //    description "Serial interface-specific options";
        //    // uses apply-advanced;
        //    leaf line-protocol {
        //      description "Line protocol to be used";
        //      default "eia530";
        //      type enumeration {
        //        enum "eia530" {
        //          description "Line protocol EIA530";
        //        }
        //        enum "v.35" {
        //          description "Line protocol V.35";
        //        }
        //        enum "x.21" {
        //          description "Line protocol X.21";
        //        }
        //      }
        //    }
        //    choice control_leads_choice {
        //      case case_1 {
        //        container dte-options {
        //          description "DTE options/control leads";
        //          // uses apply-advanced;
        //          leaf ignore-all {
        //            description "Ignore all control leads";
        //            type empty;
        //          }
        //          container dtr {
        //            description "Data Transmit Ready signal handling";
        //            choice dtr_choices {
        //              case case_1 {
        //                leaf assert {
        //                  description "Assert DTR signal";
        //                  type empty;
        //                }
        //              }
        //              case case_2 {
        //                leaf de-assert {
        //                  description "Deassert DTR signal";
        //                  type empty;
        //                }
        //              }
        //              case case_3 {
        //                leaf normal {
        //                  description "Normal DTR signal";
        //                  type empty;
        //                }
        //              }
        //              case case_4 {
        //                container auto-synchronize {
        //                  presence "enable auto-synchronize";
        //                  description "Normal DTR signal, with autoresynchronization";
        //                  // uses apply-advanced;
        //                  leaf duration {
        //                    description "Duration of autoresynchronization";
        //                    units "milliseconds";
        //                    type union {
        //                      type string {
        //                        pattern "<.*>|$.*";
        //                      }
        //                      type uint16 {
        //                        range "1 .. 1000";
        //                      }
        //                    }
        //                  }
        //                  leaf interval {
        //                    description "Interval for autoresynchronization";
        //                    units "seconds";
        //                    type union {
        //                      type string {
        //                        pattern "<.*>|$.*";
        //                      }
        //                      type uint16 {
        //                        range "1 .. 31";
        //                      }
        //                    }
        //                  }
        //                }
        //              }
        //            }
        //          }
        //          leaf control-signal {
        //            description "X.21 control signal handling";
        //            type enumeration {
        //              enum "assert" {
        //                description "Assert control signal";
        //              }
        //              enum "de-assert" {
        //                description "Deassert control signal";
        //              }
        //              enum "normal" {
        //                description "Normal control signal";
        //              }
        //            }
        //          }
        //          leaf rts {
        //            description "Request To Send signal handling";
        //            type enumeration {
        //              enum "assert" {
        //                description "Assert RTS signal";
        //              }
        //              enum "de-assert" {
        //                description "Deassert RTS signal";
        //              }
        //              enum "normal" {
        //                description "Normal RTS signal";
        //              }
        //            }
        //          }
        //          leaf dcd {
        //            description "Data Carrier Detect signal handling";
        //            type enumeration {
        //              enum "require" {
        //                description "Require DCD signal";
        //              }
        //              enum "ignore" {
        //                description "Ignore DCD signal";
        //              }
        //              enum "normal" {
        //                description "Normal DCD signal";
        //              }
        //            }
        //          }
        //          leaf dsr {
        //            description "Data Set Ready signal handling";
        //            type enumeration {
        //              enum "require" {
        //                description "Require DSR signal";
        //              }
        //              enum "ignore" {
        //                description "Ignore DSR signal";
        //              }
        //              enum "normal" {
        //                description "Normal DSR signal";
        //              }
        //            }
        //          }
        //          leaf cts {
        //            description "Clear To Send signal handling";
        //            type enumeration {
        //              enum "require" {
        //                description "Require CTS signal";
        //              }
        //              enum "ignore" {
        //                description "Ignore CTS signal";
        //              }
        //              enum "normal" {
        //                description "Normal CTS signal";
        //              }
        //            }
        //          }
        //          leaf indication {
        //            description "X.21 Indication signal handling";
        //            type enumeration {
        //              enum "require" {
        //                description "Require Indication signal";
        //              }
        //              enum "ignore" {
        //                description "Ignore Indication signal";
        //              }
        //              enum "normal" {
        //                description "Normal Indication signal";
        //              }
        //            }
        //          }
        //          leaf tm {
        //            description "Test Mode signal handling";
        //            type enumeration {
        //              enum "require" {
        //                description "Require TM signal";
        //              }
        //              enum "ignore" {
        //                description "Ignore TM signal";
        //              }
        //              enum "normal" {
        //                description "Normal TM signal";
        //              }
        //            }
        //          }
        //        }
        //      }
        //      case case_2 {
        //        container dce-options {
        //          description "DCE options";
        //          // uses apply-advanced;
        //          leaf ignore-all {
        //            description "Ignore all control leads";
        //            type empty;
        //          }
        //          leaf dtr {
        //            description "Data Transmit Ready signal handling";
        //            type enumeration {
        //              enum "require" {
        //                description "Require Data Carrier Detect (DCD) signal";
        //              }
        //              enum "ignore" {
        //                description "Ignore Data Carrier Detect (DCD) signal";
        //              }
        //              enum "normal" {
        //                description "Normal Data Carrier Detect (DCD) signal";
        //              }
        //            }
        //          }
        //          leaf rts {
        //            description "Request To Send signal handling";
        //            type enumeration {
        //              enum "require" {
        //                description "Require Data Carrier Detect (DCD) signal";
        //              }
        //              enum "ignore" {
        //                description "Ignore Data Carrier Detect (DCD) signal";
        //              }
        //              enum "normal" {
        //                description "Normal Data Carrier Detect (DCD) signal";
        //              }
        //            }
        //          }
        //          leaf dcd {
        //            description "Data Carrier Detect signal handling";
        //            type enumeration {
        //              enum "assert" {
        //                description "Assert Request To Send (RTS) signal";
        //              }
        //              enum "de-assert" {
        //                description "Deassert Request To Send (RTS) signal";
        //              }
        //              enum "normal" {
        //                description "Normal Request To Send (RTS) signal";
        //              }
        //            }
        //          }
        //          leaf dsr {
        //            description "Data Set Ready signal handling";
        //            type enumeration {
        //              enum "assert" {
        //                description "Assert Request To Send (RTS) signal";
        //              }
        //              enum "de-assert" {
        //                description "Deassert Request To Send (RTS) signal";
        //              }
        //              enum "normal" {
        //                description "Normal Request To Send (RTS) signal";
        //              }
        //            }
        //          }
        //          leaf cts {
        //            description "Clear To Send signal handling";
        //            type enumeration {
        //              enum "assert" {
        //                description "Assert Request To Send (RTS) signal";
        //              }
        //              enum "de-assert" {
        //                description "Deassert Request To Send (RTS) signal";
        //              }
        //              enum "normal" {
        //                description "Normal Request To Send (RTS) signal";
        //              }
        //            }
        //          }
        //          leaf tm {
        //            description "Test Mode signal handling";
        //            type enumeration {
        //              enum "require" {
        //                description "Require TM signal";
        //              }
        //              enum "ignore" {
        //                description "Ignore TM signal";
        //              }
        //              enum "normal" {
        //                description "Normal TM signal";
        //              }
        //            }
        //          }
        //          leaf dce-loopback-override {
        //            description "DCE loopback override";
        //            type empty;
        //          }
        //        }
        //      }
        //    }
        //    leaf dtr-circuit {
        //      description "Data Transmit Ready circuit mode";
        //      type enumeration {
        //        enum "balanced" {
        //          description "Balanced signal";
        //        }
        //        enum "unbalanced" {
        //          description "Unbalanced signal";
        //        }
        //      }
        //    }
        //    leaf dtr-polarity {
        //      description "Data Transmit Ready signal polarity";
        //      type enumeration {
        //        enum "positive" {
        //          description "Positive polarity";
        //        }
        //        enum "negative" {
        //          description "Negative polarity";
        //        }
        //      }
        //    }
        //    leaf rts-polarity {
        //      description "Request To Send signal polarity";
        //      type enumeration {
        //        enum "positive" {
        //          description "Positive polarity";
        //        }
        //        enum "negative" {
        //          description "Negative polarity";
        //        }
        //      }
        //    }
        //    leaf control-polarity {
        //      description "X.21 Control signal polarity";
        //      type enumeration {
        //        enum "positive" {
        //          description "Positive polarity";
        //        }
        //        enum "negative" {
        //          description "Negative polarity";
        //        }
        //      }
        //    }
        //    leaf dcd-polarity {
        //      description "Data Carrier Detect signal polarity";
        //      type enumeration {
        //        enum "positive" {
        //          description "Positive polarity";
        //        }
        //        enum "negative" {
        //          description "Negative polarity";
        //        }
        //      }
        //    }
        //    leaf dsr-polarity {
        //      description "Data Set Ready signal polarity";
        //      type enumeration {
        //        enum "positive" {
        //          description "Positive polarity";
        //        }
        //        enum "negative" {
        //          description "Negative polarity";
        //        }
        //      }
        //    }
        //    leaf cts-polarity {
        //      description "Clear To Send signal polarity";
        //      type enumeration {
        //        enum "positive" {
        //          description "Positive polarity";
        //        }
        //        enum "negative" {
        //          description "Negative polarity";
        //        }
        //      }
        //    }
        //    leaf indication-polarity {
        //      description "X.21 Indication signal polarity";
        //      type enumeration {
        //        enum "positive" {
        //          description "Positive polarity";
        //        }
        //        enum "negative" {
        //          description "Negative polarity";
        //        }
        //      }
        //    }
        //    leaf tm-polarity {
        //      description "Test Mode signal polarity";
        //      type enumeration {
        //        enum "positive" {
        //          description "Positive polarity";
        //        }
        //        enum "negative" {
        //          description "Negative polarity";
        //        }
        //      }
        //    }
        //    leaf clocking-mode {
        //      description "Clock mode";
        //      type enumeration {
        //        enum "dce" {
        //          description "DCE timing (DTE mode only, not valid for X.21)";
        //        }
        //        enum "internal" {
        //          description "Internal baud timing";
        //        }
        //        enum "loop" {
        //          description "Loop timing";
        //        }
        //      }
        //    }
        //    leaf transmit-clock {
        //      description "Transmit clock phase";
        //      type enumeration {
        //        enum "invert" {
        //          description "Shift clock phase 180 degrees";
        //        }
        //      }
        //    }
        //    leaf clock-rate {
        //      description "Interface clock rate";
        //      type enumeration {
        //        enum "2.048mhz" {
        //          description "2.048 MHz";
        //        }
        //        enum "2.341mhz" {
        //          description "2.341 MHz";
        //        }
        //        enum "2.731mhz" {
        //          description "2.731 MHz";
        //        }
        //        enum "3.277mhz" {
        //          description "3.277 MHz";
        //        }
        //        enum "4.096mhz" {
        //          description "4.096 MHz";
        //        }
        //        enum "5.461mhz" {
        //          description "5.461 MHz";
        //        }
        //        enum "8.192mhz" {
        //          description "8.192 MHz";
        //        }
        //        enum "16.384mhz" {
        //          description "16.384 MHz";
        //        }
        //        enum "1.2khz" {
        //          description "1.2 KHz";
        //        }
        //        enum "2.4khz" {
        //          description "2.4 KHz";
        //        }
        //        enum "9.6khz" {
        //          description "9.6 KHz";
        //        }
        //        enum "19.2khz" {
        //          description "19.2 KHz";
        //        }
        //        enum "38.4khz" {
        //          description "38.4 KHz";
        //        }
        //        enum "56.0khz" {
        //          description "56.0 KHz";
        //        }
        //        enum "64.0khz" {
        //          description "64.0 KHz";
        //        }
        //        enum "72.0khz" {
        //          description "72.0 KHz";
        //        }
        //        enum "125.0khz" {
        //          description "125.0 KHz";
        //        }
        //        enum "148.0khz" {
        //          description "148.0 KHz";
        //        }
        //        enum "250.0khz" {
        //          description "250.0 KHz";
        //        }
        //        enum "500.0khz" {
        //          description "500.0 KHz";
        //        }
        //        enum "800.0khz" {
        //          description "800.0 KHz";
        //        }
        //        enum "1.0mhz" {
        //          description "1.0 MHz";
        //        }
        //        enum "1.3mhz" {
        //          description "1.3 MHz";
        //        }
        //        enum "2.0mhz" {
        //          description "2.0 MHz";
        //        }
        //        enum "4.0mhz" {
        //          description "4.0 MHz";
        //        }
        //        enum "8.0mhz" {
        //          description "8.0 MHz";
        //        }
        //      }
        //    }
        //    leaf loopback {
        //      description "Loopback mode";
        //      type enumeration {
        //        enum "local" {
        //          description "Local loopback";
        //        }
        //        enum "remote" {
        //          description "Remote/LIU loopback";
        //        }
        //        enum "dce-local" {
        //          description "DCE local loopback (DTE mode only)";
        //        }
        //        enum "dce-remote" {
        //          description "DCE remote loopback";
        //        }
        //      }
        //    }
        //    leaf encoding {
        //      description "Line encoding";
        //      type enumeration {
        //        enum "nrz" {
        //          description "Non-Return-To-Zero";
        //        }
        //        enum "nrzi" {
        //          description "Non-Return-To-Zero-Invertible";
        //        }
        //      }
        //    }
        //    leaf idle-cycle-flag {
        //      description "Value to transmit in idle cycles";
        //      type enumeration {
        //        enum "flags" {
        //          description "Transmit 0x7E in idle cycles";
        //        }
        //        enum "ones" {
        //          description "Transmit 0xFF (all ones) in idle cycles";
        //        }
        //      }
        //    }
        //  }
        //  choice gratuitous-arp-reply-choice {
        //    leaf gratuitous-arp-reply {
        //      description "Enable gratuitous ARP reply";
        //      type empty;
        //    }
        //    leaf no-gratuitous-arp-reply {
        //      description "Don't enable gratuitous ARP reply";
        //      type empty;
        //    }
        //  }
        //  choice no-gratuitous-arp-request-choice {
        //    leaf no-gratuitous-arp-request {
        //      description "Ignore gratuitous ARP request";
        //      type empty;
        //    }
        //    leaf no-no-gratuitous-arp-request {
        //      description "Don't ignore gratuitous ARP request";
        //      type empty;
        //    }
        //  }
        //  leaf arp-l2-validate {
        //    description "Validate ARP against L2";
        //    type empty;
        //  }
         container ether-options {
           description "Ethernet interface-specific options";
           // uses apply-advanced;
           choice loopback-choice {
             leaf loopback {
               description "Enable loopback";
               type empty;
             }
             leaf no-loopback {
               description "Don't enable loopback";
               type empty;
             }
           }
           leaf loopback-remote {
             description "Enable remote loopback";
             type empty;
           }
           choice source-filtering-choice {
             leaf source-filtering {
               description "Enable source address filtering";
               type empty;
             }
             leaf no-source-filtering {
               description "Don't enable source address filtering";
               type empty;
             }
           }
           container ethernet-switch-profile {
             description "Ethernet virtual LAN/media access control-level options";
             // uses apply-advanced;
             leaf-list tag-protocol-id {
               ordered-by user;
               description "IEEE 802.1q Tag Protocol Identifier values for VLAN-tagged frames";
               type string;
             }
            //  container ethernet-policer-profile {
            //    description "Ethernet level CoS-based policer configuration";
            //    // uses apply-advanced;
            //    container input-priority-map {
            //      description "Input policer priority map";
            //      uses cos_policer_input_priority_map;
            //    }
            //    container output-priority-map {
            //      description "Output policer priority map";
            //      uses cos_policer_output_priority_map;
            //    }
            //    list policer {
            //      key name;
            //      ordered-by user;
            //      description "Policer template definition";
            //      uses cos_policer;
            //    }
            //  }
            //  container storm-control {
            //    description "Storm control profile name to bind";
            //    // uses apply-advanced;
            //    leaf profile-name {
            //      description "Profile name";
            //      type string;
            //    }
            //  }
            //  container recovery-timeout {
            //    description "Recovery timeout for this interface";
            //    leaf time-in-seconds {
            //      units "seconds";
            //      type union {
            //        type string {
            //          pattern "<.*>|$.*";
            //        }
            //        type uint32 {
            //          range "10 .. 3600";
            //        }
            //      }
            //    }
            //  }
            //  choice mac-learn-enable-choice {
            //    leaf mac-learn-enable {
            //      description "Learn MAC addresses dynamically";
            //      type empty;
            //    }
            //    leaf no-mac-learn-enable {
            //      description "Don't learn MAC addresses dynamically";
            //      type empty;
            //    }
            //  }
           }
           leaf asynchronous-notification {
             description "Enable sending asynchronous notification to peer on CCC-down";
             type empty;
           }
           list source-address-filter {
             key name;
             description "Source address filters";
             leaf name {
               description "Remote MAC address";
               type jt:mac-addr;
             }
           }
           choice auto-negotiation-choice {
             leaf auto-negotiation {
               description "Enable auto-negotiation";
               type empty;
             }
             leaf no-auto-negotiation {
               description "Don't enable auto-negotiation";
               type empty;
             }
           }
           choice flow-control-choice {
             leaf flow-control {
               description "Enable flow control";
               type empty;
             }
             leaf no-flow-control {
               description "Don't enable flow control";
               type empty;
             }
           }
           container configured-flow-control {
             presence "enable configured-flow-control";
             description "Enable flow control";
             // uses apply-advanced;
             leaf rx-buffers {
               description "Enable/Disable Rx buffers";
               type enumeration {
                 enum "on" {
                   description "Enable Rx buffers";
                 }
                 enum "off" {
                   description "Disable Rx buffers";
                 }
               }
             }
             leaf tx-buffers {
               description "Enable/Disable Tx buffers";
               type enumeration {
                 enum "on" {
                   description "Enable Tx buffers";
                 }
                 enum "off" {
                   description "Disable Tx buffers";
                 }
               }
             }
           }
           leaf link-mode {
             description "Link duplex";
             type enumeration {
               enum "automatic" {
                 description "Automatic negotiate duplex ";
               }
               enum "half-duplex" {
                 description "Half-duplex operation";
               }
               enum "full-duplex" {
                 description "Full-duplex operation";
               }
             }
           }
           container mpls {
             description "MPLS options";
             uses mpls_ifd_options;
           }
           leaf ignore-l3-incompletes {
             description "Ignore L3 incomplete errors";
             type empty;
           }
           leaf no-auto-mdix {
             description "Disable auto MDI/MDIX";
             type empty;
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
             }
           }
           container speed {
             description "Specify speed";
             choice automatic {
               case case_1 {
                 container auto-negotiation {
                   presence "enable auto-negotiation";
                   description "Enable auto-negotiation";
                   leaf auto-negotiate-10-100 {
                     description "Limits the auto-negotiation to 10m/100m only";
                     type empty;
                   }
                 }
               }
               case case_2 {
                 leaf ethernet-10m {
                   description "10Mbps";
                   type empty;
                 }
               }
               case case_3 {
                 leaf ethernet-100m {
                   description "100Mbps";
                   type empty;
                 }
               }
               case case_4 {
                 leaf ethernet-1g {
                   description "1Gbps";
                   type empty;
                 }
               }
               case case_5 {
                 leaf ethernet-10g {
                   description "10Gbps";
                   type empty;
                 }
               }
             }
           }
           container ieee-802.3ad {
             description "IEEE 802.3ad";
             // uses apply-advanced;
             container lacp {
               description "Link Aggregation Control Protocol configuration";
               // uses apply-advanced;
               leaf force-up {
                 description "Keep the port up in absence of received LACPDU";
                 type empty;
               }
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
             container link-protection-sub-group {
               description "Link Protection subgroup configuration";
               // uses apply-advanced;
               leaf subgroup-name {
                 description "Name of the subgroup";
                 type string {
                   length "2 .. 64";
                 }
               }
             }
             leaf port-priority {
               description "Link protection Priority of the port (0 ... 65535)";
               type union {
                 type uint16;
                 type string {
                   pattern "<.*>|$.*";
                 }
               }
             }
           }
           leaf ieee-802-3az-eee {
             description "IEEE 802.3az Energy Efficient Ethernet(EEE)";
             type empty;
           }
           container redundant-parent {
             description " Parent of this interface";
             // uses apply-advanced;
             leaf parent {
               description "Join a redundant ethernet interface";
               type union {
                 type jt:interface-device;
                 type string {
                   pattern "<.*>|$.*";
                 }
               }
             }
           }
           leaf autostate-exclude {
             description "Interface will not contribute to IRB state";
             type empty;
           }
         }
        //  container fibrechannel-options {
        //    description "Fibre Channel interface-specific options";
        //    // uses apply-advanced;
        //    choice loopback-choice {
        //      leaf loopback {
        //        description "Enable loopback";
        //        type empty;
        //      }
        //      leaf no-loopback {
        //        description "Don't enable loopback";
        //        type empty;
        //      }
        //    }
        //    leaf bb-sc-n {
        //      description "B2B state change number";
        //      type union {
        //        type string {
        //          pattern "<.*>|$.*";
        //        }
        //        type uint16 {
        //          range "0 .. 15";
        //        }
        //      }
        //    }
        //    leaf speed {
        //      description "Specify speed";
        //      type enumeration {
        //        enum "auto-negotiation" {
        //          description "Enable auto-negotiation";
        //        }
        //        enum "1g" {
        //          description "1Gbps";
        //        }
        //        enum "2g" {
        //          description "2Gbps";
        //        }
        //        enum "4g" {
        //          description "4Gbps";
        //        }
        //        enum "8g" {
        //          description "8Gbps";
        //        }
        //      }
        //    }
        //  }
         container gigether-options {
           description "Gigabit Ethernet interface-specific options";
           // uses apply-advanced;
           choice loopback-choice {
             leaf loopback {
               description "Enable loopback";
               type empty;
             }
             leaf no-loopback {
               description "Don't enable loopback";
               type empty;
             }
           }
           leaf loopback-remote {
             description "Enable remote loopback";
             type empty;
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           choice auto_negotiation_option {
             case case_1 {
               leaf no-auto-negotiation {
                 description "Disable auto-negotiation";
                 type empty;
               }
             }
             case case_2 {
               container auto-negotiation {
                 presence "enable auto-negotiation";
                 description "Enable auto-negotiation";
                 leaf remote-fault {
                   type enumeration {
                     enum "local-interface-offline" {
                       description "Disable local interface";
                     }
                     enum "local-interface-online" {
                       description "Enable local interface";
                     }
                   }
                 }
               }
             }
           }
           leaf asynchronous-notification {
             description "Enable sending asynchronous notification to peer on CCC-down";
             type empty;
           }
           list source-address-filter {
             key name;
             description "Source address filters";
             leaf name {
               description "Remote MAC address";
               type jt:mac-addr;
             }
           }
           leaf pad-to-minimum-frame-size {
             description "Pad Tx vlan tagged frame to minimum of 68 bytes";
             type empty;
           }
           container redundant-parent {
             description "Parent of this interface";
             // uses apply-advanced;
             leaf parent {
               description "Join a redundant-ethernet interface";
               type union {
                 type jt:interface-device;
                 type string {
                   pattern "<.*>|$.*";
                 }
               }
             }
           }
           container ieee-802.3ad {
             description "IEEE 802.3ad";
             // uses apply-advanced;
             container lacp {
               description "Link Aggregation Control Protocol configuration";
               // uses apply-advanced;
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             leaf link-index {
               description "Desired child link index within the Aggregated Interface";
               type union {
                 type string {
                   pattern "<.*>|$.*";
                 }
                 type uint16 {
                   range "0 .. 63";
                 }
               }
             }
             choice type {
               case case_1 {
                 leaf primary {
                   description "Primary interface for link-protection mode";
                   type empty;
                 }
               }
               case case_2 {
                 leaf backup {
                   description "Backup interface for link-protection mode";
                   type empty;
                 }
               }
             }
             leaf distribution-list {
               description "Distribution list to which interface belongs";
               type string {
                 length "1 .. 20";
               }
             }
           }
          //  container ethernet-switch-profile {
          //    description "Ethernet virtual LAN/media access control-level options";
          //    // uses apply-advanced;
          //    leaf-list tag-protocol-id {
          //      ordered-by user;
          //      description "IEEE 802.1q Tag Protocol Identifier values for VLAN-tagged frames";
          //      type string;
          //    }
          //    container ethernet-policer-profile {
          //      description "Ethernet level CoS-based policer configuration";
          //      // uses apply-advanced;
          //      container ieee802.1-priority-map {
          //        presence "enable ieee802.1-priority-map";
          //        description "Premium priority values for IEEE 802.1p bits";
          //        status deprecated;
          //        // uses apply-advanced;
          //        leaf-list premium {
          //          ordered-by user;
          //          description "Premium policer priority map";
          //          type union {
          //            type string {
          //              pattern "<.*>|$.*";
          //            }
          //            type uint32 {
          //              range "0 .. 7";
          //            }
          //          }
          //        }
          //      }
          //      container input-priority-map {
          //        description "Input policer priority map";
          //        uses cos_policer_input_priority_map;
          //      }
          //      container output-priority-map {
          //        description "Output policer priority map";
          //        uses cos_policer_output_priority_map;
          //      }
          //      list policer {
          //        key name;
          //        ordered-by user;
          //        description "Policer template definition";
          //        uses cos_policer;
          //      }
          //    }
          //    container accept-from {
          //      description "Accept traffic from or to specified remote MAC";
          //      status deprecated;
          //      // uses apply-advanced;
          //      list mac-address {
          //        key name;
          //        description "Remote MAC";
          //        uses mac_list;
          //      }
          //    }
          //    choice reject-the-rest-choice {
          //      leaf reject-the-rest {
          //        description "Accept traffic from only the specified MAC addresses";
          //        status deprecated;
          //        type empty;
          //      }
          //      leaf no-reject-the-rest {
          //        description "Don't accept traffic from only the specified MAC addresses";
          //        status deprecated;
          //        type empty;
          //      }
          //    }
          //    leaf mac-learn-enable {
          //      description "Learn MAC addresses dynamically";
          //      type empty;
          //    }
          //  }
           container mpls {
             description "MPLS options";
             uses mpls_ifd_options;
           }
           leaf ignore-l3-incompletes {
             description "Ignore L3 incomplete errors";
             type empty;
           }
          //  leaf no-auto-mdix {
          //    description "Disable auto MDI/MDIX";
          //    type empty;
          //  }
          //  leaf ieee-802-3az-eee {
          //    description "IEEE 802.3az Energy Efficient Ethernet(EEE)";
          //    type empty;
          //  }
           leaf mru {
             description "Maximum receive packet size";
             type union {
               type string {
                 pattern "<.*>|$.*";
               }
               type uint32;
             }
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
             }
           }
           leaf speed {
             description "Speed mode";
             type enumeration {
               enum "1g" {
                 description "Speed 1g";
               }
               enum "10g" {
                 description "Speed 10g";
               }
             }
           }
         }
        //  container optics-options {
        //    description "Optics options";
        //    // uses apply-advanced;
        //    leaf wavelength {
        //      description "Wavelength of the optics (nanometers) for 50Ghz/100Ghz spacing";
        //      type enumeration {
        //        enum "1568.77" {
        //          description "1568.77 nm/191.1003 THz 50/100Ghz spacing";
        //        }
        //        enum "1568.36" {
        //          description "1568.36 nm/191.15000 THz 6.25/12.5/50GHz spacing";
        //        }
        //        enum "1568.31" {
        //          description "1568.31 nm/191.15625 THz 6.25GHz spacing";
        //        }
        //        enum "1568.26" {
        //          description "1568.26 nm/191.16250 THz 6.25/12.5GHz spacing";
        //        }
        //        enum "1568.21" {
        //          description "1568.21 nm/191.16875 THz 6.25GHz spacing";
        //        }
        //        enum "1568.16" {
        //          description "1568.16 nm/191.17500 THz 6.25/12.5GHz spacing";
        //        }
        //        enum "1568.11" {
        //          description "1568.11 nm/191.18125 THz 6.25GHz spacing";
        //        }
        //        enum "1568.05" {
        //          description "1568.05 nm/191.18750 THz 6.25/12.5GHz spacing";
        //        }
        //        enum "1568.00" {
        //          description "1568.00 nm/191.19375 THz 6.25GHz spacing";
        //        }
        //        enum "1567.95" {
        //          description "1567.95 nm/191.20000 THz 6.25/12.5/50/100GHz spacing";
        //        }
        //        enum "1567.90" {
        //          description "1567.90 nm/191.20625 THz 6.25GHz spacing";
        //        }
        //        enum "1567.85" {
        //          description "1567.85 nm/191.21250 THz 6.25/12.5GHz spacing";
        //        }
        //        enum "1567.80" {
        //          description "1567.80 nm/191.21875 THz 6.25GHz spacing";
        //        }
        //        enum "1567.75" {
        //          description "1567.75 nm/191.22500 THz 6.25/12.5GHz spacing";
        //        }
        //        enum "1567.70" {
        //          description "1567.70 nm/191.23125 THz 6.25GHz spacing";
        //        }
        //        enum "1567.64" {
        //          description "1567.64 nm/191.23750 THz 6.25/12.5GHz spacing";
        //        }
        //        enum "1567.59" {
        //          description "1567.59 nm/191.24375 THz 6.25GHz spacing";
        //        }
        //        enum "1567.54" {
        //          description "1567.54 nm/191.25000 THz 6.25/12.5/50GHz spacing";
        //        }
        //        enum "1567.49" {
        //          description "1567.49 nm/191.25625 THz 6.25GHz spacing";
        //        }
        //        enum "1567.44" {
        //          description "1567.44 nm/191.26250 THz 6.25/12.5GHz spacing";
        //        }
        //        enum "1567.39" {
        //          description "1567.39 nm/191.26875 THz 6.25GHz spacing";
        //        }
        //        enum "1567.34" {
        //          description "1567.34 nm/191.27500 THz 6.25/12.5GHz spacing";
        //        }
        //        enum "1567.29" {
        //          description "1567.29 nm/191.28125 THz 6.25GHz spacing";
        //        }
        //        enum "1567.23" {
        //          description "1567.23 nm/191.28750 THz 6.25/12.5GHz spacing";
        //        }
        //        enum "1567.18" {
        //          description "1567.18 nm/191.29375 THz 6.25GHz spacing";
        //        }
        //        enum "1567.13" {
        //          description "1567.13 nm/191.30000 THz 6.25/12.5/50/100GHz spacing";
        //        }
        //        enum "1567.08" {
        //          description "1567.08 nm/191.30625 THz 6.25GHz spacing";
        //        }
        //        enum "1567.03" {
        //          description "1567.03 nm/191.31250 THz 6.25/12.5GHz spacing";
        //        }
        //        enum "1566.98" {
        //          description "1566.98 nm/191.31875 THz 6.25GHz spacing";
        //        }
        //        enum "1566.93" {
        //          description "1566.93 nm/191.32500 THz 6.25/12.5GHz spacing";
        //        }
        //        enum "1566.88" {
        //          description "1566.88 nm/191.33125 THz 6.25GHz spacing";
        //        }
        //        enum "1566.83" {
        //          description "1566.83 nm/191.33750 THz 6.25/12.5GHz spacing";
        //        }
        //        enum "1566.77" {
        //          description "1566.77 nm/191.34375 THz 6.25GHz spacing";
        //        }
        //        enum "1566.72" {
        //          description "1566.72 nm/191.35000 THz 6.25/12.5/50GHz spacing";
        //        }
        //        enum "1566.67" {
        //          description "1566.67 nm/191.35625 THz 6.25GHz spacing";
        //        }
        //        enum "1566.62" {
        //          description "1566.62 nm/191.36250 THz 6.25/12.5GHz spacing";
        //        }
        //        enum "1566.57" {
        //          description "1566.57 nm/191.36875 THz 6.25GHz spacing";
        //        }
        //        enum "1566.52" {
        //          description "1566.52 nm/191.37500 THz 6.25/12.5/75GHz spacing";
        //        }
        //        enum "1566.47" {
        //          description "1566.47 nm/191.38125 THz 6.25GHz spacing";
        //        }
        //        enum "1566.42" {
        //          description "1566.42 nm/191.38750 THz 6.25/12.5GHz spacing";
        //        }
        //        enum "1566.36" {
        //          description "1566.36 nm/191.39375 THz 6.25GHz spacing";
        //        }
        //        enum "1566.31" {
        //          description "1566.31 nm/191.40000 THz 6.25/12.5/50/100GHz spacing";
        //        }
        //        enum "1566.26" {
        //          description "1566.26 nm/191.40625 THz 6.25GHz spacing";
        //        }
        //        enum "1566.21" {
        //          description "1566.21 nm/191.41250 THz 6.25/12.5GHz spacing";
        //        }
        //        enum "1566.16" {
        //          description "1566.16 nm/191.41875 THz 6.25GHz spacing";
        //        }
        //        enum "1566.11" {
        //          description "1566.11 nm/191.42500 THz 6.25/12.5GHz spacing";
        //        }
        //        enum "1566.06" {
        //          description "1566.06 nm/191.43125 THz 6.25GHz spacing";
        //        }
        //        enum "1566.01" {
        //          description "1566.01 nm/191.43750 THz 6.25/12.5GHz spacing";
        //        }
        //        enum "1565.96" {
        //          description "1565.96 nm/191.44375 THz 6.25GHz spacing";
        //        }
        //        enum "1565.90" {
        //          description "1565.90 nm/191.45000 THz 6.25/12.5/50/75GHz spacing";
        //        }
        //        enum "1565.85" {
        //          description "1565.85 nm/191.45625 THz 6.25GHz spacing";
        //        }
        //        enum "1565.80" {
        //          description "1565.80 nm/191.46250 THz 6.25/12.5GHz spacing";
        //        }
        //        enum "1565.75" {
        //          description "1565.75 nm/191.46875 THz 6.25GHz spacing";
        //        }
        //        enum "1565.70" {
        //          description "1565.70 nm/191.47500 THz 6.25/12.5GHz spacing";
        //        }
        //        enum "1565.65" {
        //          description "1565.65 nm/191.48125 THz 6.25GHz spacing";
        //        }
        //        enum "1565.60" {
        //          description "1565.60 nm/191.48750 THz 6.25/12.5GHz spacing";
        //        }
        //        enum "1565.55" {
        //          description "1565.55 nm/191.49375 THz 6.25GHz spacing";
        //        }
        //        enum "1565.50" {
        //          description "1565.50 nm/191.50000 THz 6.25/12.5/50/100GHz spacing";
        //        }
        //        enum "1565.44" {
        //          description "1565.44 nm/191.50625 THz 6.25GHz spacing";
        //        }
        //        enum "1565.39" {
        //          description "1565.39 nm/191.51250 THz 6.25/12.5GHz spacing";
        //        }
        //        enum "1565.34" {
        //          description "1565.34 nm/191.51875 THz 6.25GHz spacing";
        //        }
        //        enum "1565.29" {
        //          description "1565.29 nm/191.52500 THz 6.25/12.5/75GHz spacing";
        //        }
        //        enum "1565.24" {
        //          description "1565.24 nm/191.53125 THz 6.25GHz spacing";
        //        }
        //        enum "1565.19" {
        //          description "1565.19 nm/191.53750 THz 6.25/12.5GHz spacing";
        //        }
        //        enum "1565.14" {
        //          description "1565.14 nm/191.54375 THz 6.25GHz spacing";
        //        }
        //        enum "1565.09" {
        //          description "1565.09 nm/191.55000 THz 6.25/12.5/50GHz spacing";
        //        }
        //        enum "1565.04" {
        //          description "1565.04 nm/191.55625 THz 6.25GHz spacing";
        //        }
        //        enum "1564.99" {
        //          description "1564.99 nm/191.56250 THz 6.25/12.5GHz spacing";
        //        }
        //        enum "1564.93" {
        //          description "1564.93 nm/191.56875 THz 6.25GHz spacing";
        //        }
        //        enum "1564.88" {
        //          description "1564.88 nm/191.57500 THz 6.25/12.5GHz spacing";
        //        }
        //        enum "1564.83" {
        //          description "1564.83 nm/191.58125 THz 6.25GHz spacing";
        //        }
        //        enum "1564.78" {
        //          description "1564.78 nm/191.58750 THz 6.25/12.5GHz spacing";
        //        }
        //        enum "1564.73" {
        //          description "1564.73 nm/191.59375 THz 6.25GHz spacing";
        //        }
        //        enum "1564.68" {
        //          description "1564.68 nm/191.60000 THz 6.25/12.5/50/75/100GHz spacing";
        //        }
        //        enum "1564.63" {
        //          description "1564.63 nm/191.60625 THz 6.25GHz spacing";
        //        }
        //        enum "1564.58" {
        //          description "1564.58 nm/191.61250 THz 6.25/12.5GHz spacing";
        //        }
        //        enum "1564.53" {
        //          description "1564.53 nm/191.61875 THz 6.25GHz spacing";
        //        }
        //        enum "1564.47" {
        //          description "1564.47 nm/191.62500 THz 6.25/12.5GHz spacing";
        //        }
        //        enum "1564.42" {
        //          description "1564.42 nm/191.63125 THz 6.25GHz spacing";
        //        }
        //        enum "1564.37" {
        //          description "1564.37 nm/191.63750 THz 6.25/12.5GHz spacing";
        //        }
        //        enum "1564.32" {
        //          description "1564.32 nm/191.64375 THz 6.25GHz spacing";
        //        }
        //        enum "1564.27" {
        //          description "1564.27 nm/191.65000 THz 6.25/12.5/50GHz spacing";
        //        }
        //        enum "1564.22" {
        //          description "1564.22 nm/191.65625 THz 6.25GHz spacing";
        //        }
        //        enum "1564.17" {
        //          description "1564.17 nm/191.66250 THz 6.25/12.5GHz spacing";
        //        }
        //        enum "1564.12" {
        //          description "1564.12 nm/191.66875 THz 6.25GHz spacing";
        //        }
        //        enum "1564.07" {
        //          description "1564.07 nm/191.67500 THz 6.25/12.5/75GHz spacing";
        //        }
        //        enum "1564.02" {
        //          description "1564.02 nm/191.68125 THz 6.25GHz spacing";
        //        }
        //        enum "1563.96" {
        //          description "1563.96 nm/191.68750 THz 6.25/12.5GHz spacing";
        //        }
        //        enum "1563.91" {
        //          description "1563.91 nm/191.69375 THz 6.25GHz spacing";
        //        }
        //        enum "1563.86" {
        //          description "1563.86 nm/191.70000 THz 6.25/12.5/50/100GHz spacing";
        //        }
        //        enum "1563.81" {
        //          description "1563.81 nm/191.70625 THz 6.25GHz spacing";
        //        }
        //        enum "1563.76" {
        //          description "1563.76 nm/191.71250 THz 6.25/12.5GHz spacing";
        //        }
        //        enum "1563.71" {
        //          description "1563.71 nm/191.71875 THz 6.25GHz spacing";
        //        }
        //        enum "1563.66" {
        //          description "1563.66 nm/191.72500 THz 6.25/12.5GHz spacing";
        //        }
        //        enum "1563.61" {
        //          description "1563.61 nm/191.73125 THz 6.25GHz spacing";
        //        }
        //        enum "1563.56" {
        //          description "1563.56 nm/191.73750 THz 6.25/12.5GHz spacing";
        //        }
        //        enum "1563.51" {
        //          description "1563.51 nm/191.74375 THz 6.25GHz spacing";
        //        }
        //        enum "1563.45" {
        //          description "1563.45 nm/191.75000 THz 6.25/12.5/50/75GHz spacing";
        //        }
        //        enum "1563.40" {
        //          description "1563.40 nm/191.75625 THz 6.25GHz spacing";
        //        }
        //        enum "1563.35" {
        //          description "1563.35 nm/191.76250 THz 6.25/12.5GHz spacing";
        //        }
        //        enum "1563.30" {
        //          description "1563.30 nm/191.76875 THz 6.25GHz spacing";
        //        }
        //        enum "1563.25" {
        //          description "1563.25 nm/191.77500 THz 6.25/12.5GHz spacing";
        //        }
        //        enum "1563.20" {
        //          description "1563.20 nm/191.78125 THz 6.25GHz spacing";
        //        }
        //        enum "1563.15" {
        //          description "1563.15 nm/191.78750 THz 6.25/12.5GHz spacing";
        //        }
        //        enum "1563.10" {
        //          description "1563.10 nm/191.79375 THz 6.25GHz spacing";
        //        }
        //        enum "1563.05" {
        //          description "1563.05 nm/191.80000 THz 6.25/12.5/50/100GHz spacing";
        //        }
        //        enum "1563.00" {
        //          description "1563.00 nm/191.80625 THz 6.25GHz spacing";
        //        }
        //        enum "1562.95" {
        //          description "1562.95 nm/191.81250 THz 6.25/12.5GHz spacing";
        //        }
        //        enum "1562.89" {
        //          description "1562.89 nm/191.81875 THz 6.25GHz spacing";
        //        }
        //        enum "1562.84" {
        //          description "1562.84 nm/191.82500 THz 6.25/12.5/75GHz spacing";
        //        }
        //        enum "1562.79" {
        //          description "1562.79 nm/191.83125 THz 6.25GHz spacing";
        //        }
        //        enum "1562.74" {
        //          description "1562.74 nm/191.83750 THz 6.25/12.5GHz spacing";
        //        }
        //        enum "1562.69" {
        //          description "1562.69 nm/191.84375 THz 6.25GHz spacing";
        //        }
        //        enum "1562.64" {
        //          description "1562.64 nm/191.85000 THz 6.25/12.5/50GHz spacing";
        //        }
        //        enum "1562.59" {
        //          description "1562.59 nm/191.85625 THz 6.25GHz spacing";
        //        }
        //        enum "1562.54" {
        //          description "1562.54 nm/191.86250 THz 6.25/12.5GHz spacing";
        //        }
        //        enum "1562.49" {
        //          description "1562.49 nm/191.86875 THz 6.25GHz spacing";
        //        }
        //        enum "1562.44" {
        //          description "1562.44 nm/191.87500 THz 6.25/12.5GHz spacing";
        //        }
        //        enum "1562.39" {
        //          description "1562.39 nm/191.88125 THz 6.25GHz spacing";
        //        }
        //        enum "1562.33" {
        //          description "1562.33 nm/191.88750 THz 6.25/12.5GHz spacing";
        //        }
        //        enum "1562.28" {
        //          description "1562.28 nm/191.89375 THz 6.25GHz spacing";
        //        }
        //        enum "1562.23" {
        //          description "1562.23 nm/191.90000 THz 6.25/12.5/50/75/100GHz spacing";
        //        }
        //        enum "1562.18" {
        //          description "1562.18 nm/191.90625 THz 6.25GHz spacing";
        //        }
        //        enum "1562.13" {
        //          description "1562.13 nm/191.91250 THz 6.25/12.5GHz spacing";
        //        }
        //        enum "1562.08" {
        //          description "1562.08 nm/191.91875 THz 6.25GHz spacing";
        //        }
        //        enum "1562.03" {
        //          description "1562.03 nm/191.92500 THz 6.25/12.5GHz spacing";
        //        }
        //        enum "1561.98" {
        //          description "1561.98 nm/191.93125 THz 6.25GHz spacing";
        //        }
        //        enum "1561.93" {
        //          description "1561.93 nm/191.93750 THz 6.25/12.5GHz spacing";
        //        }
        //        enum "1561.88" {
        //          description "1561.88 nm/191.94375 THz 6.25GHz spacing";
        //        }
        //        enum "1561.83" {
        //          description "1561.83 nm/191.95000 THz 6.25/12.5/50GHz spacing";
        //        }
        //        enum "1561.77" {
        //          description "1561.77 nm/191.95625 THz 6.25GHz spacing";
        //        }
        //        enum "1561.72" {
        //          description "1561.72 nm/191.96250 THz 6.25/12.5GHz spacing";
        //        }
        //        enum "1561.67" {
        //          description "1561.67 nm/191.96875 THz 6.25GHz spacing";
        //        }
        //        enum "1561.62" {
        //          description "1561.62 nm/191.97500 THz 6.25/12.5/75GHz spacing";
        //        }
        //        enum "1561.57" {
        //          description "1561.57 nm/191.98125 THz 6.25GHz spacing";
        //        }
        //        enum "1561.52" {
        //          description "1561.52 nm/191.98750 THz 6.25/12.5GHz spacing";
        //        }
        //        enum "1561.47" {
        //          description "1561.47 nm/191.99375 THz 6.25GHz spacing";
        //        }
        //        enum "1561.42" {
        //          description "1561.42 nm/192.00000 THz 6.25/12.5/50/100GHz spacing";
        //        }
        //        enum "1561.37" {
        //          description "1561.37 nm/192.00625 THz 6.25GHz spacing";
        //        }
        //        enum "1561.32" {
        //          description "1561.32 nm/192.01250 THz 6.25/12.5GHz spacing";
        //        }
        //        enum "1561.27" {
        //          description "1561.27 nm/192.01875 THz 6.25GHz spacing";
        //        }
        //        enum "1561.22" {
        //          description "1561.22 nm/192.02500 THz 6.25/12.5GHz spacing";
        //        }
        //        enum "1561.16" {
        //          description "1561.16 nm/192.03125 THz 6.25GHz spacing";
        //        }
        //        enum "1561.11" {
        //          description "1561.11 nm/192.03750 THz 6.25/12.5GHz spacing";
        //        }
        //        enum "1561.06" {
        //          description "1561.06 nm/192.04375 THz 6.25GHz spacing";
        //        }
        //        enum "1561.01" {
        //          description "1561.01 nm/192.05000 THz 6.25/12.5/50G/75Hz spacing";
        //        }
        //        enum "1560.96" {
        //          description "1560.96 nm/192.05625 THz 6.25GHz spacing";
        //        }
        //        enum "1560.91" {
        //          description "1560.91 nm/192.06250 THz 6.25/12.5GHz spacing";
        //        }
        //        enum "1560.86" {
        //          description "1560.86 nm/192.06875 THz 6.25GHz spacing";
        //        }
        //        enum "1560.81" {
        //          description "1560.81 nm/192.07500 THz 6.25/12.5GHz spacing";
        //        }
        //        enum "1560.76" {
        //          description "1560.76 nm/192.08125 THz 6.25GHz spacing";
        //        }
        //        enum "1560.71" {
        //          description "1560.71 nm/192.08750 THz 6.25/12.5GHz spacing";
        //        }
        //        enum "1560.66" {
        //          description "1560.66 nm/192.09375 THz 6.25GHz spacing";
        //        }
        //        enum "1560.61" {
        //          description "1560.61 nm/192.10000 THz 6.25/12.5/50/100GHz spacing";
        //        }
        //        enum "1560.56" {
        //          description "1560.56 nm/192.10625 THz 6.25GHz spacing";
        //        }
        //        enum "1560.50" {
        //          description "1560.50 nm/192.11250 THz 6.25/12.5GHz spacing";
        //        }
        //        enum "1560.45" {
        //          description "1560.45 nm/192.11875 THz 6.25GHz spacing";
        //        }
        //        enum "1560.40" {
        //          description "1560.40 nm/192.12500 THz 6.25/12.5/75GHz spacing";
        //        }
        //        enum "1560.35" {
        //          description "1560.35 nm/192.13125 THz 6.25GHz spacing";
        //        }
        //        enum "1560.30" {
        //          description "1560.30 nm/192.13750 THz 6.25/12.5GHz spacing";
        //        }
        //        enum "1560.25" {
        //          description "1560.25 nm/192.14375 THz 6.25GHz spacing";
        //        }
        //        enum "1560.20" {
        //          description "1560.20 nm/192.15000 THz 6.25/12.5/50GHz spacing";
        //        }
        //        enum "1560.15" {
        //          description "1560.15 nm/192.15625 THz 6.25GHz spacing";
        //        }
        //        enum "1560.10" {
        //          description "1560.10 nm/192.16250 THz 6.25/12.5GHz spacing";
        //        }
        //        enum "1560.05" {
        //          description "1560.05 nm/192.16875 THz 6.25GHz spacing";
        //        }
        //        enum "1560.00" {
        //          description "1560.00 nm/192.17500 THz 6.25/12.5GHz spacing";
        //        }
        //        enum "1559.95" {
        //          description "1559.95 nm/192.18125 THz 6.25GHz spacing";
        //        }
        //        enum "1559.90" {
        //          description "1559.90 nm/192.18750 THz 6.25/12.5GHz spacing";
        //        }
        //        enum "1559.84" {
        //          description "1559.84 nm/192.19375 THz 6.25GHz spacing";
        //        }
        //        enum "1559.79" {
        //          description "1559.79 nm/192.20000 THz 6.25/12.5/50/75/100GHz spacing";
        //        }
        //        enum "1559.74" {
        //          description "1559.74 nm/192.20625 THz 6.25GHz spacing";
        //        }
        //        enum "1559.69" {
        //          description "1559.69 nm/192.21250 THz 6.25/12.5GHz spacing";
        //        }
        //        enum "1559.64" {
        //          description "1559.64 nm/192.21875 THz 6.25GHz spacing";
        //        }
        //        enum "1559.59" {
        //          description "1559.59 nm/192.22500 THz 6.25/12.5GHz spacing";
        //        }
        //        enum "1559.54" {
        //          description "1559.54 nm/192.23125 THz 6.25GHz spacing";
        //        }
        //        enum "1559.49" {
        //          description "1559.49 nm/192.23750 THz 6.25/12.5GHz spacing";
        //        }
        //        enum "1559.44" {
        //          description "1559.44 nm/192.24375 THz 6.25GHz spacing";
        //        }
        //        enum "1559.39" {
        //          description "1559.39 nm/192.25000 THz 6.25/12.5/50GHz spacing";
        //        }
        //        enum "1559.34" {
        //          description "1559.34 nm/192.25625 THz 6.25GHz spacing";
        //        }
        //        enum "1559.29" {
        //          description "1559.29 nm/192.26250 THz 6.25/12.5GHz spacing";
        //        }
        //        enum "1559.24" {
        //          description "1559.24 nm/192.26875 THz 6.25GHz spacing";
        //        }
        //        enum "1559.19" {
        //          description "1559.19 nm/192.27500 THz 6.25/12.5/75GHz spacing";
        //        }
        //        enum "1559.14" {
        //          description "1559.14 nm/192.28125 THz 6.25GHz spacing";
        //        }
        //        enum "1559.08" {
        //          description "1559.08 nm/192.28750 THz 6.25/12.5GHz spacing";
        //        }
        //        enum "1559.03" {
        //          description "1559.03 nm/192.29375 THz 6.25GHz spacing";
        //        }
        //        enum "1558.98" {
        //          description "1558.98 nm/192.30000 THz 6.25/12.5/50/100GHz spacing";
        //        }
        //        enum "1558.93" {
        //          description "1558.93 nm/192.30625 THz 6.25GHz spacing";
        //        }
        //        enum "1558.88" {
        //          description "1558.88 nm/192.31250 THz 6.25/12.5GHz spacing";
        //        }
        //        enum "1558.83" {
        //          description "1558.83 nm/192.31875 THz 6.25GHz spacing";
        //        }
        //        enum "1558.78" {
        //          description "1558.78 nm/192.32500 THz 6.25/12.5GHz spacing";
        //        }
        //        enum "1558.73" {
        //          description "1558.73 nm/192.33125 THz 6.25GHz spacing";
        //        }
        //        enum "1558.68" {
        //          description "1558.68 nm/192.33750 THz 6.25/12.5GHz spacing";
        //        }
        //        enum "1558.63" {
        //          description "1558.63 nm/192.34375 THz 6.25GHz spacing";
        //        }
        //        enum "1558.58" {
        //          description "1558.58 nm/192.35000 THz 6.25/12.5/50/75GHz spacing";
        //        }
        //        enum "1558.53" {
        //          description "1558.53 nm/192.35625 THz 6.25GHz spacing";
        //        }
        //        enum "1558.48" {
        //          description "1558.48 nm/192.36250 THz 6.25/12.5GHz spacing";
        //        }
        //        enum "1558.43" {
        //          description "1558.43 nm/192.36875 THz 6.25GHz spacing";
        //        }
        //        enum "1558.38" {
        //          description "1558.38 nm/192.37500 THz 6.25/12.5GHz spacing";
        //        }
        //        enum "1558.32" {
        //          description "1558.32 nm/192.38125 THz 6.25GHz spacing";
        //        }
        //        enum "1558.27" {
        //          description "1558.27 nm/192.38750 THz 6.25/12.5GHz spacing";
        //        }
        //        enum "1558.22" {
        //          description "1558.22 nm/192.39375 THz 6.25GHz spacing";
        //        }
        //        enum "1558.17" {
        //          description "1558.17 nm/192.40000 THz 6.25/12.5/50/100GHz spacing";
        //        }
        //        enum "1558.12" {
        //          description "1558.12 nm/192.40625 THz 6.25GHz spacing";
        //        }
        //        enum "1558.07" {
        //          description "1558.07 nm/192.41250 THz 6.25/12.5GHz spacing";
        //        }
        //        enum "1558.02" {
        //          description "1558.02 nm/192.41875 THz 6.25GHz spacing";
        //        }
        //        enum "1557.97" {
        //          description "1557.97 nm/192.42500 THz 6.25/12.5/75GHz spacing";
        //        }
        //        enum "1557.92" {
        //          description "1557.92 nm/192.43125 THz 6.25GHz spacing";
        //        }
        //        enum "1557.87" {
        //          description "1557.87 nm/192.43750 THz 6.25/12.5GHz spacing";
        //        }
        //        enum "1557.82" {
        //          description "1557.82 nm/192.44375 THz 6.25GHz spacing";
        //        }
        //        enum "1557.77" {
        //          description "1557.77 nm/192.45000 THz 6.25/12.5/50GHz spacing";
        //        }
        //        enum "1557.72" {
        //          description "1557.72 nm/192.45625 THz 6.25GHz spacing";
        //        }
        //        enum "1557.67" {
        //          description "1557.67 nm/192.46250 THz 6.25/12.5GHz spacing";
        //        }
        //        enum "1557.62" {
        //          description "1557.62 nm/192.46875 THz 6.25GHz spacing";
        //        }
        //        enum "1557.57" {
        //          description "1557.57 nm/192.47500 THz 6.25/12.5GHz spacing";
        //        }
        //        enum "1557.52" {
        //          description "1557.52 nm/192.48125 THz 6.25GHz spacing";
        //        }
        //        enum "1557.46" {
        //          description "1557.46 nm/192.48750 THz 6.25/12.5GHz spacing";
        //        }
        //        enum "1557.41" {
        //          description "1557.41 nm/192.49375 THz 6.25GHz spacing";
        //        }
        //        enum "1557.36" {
        //          description "1557.36 nm/192.50000 THz 6.25/12.5/50/75/100GHz spacing";
        //        }
        //        enum "1557.31" {
        //          description "1557.31 nm/192.50625 THz 6.25GHz spacing";
        //        }
        //        enum "1557.26" {
        //          description "1557.26 nm/192.51250 THz 6.25/12.5GHz spacing";
        //        }
        //        enum "1557.21" {
        //          description "1557.21 nm/192.51875 THz 6.25GHz spacing";
        //        }
        //        enum "1557.16" {
        //          description "1557.16 nm/192.52500 THz 6.25/12.5GHz spacing";
        //        }
        //        enum "1557.11" {
        //          description "1557.11 nm/192.53125 THz 6.25GHz spacing";
        //        }
        //        enum "1557.06" {
        //          description "1557.06 nm/192.53750 THz 6.25/12.5GHz spacing";
        //        }
        //        enum "1557.01" {
        //          description "1557.01 nm/192.54375 THz 6.25GHz spacing";
        //        }
        //        enum "1556.96" {
        //          description "1556.96 nm/192.55000 THz 6.25/12.5/50GHz spacing";
        //        }
        //        enum "1556.91" {
        //          description "1556.91 nm/192.55625 THz 6.25GHz spacing";
        //        }
        //        enum "1556.86" {
        //          description "1556.86 nm/192.56250 THz 6.25/12.5GHz spacing";
        //        }
        //        enum "1556.81" {
        //          description "1556.81 nm/192.56875 THz 6.25GHz spacing";
        //        }
        //        enum "1556.76" {
        //          description "1556.76 nm/192.57500 THz 6.25/12.5/75GHz spacing";
        //        }
        //        enum "1556.71" {
        //          description "1556.71 nm/192.58125 THz 6.25GHz spacing";
        //        }
        //        enum "1556.66" {
        //          description "1556.66 nm/192.58750 THz 6.25/12.5GHz spacing";
        //        }
        //        enum "1556.61" {
        //          description "1556.61 nm/192.59375 THz 6.25GHz spacing";
        //        }
        //        enum "1556.55" {
        //          description "1556.55 nm/192.60000 THz 6.25/12.5/50/100GHz spacing";
        //        }
        //        enum "1556.50" {
        //          description "1556.50 nm/192.60625 THz 6.25GHz spacing";
        //        }
        //        enum "1556.45" {
        //          description "1556.45 nm/192.61250 THz 6.25/12.5GHz spacing";
        //        }
        //        enum "1556.40" {
        //          description "1556.40 nm/192.61875 THz 6.25GHz spacing";
        //        }
        //        enum "1556.35" {
        //          description "1556.35 nm/192.62500 THz 6.25/12.5GHz spacing";
        //        }
        //        enum "1556.30" {
        //          description "1556.30 nm/192.63125 THz 6.25GHz spacing";
        //        }
        //        enum "1556.25" {
        //          description "1556.25 nm/192.63750 THz 6.25/12.5GHz spacing";
        //        }
        //        enum "1556.20" {
        //          description "1556.20 nm/192.64375 THz 6.25GHz spacing";
        //        }
        //        enum "1556.15" {
        //          description "1556.15 nm/192.65000 THz 6.25/12.5/50/75GHz spacing";
        //        }
        //        enum "1556.10" {
        //          description "1556.10 nm/192.65625 THz 6.25GHz spacing";
        //        }
        //        enum "1556.05" {
        //          description "1556.05 nm/192.66250 THz 6.25/12.5GHz spacing";
        //        }
        //        enum "1556.00" {
        //          description "1556.00 nm/192.66875 THz 6.25GHz spacing";
        //        }
        //        enum "1555.95" {
        //          description "1555.95 nm/192.67500 THz 6.25/12.5GHz spacing";
        //        }
        //        enum "1555.90" {
        //          description "1555.90 nm/192.68125 THz 6.25GHz spacing";
        //        }
        //        enum "1555.85" {
        //          description "1555.85 nm/192.68750 THz 6.25/12.5GHz spacing";
        //        }
        //        enum "1555.80" {
        //          description "1555.80 nm/192.69375 THz 6.25GHz spacing";
        //        }
        //        enum "1555.75" {
        //          description "1555.75 nm/192.70000 THz 6.25/12.5/50/100GHz spacing";
        //        }
        //        enum "1555.70" {
        //          description "1555.70 nm/192.70625 THz 6.25GHz spacing";
        //        }
        //        enum "1555.65" {
        //          description "1555.65 nm/192.71250 THz 6.25/12.5GHz spacing";
        //        }
        //        enum "1555.60" {
        //          description "1555.60 nm/192.71875 THz 6.25GHz spacing";
        //        }
        //        enum "1555.55" {
        //          description "1555.55 nm/192.72500 THz 6.25/12.5/75GHz spacing";
        //        }
        //        enum "1555.49" {
        //          description "1555.49 nm/192.73125 THz 6.25GHz spacing";
        //        }
        //        enum "1555.44" {
        //          description "1555.44 nm/192.73750 THz 6.25/12.5GHz spacing";
        //        }
        //        enum "1555.39" {
        //          description "1555.39 nm/192.74375 THz 6.25GHz spacing";
        //        }
        //        enum "1555.34" {
        //          description "1555.34 nm/192.75000 THz 6.25/12.5/50GHz spacing";
        //        }
        //        enum "1555.29" {
        //          description "1555.29 nm/192.75625 THz 6.25GHz spacing";
        //        }
        //        enum "1555.24" {
        //          description "1555.24 nm/192.76250 THz 6.25/12.5GHz spacing";
        //        }
        //        enum "1555.19" {
        //          description "1555.19 nm/192.76875 THz 6.25GHz spacing";
        //        }
        //        enum "1555.14" {
        //          description "1555.14 nm/192.77500 THz 6.25/12.5GHz spacing";
        //        }
        //        enum "1555.09" {
        //          description "1555.09 nm/192.78125 THz 6.25GHz spacing";
        //        }
        //        enum "1555.04" {
        //          description "1555.04 nm/192.78750 THz 6.25/12.5GHz spacing";
        //        }
        //        enum "1554.99" {
        //          description "1554.99 nm/192.79375 THz 6.25GHz spacing";
        //        }
        //        enum "1554.94" {
        //          description "1554.94 nm/192.80000 THz 6.25/12.5/50/75/100GHz spacing";
        //        }
        //        enum "1554.89" {
        //          description "1554.89 nm/192.80625 THz 6.25GHz spacing";
        //        }
        //        enum "1554.84" {
        //          description "1554.84 nm/192.81250 THz 6.25/12.5GHz spacing";
        //        }
        //        enum "1554.79" {
        //          description "1554.79 nm/192.81875 THz 6.25GHz spacing";
        //        }
        //        enum "1554.74" {
        //          description "1554.74 nm/192.82500 THz 6.25/12.5GHz spacing";
        //        }
        //        enum "1554.69" {
        //          description "1554.69 nm/192.83125 THz 6.25GHz spacing";
        //        }
        //        enum "1554.64" {
        //          description "1554.64 nm/192.83750 THz 6.25/12.5GHz spacing";
        //        }
        //        enum "1554.59" {
        //          description "1554.59 nm/192.84375 THz 6.25GHz spacing";
        //        }
        //        enum "1554.54" {
        //          description "1554.54 nm/192.85000 THz 6.25/12.5/50GHz spacing";
        //        }
        //        enum "1554.49" {
        //          description "1554.49 nm/192.85625 THz 6.25GHz spacing";
        //        }
        //        enum "1554.44" {
        //          description "1554.44 nm/192.86250 THz 6.25/12.5GHz spacing";
        //        }
        //        enum "1554.39" {
        //          description "1554.39 nm/192.86875 THz 6.25GHz spacing";
        //        }
        //        enum "1554.34" {
        //          description "1554.34 nm/192.87500 THz 6.25/12.5/75GHz spacing";
        //        }
        //        enum "1554.29" {
        //          description "1554.29 nm/192.88125 THz 6.25GHz spacing";
        //        }
        //        enum "1554.23" {
        //          description "1554.23 nm/192.88750 THz 6.25/12.5GHz spacing";
        //        }
        //        enum "1554.18" {
        //          description "1554.18 nm/192.89375 THz 6.25GHz spacing";
        //        }
        //        enum "1554.13" {
        //          description "1554.13 nm/192.90000 THz 6.25/12.5/50/100GHz spacing";
        //        }
        //        enum "1554.08" {
        //          description "1554.08 nm/192.90625 THz 6.25GHz spacing";
        //        }
        //        enum "1554.03" {
        //          description "1554.03 nm/192.91250 THz 6.25/12.5GHz spacing";
        //        }
        //        enum "1553.98" {
        //          description "1553.98 nm/192.91875 THz 6.25GHz spacing";
        //        }
        //        enum "1553.93" {
        //          description "1553.93 nm/192.92500 THz 6.25/12.5GHz spacing";
        //        }
        //        enum "1553.88" {
        //          description "1553.88 nm/192.93125 THz 6.25GHz spacing";
        //        }
        //        enum "1553.83" {
        //          description "1553.83 nm/192.93750 THz 6.25/12.5GHz spacing";
        //        }
        //        enum "1553.78" {
        //          description "1553.78 nm/192.94375 THz 6.25GHz spacing";
        //        }
        //        enum "1553.73" {
        //          description "1553.73 nm/192.95000 THz 6.25/12.5/50/75GHz spacing";
        //        }
        //        enum "1553.68" {
        //          description "1553.68 nm/192.95625 THz 6.25GHz spacing";
        //        }
        //        enum "1553.63" {
        //          description "1553.63 nm/192.96250 THz 6.25/12.5GHz spacing";
        //        }
        //        enum "1553.58" {
        //          description "1553.58 nm/192.96875 THz 6.25GHz spacing";
        //        }
        //        enum "1553.53" {
        //          description "1553.53 nm/192.97500 THz 6.25/12.5GHz spacing";
        //        }
        //        enum "1553.48" {
        //          description "1553.48 nm/192.98125 THz 6.25GHz spacing";
        //        }
        //        enum "1553.43" {
        //          description "1553.43 nm/192.98750 THz 6.25/12.5GHz spacing";
        //        }
        //        enum "1553.38" {
        //          description "1553.38 nm/192.99375 THz 6.25GHz spacing";
        //        }
        //        enum "1553.33" {
        //          description "1553.33 nm/193.00000 THz 6.25/12.5/50/100GHz spacing";
        //        }
        //        enum "1553.28" {
        //          description "1553.28 nm/193.00625 THz 6.25GHz spacing";
        //        }
        //        enum "1553.23" {
        //          description "1553.23 nm/193.01250 THz 6.25/12.5GHz spacing";
        //        }
        //        enum "1553.18" {
        //          description "1553.18 nm/193.01875 THz 6.25GHz spacing";
        //        }
        //        enum "1553.13" {
        //          description "1553.13 nm/193.02500 THz 6.25/12.5/75GHz spacing";
        //        }
        //        enum "1553.08" {
        //          description "1553.08 nm/193.03125 THz 6.25GHz spacing";
        //        }
        //        enum "1553.03" {
        //          description "1553.03 nm/193.03750 THz 6.25/12.5GHz spacing";
        //        }
        //        enum "1552.98" {
        //          description "1552.98 nm/193.04375 THz 6.25GHz spacing";
        //        }
        //        enum "1552.93" {
        //          description "1552.93 nm/193.05000 THz 6.25/12.5/50GHz spacing";
        //        }
        //        enum "1552.88" {
        //          description "1552.88 nm/193.05625 THz 6.25GHz spacing";
        //        }
        //        enum "1552.83" {
        //          description "1552.83 nm/193.06250 THz 6.25/12.5GHz spacing";
        //        }
        //        enum "1552.78" {
        //          description "1552.78 nm/193.06875 THz 6.25GHz spacing";
        //        }
        //        enum "1552.73" {
        //          description "1552.73 nm/193.07500 THz 6.25/12.5GHz spacing";
        //        }
        //        enum "1552.68" {
        //          description "1552.68 nm/193.08125 THz 6.25GHz spacing";
        //        }
        //        enum "1552.62" {
        //          description "1552.62 nm/193.08750 THz 6.25/12.5GHz spacing";
        //        }
        //        enum "1552.57" {
        //          description "1552.57 nm/193.09375 THz 6.25GHz spacing";
        //        }
        //        enum "1552.52" {
        //          description "1552.52 nm/193.10000 THz 6.25/12.5/50/75/100GHz spacing";
        //        }
        //        enum "1552.47" {
        //          description "1552.47 nm/193.10625 THz 6.25GHz spacing";
        //        }
        //        enum "1552.42" {
        //          description "1552.42 nm/193.11250 THz 6.25/12.5GHz spacing";
        //        }
        //        enum "1552.37" {
        //          description "1552.37 nm/193.11875 THz 6.25GHz spacing";
        //        }
        //        enum "1552.32" {
        //          description "1552.32 nm/193.12500 THz 6.25/12.5GHz spacing";
        //        }
        //        enum "1552.27" {
        //          description "1552.27 nm/193.13125 THz 6.25GHz spacing";
        //        }
        //        enum "1552.22" {
        //          description "1552.22 nm/193.13750 THz 6.25/12.5GHz spacing";
        //        }
        //        enum "1552.17" {
        //          description "1552.17 nm/193.14375 THz 6.25GHz spacing";
        //        }
        //        enum "1552.12" {
        //          description "1552.12 nm/193.15000 THz 6.25/12.5/50GHz spacing";
        //        }
        //        enum "1552.07" {
        //          description "1552.07 nm/193.15625 THz 6.25GHz spacing";
        //        }
        //        enum "1552.02" {
        //          description "1552.02 nm/193.16250 THz 6.25/12.5GHz spacing";
        //        }
        //        enum "1551.97" {
        //          description "1551.97 nm/193.16875 THz 6.25GHz spacing";
        //        }
        //        enum "1551.92" {
        //          description "1551.92 nm/193.17500 THz 6.25/12.5/75GHz spacing";
        //        }
        //        enum "1551.87" {
        //          description "1551.87 nm/193.18125 THz 6.25GHz spacing";
        //        }
        //        enum "1551.82" {
        //          description "1551.82 nm/193.18750 THz 6.25/12.5GHz spacing";
        //        }
        //        enum "1551.77" {
        //          description "1551.77 nm/193.19375 THz 6.25GHz spacing";
        //        }
        //        enum "1551.72" {
        //          description "1551.72 nm/193.20000 THz 6.25/12.5/50/100GHz spacing";
        //        }
        //        enum "1551.67" {
        //          description "1551.67 nm/193.20625 THz 6.25GHz spacing";
        //        }
        //        enum "1551.62" {
        //          description "1551.62 nm/193.21250 THz 6.25/12.5GHz spacing";
        //        }
        //        enum "1551.57" {
        //          description "1551.57 nm/193.21875 THz 6.25GHz spacing";
        //        }
        //        enum "1551.52" {
        //          description "1551.52 nm/193.22500 THz 6.25/12.5GHz spacing";
        //        }
        //        enum "1551.47" {
        //          description "1551.47 nm/193.23125 THz 6.25GHz spacing";
        //        }
        //        enum "1551.42" {
        //          description "1551.42 nm/193.23750 THz 6.25/12.5GHz spacing";
        //        }
        //        enum "1551.37" {
        //          description "1551.37 nm/193.24375 THz 6.25GHz spacing";
        //        }
        //        enum "1551.32" {
        //          description "1551.32 nm/193.25000 THz 6.25/12.5/50/75GHz spacing";
        //        }
        //        enum "1551.27" {
        //          description "1551.27 nm/193.25625 THz 6.25GHz spacing";
        //        }
        //        enum "1551.22" {
        //          description "1551.22 nm/193.26250 THz 6.25/12.5GHz spacing";
        //        }
        //        enum "1551.17" {
        //          description "1551.17 nm/193.26875 THz 6.25GHz spacing";
        //        }
        //        enum "1551.12" {
        //          description "1551.12 nm/193.27500 THz 6.25/12.5GHz spacing";
        //        }
        //        enum "1551.07" {
        //          description "1551.07 nm/193.28125 THz 6.25GHz spacing";
        //        }
        //        enum "1551.02" {
        //          description "1551.02 nm/193.28750 THz 6.25/12.5GHz spacing";
        //        }
        //        enum "1550.97" {
        //          description "1550.97 nm/193.29375 THz 6.25GHz spacing";
        //        }
        //        enum "1550.92" {
        //          description "1550.92 nm/193.30000 THz 6.25/12.5/50/100GHz spacing";
        //        }
        //        enum "1550.87" {
        //          description "1550.87 nm/193.30625 THz 6.25GHz spacing";
        //        }
        //        enum "1550.82" {
        //          description "1550.82 nm/193.31250 THz 6.25/12.5GHz spacing";
        //        }
        //        enum "1550.77" {
        //          description "1550.77 nm/193.31875 THz 6.25GHz spacing";
        //        }
        //        enum "1550.72" {
        //          description "1550.72 nm/193.32500 THz 6.25/12.5/75GHz spacing";
        //        }
        //        enum "1550.67" {
        //          description "1550.67 nm/193.33125 THz 6.25GHz spacing";
        //        }
        //        enum "1550.62" {
        //          description "1550.62 nm/193.33750 THz 6.25/12.5GHz spacing";
        //        }
        //        enum "1550.57" {
        //          description "1550.57 nm/193.34375 THz 6.25GHz spacing";
        //        }
        //        enum "1550.52" {
        //          description "1550.52 nm/193.35000 THz 6.25/12.5/50GHz spacing";
        //        }
        //        enum "1550.47" {
        //          description "1550.47 nm/193.35625 THz 6.25GHz spacing";
        //        }
        //        enum "1550.42" {
        //          description "1550.42 nm/193.36250 THz 6.25/12.5GHz spacing";
        //        }
        //        enum "1550.37" {
        //          description "1550.37 nm/193.36875 THz 6.25GHz spacing";
        //        }
        //        enum "1550.32" {
        //          description "1550.32 nm/193.37500 THz 6.25/12.5GHz spacing";
        //        }
        //        enum "1550.27" {
        //          description "1550.27 nm/193.38125 THz 6.25GHz spacing";
        //        }
        //        enum "1550.22" {
        //          description "1550.22 nm/193.38750 THz 6.25/12.5GHz spacing";
        //        }
        //        enum "1550.17" {
        //          description "1550.17 nm/193.39375 THz 6.25GHz spacing";
        //        }
        //        enum "1550.12" {
        //          description "1550.12 nm/193.40000 THz 6.25/12.5/50/75/100GHz spacing";
        //        }
        //        enum "1550.07" {
        //          description "1550.07 nm/193.40625 THz 6.25GHz spacing";
        //        }
        //        enum "1550.02" {
        //          description "1550.02 nm/193.41250 THz 6.25/12.5GHz spacing";
        //        }
        //        enum "1549.97" {
        //          description "1549.97 nm/193.41875 THz 6.25GHz spacing";
        //        }
        //        enum "1549.92" {
        //          description "1549.92 nm/193.42500 THz 6.25/12.5GHz spacing";
        //        }
        //        enum "1549.87" {
        //          description "1549.87 nm/193.43125 THz 6.25GHz spacing";
        //        }
        //        enum "1549.82" {
        //          description "1549.82 nm/193.43750 THz 6.25/12.5GHz spacing";
        //        }
        //        enum "1549.77" {
        //          description "1549.77 nm/193.44375 THz 6.25GHz spacing";
        //        }
        //        enum "1549.72" {
        //          description "1549.72 nm/193.45000 THz 6.25/12.5/50GHz spacing";
        //        }
        //        enum "1549.67" {
        //          description "1549.67 nm/193.45625 THz 6.25GHz spacing";
        //        }
        //        enum "1549.62" {
        //          description "1549.62 nm/193.46250 THz 6.25/12.5GHz spacing";
        //        }
        //        enum "1549.57" {
        //          description "1549.57 nm/193.46875 THz 6.25GHz spacing";
        //        }
        //        enum "1549.52" {
        //          description "1549.52 nm/193.47500 THz 6.25/12.5/75GHz spacing";
        //        }
        //        enum "1549.47" {
        //          description "1549.47 nm/193.48125 THz 6.25GHz spacing";
        //        }
        //        enum "1549.42" {
        //          description "1549.42 nm/193.48750 THz 6.25/12.5GHz spacing";
        //        }
        //        enum "1549.37" {
        //          description "1549.37 nm/193.49375 THz 6.25GHz spacing";
        //        }
        //        enum "1549.32" {
        //          description "1549.32 nm/193.50000 THz 6.25/12.5/50/100GHz spacing";
        //        }
        //        enum "1549.26" {
        //          description "1549.26 nm/193.50625 THz 6.25GHz spacing";
        //        }
        //        enum "1549.21" {
        //          description "1549.21 nm/193.51250 THz 6.25/12.5GHz spacing";
        //        }
        //        enum "1549.16" {
        //          description "1549.16 nm/193.51875 THz 6.25GHz spacing";
        //        }
        //        enum "1549.11" {
        //          description "1549.11 nm/193.52500 THz 6.25/12.5GHz spacing";
        //        }
        //        enum "1549.06" {
        //          description "1549.06 nm/193.53125 THz 6.25GHz spacing";
        //        }
        //        enum "1549.01" {
        //          description "1549.01 nm/193.53750 THz 6.25/12.5GHz spacing";
        //        }
        //        enum "1548.96" {
        //          description "1548.96 nm/193.54375 THz 6.25GHz spacing";
        //        }
        //        enum "1548.91" {
        //          description "1548.91 nm/193.55000 THz 6.25/12.5/50G/75Hz spacing";
        //        }
        //        enum "1548.86" {
        //          description "1548.86 nm/193.55625 THz 6.25GHz spacing";
        //        }
        //        enum "1548.81" {
        //          description "1548.81 nm/193.56250 THz 6.25/12.5GHz spacing";
        //        }
        //        enum "1548.76" {
        //          description "1548.76 nm/193.56875 THz 6.25GHz spacing";
        //        }
        //        enum "1548.71" {
        //          description "1548.71 nm/193.57500 THz 6.25/12.5GHz spacing";
        //        }
        //        enum "1548.66" {
        //          description "1548.66 nm/193.58125 THz 6.25GHz spacing";
        //        }
        //        enum "1548.61" {
        //          description "1548.61 nm/193.58750 THz 6.25/12.5GHz spacing";
        //        }
        //        enum "1548.56" {
        //          description "1548.56 nm/193.59375 THz 6.25GHz spacing";
        //        }
        //        enum "1548.51" {
        //          description "1548.51 nm/193.60000 THz 6.25/12.5/50/100GHz spacing";
        //        }
        //        enum "1548.46" {
        //          description "1548.46 nm/193.60625 THz 6.25GHz spacing";
        //        }
        //        enum "1548.41" {
        //          description "1548.41 nm/193.61250 THz 6.25/12.5GHz spacing";
        //        }
        //        enum "1548.36" {
        //          description "1548.36 nm/193.61875 THz 6.25GHz spacing";
        //        }
        //        enum "1548.31" {
        //          description "1548.31 nm/193.62500 THz 6.25/12.5/75GHz spacing";
        //        }
        //        enum "1548.26" {
        //          description "1548.26 nm/193.63125 THz 6.25GHz spacing";
        //        }
        //        enum "1548.21" {
        //          description "1548.21 nm/193.63750 THz 6.25/12.5GHz spacing";
        //        }
        //        enum "1548.16" {
        //          description "1548.16 nm/193.64375 THz 6.25GHz spacing";
        //        }
        //        enum "1548.11" {
        //          description "1548.11 nm/193.65000 THz 6.25/12.5/50GHz spacing";
        //        }
        //        enum "1548.06" {
        //          description "1548.06 nm/193.65625 THz 6.25GHz spacing";
        //        }
        //        enum "1548.02" {
        //          description "1548.02 nm/193.66250 THz 6.25/12.5GHz spacing";
        //        }
        //        enum "1547.97" {
        //          description "1547.97 nm/193.66875 THz 6.25GHz spacing";
        //        }
        //        enum "1547.92" {
        //          description "1547.92 nm/193.67500 THz 6.25/12.5GHz spacing";
        //        }
        //        enum "1547.87" {
        //          description "1547.87 nm/193.68125 THz 6.25GHz spacing";
        //        }
        //        enum "1547.82" {
        //          description "1547.82 nm/193.68750 THz 6.25/12.5GHz spacing";
        //        }
        //        enum "1547.77" {
        //          description "1547.77 nm/193.69375 THz 6.25GHz spacing";
        //        }
        //        enum "1547.72" {
        //          description "1547.72 nm/193.70000 THz 6.25/12.5/50/75/100GHz spacing";
        //        }
        //        enum "1547.67" {
        //          description "1547.67 nm/193.70625 THz 6.25GHz spacing";
        //        }
        //        enum "1547.62" {
        //          description "1547.62 nm/193.71250 THz 6.25/12.5GHz spacing";
        //        }
        //        enum "1547.57" {
        //          description "1547.57 nm/193.71875 THz 6.25GHz spacing";
        //        }
        //        enum "1547.52" {
        //          description "1547.52 nm/193.72500 THz 6.25/12.5GHz spacing";
        //        }
        //        enum "1547.47" {
        //          description "1547.47 nm/193.73125 THz 6.25GHz spacing";
        //        }
        //        enum "1547.42" {
        //          description "1547.42 nm/193.73750 THz 6.25/12.5GHz spacing";
        //        }
        //        enum "1547.37" {
        //          description "1547.37 nm/193.74375 THz 6.25GHz spacing";
        //        }
        //        enum "1547.32" {
        //          description "1547.32 nm/193.75000 THz 6.25/12.5/50GHz spacing";
        //        }
        //        enum "1547.27" {
        //          description "1547.27 nm/193.75625 THz 6.25GHz spacing";
        //        }
        //        enum "1547.22" {
        //          description "1547.22 nm/193.76250 THz 6.25/12.5GHz spacing";
        //        }
        //        enum "1547.17" {
        //          description "1547.17 nm/193.76875 THz 6.25GHz spacing";
        //        }
        //        enum "1547.12" {
        //          description "1547.12 nm/193.77500 THz 6.25/12.5/75GHz spacing";
        //        }
        //        enum "1547.07" {
        //          description "1547.07 nm/193.78125 THz 6.25GHz spacing";
        //        }
        //        enum "1547.02" {
        //          description "1547.02 nm/193.78750 THz 6.25/12.5GHz spacing";
        //        }
        //        enum "1546.97" {
        //          description "1546.97 nm/193.79375 THz 6.25GHz spacing";
        //        }
        //        enum "1546.92" {
        //          description "1546.92 nm/193.80000 THz 6.25/12.5/50/100GHz spacing";
        //        }
        //        enum "1546.87" {
        //          description "1546.87 nm/193.80625 THz 6.25GHz spacing";
        //        }
        //        enum "1546.82" {
        //          description "1546.82 nm/193.81250 THz 6.25/12.5GHz spacing";
        //        }
        //        enum "1546.77" {
        //          description "1546.77 nm/193.81875 THz 6.25GHz spacing";
        //        }
        //        enum "1546.72" {
        //          description "1546.72 nm/193.82500 THz 6.25/12.5GHz spacing";
        //        }
        //        enum "1546.67" {
        //          description "1546.67 nm/193.83125 THz 6.25GHz spacing";
        //        }
        //        enum "1546.62" {
        //          description "1546.62 nm/193.83750 THz 6.25/12.5GHz spacing";
        //        }
        //        enum "1546.57" {
        //          description "1546.57 nm/193.84375 THz 6.25GHz spacing";
        //        }
        //        enum "1546.52" {
        //          description "1546.52 nm/193.85000 THz 6.25/12.5/50/75GHz spacing";
        //        }
        //        enum "1546.47" {
        //          description "1546.47 nm/193.85625 THz 6.25GHz spacing";
        //        }
        //        enum "1546.42" {
        //          description "1546.42 nm/193.86250 THz 6.25/12.5GHz spacing";
        //        }
        //        enum "1546.37" {
        //          description "1546.37 nm/193.86875 THz 6.25GHz spacing";
        //        }
        //        enum "1546.32" {
        //          description "1546.32 nm/193.87500 THz 6.25/12.5GHz spacing";
        //        }
        //        enum "1546.27" {
        //          description "1546.27 nm/193.88125 THz 6.25GHz spacing";
        //        }
        //        enum "1546.22" {
        //          description "1546.22 nm/193.88750 THz 6.25/12.5GHz spacing";
        //        }
        //        enum "1546.17" {
        //          description "1546.17 nm/193.89375 THz 6.25GHz spacing";
        //        }
        //        enum "1546.12" {
        //          description "1546.12 nm/193.90000 THz 6.25/12.5/50/100GHz spacing";
        //        }
        //        enum "1546.07" {
        //          description "1546.07 nm/193.90625 THz 6.25GHz spacing";
        //        }
        //        enum "1546.02" {
        //          description "1546.02 nm/193.91250 THz 6.25/12.5GHz spacing";
        //        }
        //        enum "1545.97" {
        //          description "1545.97 nm/193.91875 THz 6.25GHz spacing";
        //        }
        //        enum "1545.92" {
        //          description "1545.92 nm/193.92500 THz 6.25/12.5/75GHz spacing";
        //        }
        //        enum "1545.87" {
        //          description "1545.87 nm/193.93125 THz 6.25GHz spacing";
        //        }
        //        enum "1545.82" {
        //          description "1545.82 nm/193.93750 THz 6.25/12.5GHz spacing";
        //        }
        //        enum "1545.77" {
        //          description "1545.77 nm/193.94375 THz 6.25GHz spacing";
        //        }
        //        enum "1545.72" {
        //          description "1545.72 nm/193.95000 THz 6.25/12.5/50GHz spacing";
        //        }
        //        enum "1545.67" {
        //          description "1545.67 nm/193.95625 THz 6.25GHz spacing";
        //        }
        //        enum "1545.62" {
        //          description "1545.62 nm/193.96250 THz 6.25/12.5GHz spacing";
        //        }
        //        enum "1545.57" {
        //          description "1545.57 nm/193.96875 THz 6.25GHz spacing";
        //        }
        //        enum "1545.52" {
        //          description "1545.52 nm/193.97500 THz 6.25/12.5GHz spacing";
        //        }
        //        enum "1545.47" {
        //          description "1545.47 nm/193.98125 THz 6.25GHz spacing";
        //        }
        //        enum "1545.42" {
        //          description "1545.42 nm/193.98750 THz 6.25/12.5GHz spacing";
        //        }
        //        enum "1545.37" {
        //          description "1545.37 nm/193.99375 THz 6.25GHz spacing";
        //        }
        //        enum "1545.32" {
        //          description "1545.32 nm/194.00000 THz 6.25/12.5/50/75/100GHz spacing";
        //        }
        //        enum "1545.27" {
        //          description "1545.27 nm/194.00625 THz 6.25GHz spacing";
        //        }
        //        enum "1545.22" {
        //          description "1545.22 nm/194.01250 THz 6.25/12.5GHz spacing";
        //        }
        //        enum "1545.17" {
        //          description "1545.17 nm/194.01875 THz 6.25GHz spacing";
        //        }
        //        enum "1545.12" {
        //          description "1545.12 nm/194.02500 THz 6.25/12.5GHz spacing";
        //        }
        //        enum "1545.07" {
        //          description "1545.07 nm/194.03125 THz 6.25GHz spacing";
        //        }
        //        enum "1545.02" {
        //          description "1545.02 nm/194.03750 THz 6.25/12.5GHz spacing";
        //        }
        //        enum "1544.97" {
        //          description "1544.97 nm/194.04375 THz 6.25GHz spacing";
        //        }
        //        enum "1544.92" {
        //          description "1544.92 nm/194.05000 THz 6.25/12.5/50GHz spacing";
        //        }
        //        enum "1544.87" {
        //          description "1544.87 nm/194.05625 THz 6.25GHz spacing";
        //        }
        //        enum "1544.82" {
        //          description "1544.82 nm/194.06250 THz 6.25/12.5GHz spacing";
        //        }
        //        enum "1544.77" {
        //          description "1544.77 nm/194.06875 THz 6.25GHz spacing";
        //        }
        //        enum "1544.72" {
        //          description "1544.72 nm/194.07500 THz 6.25/12.5/75GHz spacing";
        //        }
        //        enum "1544.68" {
        //          description "1544.68 nm/194.08125 THz 6.25GHz spacing";
        //        }
        //        enum "1544.63" {
        //          description "1544.63 nm/194.08750 THz 6.25/12.5GHz spacing";
        //        }
        //        enum "1544.58" {
        //          description "1544.58 nm/194.09375 THz 6.25GHz spacing";
        //        }
        //        enum "1544.53" {
        //          description "1544.53 nm/194.10000 THz 6.25/12.5/50/100GHz spacing";
        //        }
        //        enum "1544.48" {
        //          description "1544.48 nm/194.10625 THz 6.25GHz spacing";
        //        }
        //        enum "1544.43" {
        //          description "1544.43 nm/194.11250 THz 6.25/12.5GHz spacing";
        //        }
        //        enum "1544.38" {
        //          description "1544.38 nm/194.11875 THz 6.25GHz spacing";
        //        }
        //        enum "1544.33" {
        //          description "1544.33 nm/194.12500 THz 6.25/12.5GHz spacing";
        //        }
        //        enum "1544.28" {
        //          description "1544.28 nm/194.13125 THz 6.25GHz spacing";
        //        }
        //        enum "1544.23" {
        //          description "1544.23 nm/194.13750 THz 6.25/12.5GHz spacing";
        //        }
        //        enum "1544.18" {
        //          description "1544.18 nm/194.14375 THz 6.25GHz spacing";
        //        }
        //        enum "1544.13" {
        //          description "1544.13 nm/194.15000 THz 6.25/12.5/50/75GHz spacing";
        //        }
        //        enum "1544.08" {
        //          description "1544.08 nm/194.15625 THz 6.25GHz spacing";
        //        }
        //        enum "1544.03" {
        //          description "1544.03 nm/194.16250 THz 6.25/12.5GHz spacing";
        //        }
        //        enum "1543.98" {
        //          description "1543.98 nm/194.16875 THz 6.25GHz spacing";
        //        }
        //        enum "1543.93" {
        //          description "1543.93 nm/194.17500 THz 6.25/12.5GHz spacing";
        //        }
        //        enum "1543.88" {
        //          description "1543.88 nm/194.18125 THz 6.25GHz spacing";
        //        }
        //        enum "1543.83" {
        //          description "1543.83 nm/194.18750 THz 6.25/12.5GHz spacing";
        //        }
        //        enum "1543.78" {
        //          description "1543.78 nm/194.19375 THz 6.25GHz spacing";
        //        }
        //        enum "1543.73" {
        //          description "1543.73 nm/194.20000 THz 6.25/12.5/50/100GHz spacing";
        //        }
        //        enum "1543.68" {
        //          description "1543.68 nm/194.20625 THz 6.25GHz spacing";
        //        }
        //        enum "1543.63" {
        //          description "1543.63 nm/194.21250 THz 6.25/12.5GHz spacing";
        //        }
        //        enum "1543.58" {
        //          description "1543.58 nm/194.21875 THz 6.25GHz spacing";
        //        }
        //        enum "1543.53" {
        //          description "1543.53 nm/194.22500 THz 6.25/12.5/75GHz spacing";
        //        }
        //        enum "1543.48" {
        //          description "1543.48 nm/194.23125 THz 6.25GHz spacing";
        //        }
        //        enum "1543.43" {
        //          description "1543.43 nm/194.23750 THz 6.25/12.5GHz spacing";
        //        }
        //        enum "1543.38" {
        //          description "1543.38 nm/194.24375 THz 6.25GHz spacing";
        //        }
        //        enum "1543.33" {
        //          description "1543.33 nm/194.25000 THz 6.25/12.5/50GHz spacing";
        //        }
        //        enum "1543.28" {
        //          description "1543.28 nm/194.25625 THz 6.25GHz spacing";
        //        }
        //        enum "1543.23" {
        //          description "1543.23 nm/194.26250 THz 6.25/12.5GHz spacing";
        //        }
        //        enum "1543.18" {
        //          description "1543.18 nm/194.26875 THz 6.25GHz spacing";
        //        }
        //        enum "1543.13" {
        //          description "1543.13 nm/194.27500 THz 6.25/12.5GHz spacing";
        //        }
        //        enum "1543.08" {
        //          description "1543.08 nm/194.28125 THz 6.25GHz spacing";
        //        }
        //        enum "1543.04" {
        //          description "1543.04 nm/194.28750 THz 6.25/12.5GHz spacing";
        //        }
        //        enum "1542.99" {
        //          description "1542.99 nm/194.29375 THz 6.25GHz spacing";
        //        }
        //        enum "1542.94" {
        //          description "1542.94 nm/194.30000 THz 6.25/12.5/50/75/100GHz spacing";
        //        }
        //        enum "1542.89" {
        //          description "1542.89 nm/194.30625 THz 6.25GHz spacing";
        //        }
        //        enum "1542.84" {
        //          description "1542.84 nm/194.31250 THz 6.25/12.5GHz spacing";
        //        }
        //        enum "1542.79" {
        //          description "1542.79 nm/194.31875 THz 6.25GHz spacing";
        //        }
        //        enum "1542.74" {
        //          description "1542.74 nm/194.32500 THz 6.25/12.5GHz spacing";
        //        }
        //        enum "1542.69" {
        //          description "1542.69 nm/194.33125 THz 6.25GHz spacing";
        //        }
        //        enum "1542.64" {
        //          description "1542.64 nm/194.33750 THz 6.25/12.5GHz spacing";
        //        }
        //        enum "1542.59" {
        //          description "1542.59 nm/194.34375 THz 6.25GHz spacing";
        //        }
        //        enum "1542.54" {
        //          description "1542.54 nm/194.35000 THz 6.25/12.5/50GHz spacing";
        //        }
        //        enum "1542.49" {
        //          description "1542.49 nm/194.35625 THz 6.25GHz spacing";
        //        }
        //        enum "1542.44" {
        //          description "1542.44 nm/194.36250 THz 6.25/12.5GHz spacing";
        //        }
        //        enum "1542.39" {
        //          description "1542.39 nm/194.36875 THz 6.25GHz spacing";
        //        }
        //        enum "1542.34" {
        //          description "1542.34 nm/194.37500 THz 6.25/12.5/75GHz spacing";
        //        }
        //        enum "1542.29" {
        //          description "1542.29 nm/194.38125 THz 6.25GHz spacing";
        //        }
        //        enum "1542.24" {
        //          description "1542.24 nm/194.38750 THz 6.25/12.5GHz spacing";
        //        }
        //        enum "1542.19" {
        //          description "1542.19 nm/194.39375 THz 6.25GHz spacing";
        //        }
        //        enum "1542.14" {
        //          description "1542.14 nm/194.40000 THz 6.25/12.5/50/100GHz spacing";
        //        }
        //        enum "1542.09" {
        //          description "1542.09 nm/194.40625 THz 6.25GHz spacing";
        //        }
        //        enum "1542.04" {
        //          description "1542.04 nm/194.41250 THz 6.25/12.5GHz spacing";
        //        }
        //        enum "1541.99" {
        //          description "1541.99 nm/194.41875 THz 6.25GHz spacing";
        //        }
        //        enum "1541.94" {
        //          description "1541.94 nm/194.42500 THz 6.25/12.5GHz spacing";
        //        }
        //        enum "1541.89" {
        //          description "1541.89 nm/194.43125 THz 6.25GHz spacing";
        //        }
        //        enum "1541.84" {
        //          description "1541.84 nm/194.43750 THz 6.25/12.5GHz spacing";
        //        }
        //        enum "1541.80" {
        //          description "1541.80 nm/194.44375 THz 6.25GHz spacing";
        //        }
        //        enum "1541.75" {
        //          description "1541.75 nm/194.45000 THz 6.25/12.5/50/75GHz spacing";
        //        }
        //        enum "1541.70" {
        //          description "1541.70 nm/194.45625 THz 6.25GHz spacing";
        //        }
        //        enum "1541.65" {
        //          description "1541.65 nm/194.46250 THz 6.25/12.5GHz spacing";
        //        }
        //        enum "1541.60" {
        //          description "1541.60 nm/194.46875 THz 6.25GHz spacing";
        //        }
        //        enum "1541.55" {
        //          description "1541.55 nm/194.47500 THz 6.25/12.5GHz spacing";
        //        }
        //        enum "1541.50" {
        //          description "1541.50 nm/194.48125 THz 6.25GHz spacing";
        //        }
        //        enum "1541.45" {
        //          description "1541.45 nm/194.48750 THz 6.25/12.5GHz spacing";
        //        }
        //        enum "1541.40" {
        //          description "1541.40 nm/194.49375 THz 6.25GHz spacing";
        //        }
        //        enum "1541.35" {
        //          description "1541.35 nm/194.50000 THz 6.25/12.5/50/100GHz spacing";
        //        }
        //        enum "1541.30" {
        //          description "1541.30 nm/194.50625 THz 6.25GHz spacing";
        //        }
        //        enum "1541.25" {
        //          description "1541.25 nm/194.51250 THz 6.25/12.5GHz spacing";
        //        }
        //        enum "1541.20" {
        //          description "1541.20 nm/194.51875 THz 6.25GHz spacing";
        //        }
        //        enum "1541.15" {
        //          description "1541.15 nm/194.52500 THz 6.25/12.5/75GHz spacing";
        //        }
        //        enum "1541.10" {
        //          description "1541.10 nm/194.53125 THz 6.25GHz spacing";
        //        }
        //        enum "1541.05" {
        //          description "1541.05 nm/194.53750 THz 6.25/12.5GHz spacing";
        //        }
        //        enum "1541.00" {
        //          description "1541.00 nm/194.54375 THz 6.25GHz spacing";
        //        }
        //        enum "1540.95" {
        //          description "1540.95 nm/194.55000 THz 6.25/12.5/50GHz spacing";
        //        }
        //        enum "1540.90" {
        //          description "1540.90 nm/194.55625 THz 6.25GHz spacing";
        //        }
        //        enum "1540.85" {
        //          description "1540.85 nm/194.56250 THz 6.25/12.5GHz spacing";
        //        }
        //        enum "1540.80" {
        //          description "1540.80 nm/194.56875 THz 6.25GHz spacing";
        //        }
        //        enum "1540.76" {
        //          description "1540.76 nm/194.57500 THz 6.25/12.5GHz spacing";
        //        }
        //        enum "1540.71" {
        //          description "1540.71 nm/194.58125 THz 6.25GHz spacing";
        //        }
        //        enum "1540.66" {
        //          description "1540.66 nm/194.58750 THz 6.25/12.5GHz spacing";
        //        }
        //        enum "1540.61" {
        //          description "1540.61 nm/194.59375 THz 6.25GHz spacing";
        //        }
        //        enum "1540.56" {
        //          description "1540.56 nm/194.60000 THz 6.25/12.5/50/75/100GHz spacing";
        //        }
        //        enum "1540.51" {
        //          description "1540.51 nm/194.60625 THz 6.25GHz spacing";
        //        }
        //        enum "1540.46" {
        //          description "1540.46 nm/194.61250 THz 6.25/12.5GHz spacing";
        //        }
        //        enum "1540.41" {
        //          description "1540.41 nm/194.61875 THz 6.25GHz spacing";
        //        }
        //        enum "1540.36" {
        //          description "1540.36 nm/194.62500 THz 6.25/12.5GHz spacing";
        //        }
        //        enum "1540.31" {
        //          description "1540.31 nm/194.63125 THz 6.25GHz spacing";
        //        }
        //        enum "1540.26" {
        //          description "1540.26 nm/194.63750 THz 6.25/12.5GHz spacing";
        //        }
        //        enum "1540.21" {
        //          description "1540.21 nm/194.64375 THz 6.25GHz spacing";
        //        }
        //        enum "1540.16" {
        //          description "1540.16 nm/194.65000 THz 6.25/12.5/50GHz spacing";
        //        }
        //        enum "1540.11" {
        //          description "1540.11 nm/194.65625 THz 6.25GHz spacing";
        //        }
        //        enum "1540.06" {
        //          description "1540.06 nm/194.66250 THz 6.25/12.5GHz spacing";
        //        }
        //        enum "1540.01" {
        //          description "1540.01 nm/194.66875 THz 6.25GHz spacing";
        //        }
        //        enum "1539.96" {
        //          description "1539.96 nm/194.67500 THz 6.25/12.5/50/75GHz spacing";
        //        }
        //        enum "1539.91" {
        //          description "1539.91 nm/194.68125 THz 6.25GHz spacing";
        //        }
        //        enum "1539.86" {
        //          description "1539.86 nm/194.68750 THz 6.25/12.5GHz spacing";
        //        }
        //        enum "1539.82" {
        //          description "1539.82 nm/194.69375 THz 6.25GHz spacing";
        //        }
        //        enum "1539.77" {
        //          description "1539.77 nm/194.70000 THz 6.25/12.5/50/100GHz spacing";
        //        }
        //        enum "1539.72" {
        //          description "1539.72 nm/194.70625 THz 6.25GHz spacing";
        //        }
        //        enum "1539.67" {
        //          description "1539.67 nm/194.71250 THz 6.25/12.5GHz spacing";
        //        }
        //        enum "1539.62" {
        //          description "1539.62 nm/194.71875 THz 6.25GHz spacing";
        //        }
        //        enum "1539.57" {
        //          description "1539.57 nm/194.72500 THz 6.25/12.5GHz spacing";
        //        }
        //        enum "1539.52" {
        //          description "1539.52 nm/194.73125 THz 6.25GHz spacing";
        //        }
        //        enum "1539.47" {
        //          description "1539.47 nm/194.73750 THz 6.25/12.5GHz spacing";
        //        }
        //        enum "1539.42" {
        //          description "1539.42 nm/194.74375 THz 6.25GHz spacing";
        //        }
        //        enum "1539.37" {
        //          description "1539.37 nm/194.75000 THz 6.25/12.5/50/75GHz spacing";
        //        }
        //        enum "1539.32" {
        //          description "1539.32 nm/194.75625 THz 6.25GHz spacing";
        //        }
        //        enum "1539.27" {
        //          description "1539.27 nm/194.76250 THz 6.25/12.5GHz spacing";
        //        }
        //        enum "1539.22" {
        //          description "1539.22 nm/194.76875 THz 6.25GHz spacing";
        //        }
        //        enum "1539.17" {
        //          description "1539.17 nm/194.77500 THz 6.25/12.5GHz spacing";
        //        }
        //        enum "1539.12" {
        //          description "1539.12 nm/194.78125 THz 6.25GHz spacing";
        //        }
        //        enum "1539.07" {
        //          description "1539.07 nm/194.78750 THz 6.25/12.5GHz spacing";
        //        }
        //        enum "1539.03" {
        //          description "1539.03 nm/194.79375 THz 6.25GHz spacing";
        //        }
        //        enum "1538.98" {
        //          description "1538.98 nm/194.80000 THz 6.25/12.5/50/100GHz spacing";
        //        }
        //        enum "1538.93" {
        //          description "1538.93 nm/194.80625 THz 6.25GHz spacing";
        //        }
        //        enum "1538.88" {
        //          description "1538.88 nm/194.81250 THz 6.25/12.5GHz spacing";
        //        }
        //        enum "1538.83" {
        //          description "1538.83 nm/194.81875 THz 6.25GHz spacing";
        //        }
        //        enum "1538.78" {
        //          description "1538.78 nm/194.82500 THz 6.25/12.5/75GHz spacing";
        //        }
        //        enum "1538.73" {
        //          description "1538.73 nm/194.83125 THz 6.25GHz spacing";
        //        }
        //        enum "1538.68" {
        //          description "1538.68 nm/194.83750 THz 6.25/12.5GHz spacing";
        //        }
        //        enum "1538.63" {
        //          description "1538.63 nm/194.84375 THz 6.25GHz spacing";
        //        }
        //        enum "1538.58" {
        //          description "1538.58 nm/194.85000 THz 6.25/12.5/50GHz spacing";
        //        }
        //        enum "1538.53" {
        //          description "1538.53 nm/194.85625 THz 6.25GHz spacing";
        //        }
        //        enum "1538.48" {
        //          description "1538.48 nm/194.86250 THz 6.25/12.5GHz spacing";
        //        }
        //        enum "1538.43" {
        //          description "1538.43 nm/194.86875 THz 6.25GHz spacing";
        //        }
        //        enum "1538.38" {
        //          description "1538.38 nm/194.87500 THz 6.25/12.5/75GHz spacing";
        //        }
        //        enum "1538.33" {
        //          description "1538.33 nm/194.88125 THz 6.25GHz spacing";
        //        }
        //        enum "1538.28" {
        //          description "1538.28 nm/194.88750 THz 6.25/12.5GHz spacing";
        //        }
        //        enum "1538.24" {
        //          description "1538.24 nm/194.89375 THz 6.25GHz spacing";
        //        }
        //        enum "1538.19" {
        //          description "1538.19 nm/194.90000 THz 6.25/12.5/50/75/100GHz spacing";
        //        }
        //        enum "1538.14" {
        //          description "1538.14 nm/194.90625 THz 6.25GHz spacing";
        //        }
        //        enum "1538.09" {
        //          description "1538.09 nm/194.91250 THz 6.25/12.5GHz spacing";
        //        }
        //        enum "1538.04" {
        //          description "1538.04 nm/194.91875 THz 6.25GHz spacing";
        //        }
        //        enum "1537.99" {
        //          description "1537.99 nm/194.92500 THz 6.25/12.5GHz spacing";
        //        }
        //        enum "1537.94" {
        //          description "1537.94 nm/194.93125 THz 6.25GHz spacing";
        //        }
        //        enum "1537.89" {
        //          description "1537.89 nm/194.93750 THz 6.25/12.5GHz spacing";
        //        }
        //        enum "1537.84" {
        //          description "1537.84 nm/194.94375 THz 6.25GHz spacing";
        //        }
        //        enum "1537.79" {
        //          description "1537.79 nm/194.95000 THz 6.25/12.5/50GHz spacing";
        //        }
        //        enum "1537.74" {
        //          description "1537.74 nm/194.95625 THz 6.25GHz spacing";
        //        }
        //        enum "1537.69" {
        //          description "1537.69 nm/194.96250 THz 6.25/12.5GHz spacing";
        //        }
        //        enum "1537.64" {
        //          description "1537.64 nm/194.96875 THz 6.25GHz spacing";
        //        }
        //        enum "1537.59" {
        //          description "1537.59 nm/194.97500 THz 6.25/12.5/75GHz spacing";
        //        }
        //        enum "1537.55" {
        //          description "1537.55 nm/194.98125 THz 6.25GHz spacing";
        //        }
        //        enum "1537.50" {
        //          description "1537.50 nm/194.98750 THz 6.25/12.5GHz spacing";
        //        }
        //        enum "1537.45" {
        //          description "1537.45 nm/194.99375 THz 6.25GHz spacing";
        //        }
        //        enum "1537.40" {
        //          description "1537.40 nm/195.00000 THz 6.25/12.5/50/100GHz spacing";
        //        }
        //        enum "1537.35" {
        //          description "1537.35 nm/195.00625 THz 6.25GHz spacing";
        //        }
        //        enum "1537.30" {
        //          description "1537.30 nm/195.01250 THz 6.25/12.5GHz spacing";
        //        }
        //        enum "1537.25" {
        //          description "1537.25 nm/195.01875 THz 6.25GHz spacing";
        //        }
        //        enum "1537.20" {
        //          description "1537.20 nm/195.02500 THz 6.25/12.5GHz spacing";
        //        }
        //        enum "1537.15" {
        //          description "1537.15 nm/195.03125 THz 6.25GHz spacing";
        //        }
        //        enum "1537.10" {
        //          description "1537.10 nm/195.03750 THz 6.25/12.5GHz spacing";
        //        }
        //        enum "1537.05" {
        //          description "1537.05 nm/195.04375 THz 6.25GHz spacing";
        //        }
        //        enum "1537.00" {
        //          description "1537.00 nm/195.05000 THz 6.25/12.5/50/75GHz spacing";
        //        }
        //        enum "1536.95" {
        //          description "1536.95 nm/195.05625 THz 6.25GHz spacing";
        //        }
        //        enum "1536.90" {
        //          description "1536.90 nm/195.06250 THz 6.25/12.5GHz spacing";
        //        }
        //        enum "1536.86" {
        //          description "1536.86 nm/195.06875 THz 6.25GHz spacing";
        //        }
        //        enum "1536.81" {
        //          description "1536.81 nm/195.07500 THz 6.25/12.5GHz spacing";
        //        }
        //        enum "1536.76" {
        //          description "1536.76 nm/195.08125 THz 6.25GHz spacing";
        //        }
        //        enum "1536.71" {
        //          description "1536.71 nm/195.08750 THz 6.25/12.5GHz spacing";
        //        }
        //        enum "1536.66" {
        //          description "1536.66 nm/195.09375 THz 6.25GHz spacing";
        //        }
        //        enum "1536.61" {
        //          description "1536.61 nm/195.10000 THz 6.25/12.5/50/100GHz spacing";
        //        }
        //        enum "1536.56" {
        //          description "1536.56 nm/195.10625 THz 6.25GHz spacing";
        //        }
        //        enum "1536.51" {
        //          description "1536.51 nm/195.11250 THz 6.25/12.5GHz spacing";
        //        }
        //        enum "1536.46" {
        //          description "1536.46 nm/195.11875 THz 6.25GHz spacing";
        //        }
        //        enum "1536.41" {
        //          description "1536.41 nm/195.12500 THz 6.25/12.5/75GHz spacing";
        //        }
        //        enum "1536.36" {
        //          description "1536.36 nm/195.13125 THz 6.25GHz spacing";
        //        }
        //        enum "1536.31" {
        //          description "1536.31 nm/195.13750 THz 6.25/12.5GHz spacing";
        //        }
        //        enum "1536.26" {
        //          description "1536.26 nm/195.14375 THz 6.25GHz spacing";
        //        }
        //        enum "1536.22" {
        //          description "1536.22 nm/195.15000 THz 6.25/12.5/50GHz spacing";
        //        }
        //        enum "1536.17" {
        //          description "1536.17 nm/195.15625 THz 6.25GHz spacing";
        //        }
        //        enum "1536.12" {
        //          description "1536.12 nm/195.16250 THz 6.25/12.5GHz spacing";
        //        }
        //        enum "1536.07" {
        //          description "1536.07 nm/195.16875 THz 6.25GHz spacing";
        //        }
        //        enum "1536.02" {
        //          description "1536.02 nm/195.17500 THz 6.25/12.5GHz spacing";
        //        }
        //        enum "1535.97" {
        //          description "1535.97 nm/195.18125 THz 6.25GHz spacing";
        //        }
        //        enum "1535.92" {
        //          description "1535.92 nm/195.18750 THz 6.25/12.5GHz spacing";
        //        }
        //        enum "1535.87" {
        //          description "1535.87 nm/195.19375 THz 6.25GHz spacing";
        //        }
        //        enum "1535.82" {
        //          description "1535.82 nm/195.20000 THz 6.25/12.5/50/75/100GHz spacing";
        //        }
        //        enum "1535.77" {
        //          description "1535.77 nm/195.20625 THz 6.25GHz spacing";
        //        }
        //        enum "1535.72" {
        //          description "1535.72 nm/195.21250 THz 6.25/12.5GHz spacing";
        //        }
        //        enum "1535.67" {
        //          description "1535.67 nm/195.21875 THz 6.25GHz spacing";
        //        }
        //        enum "1535.63" {
        //          description "1535.63 nm/195.22500 THz 6.25/12.5GHz spacing";
        //        }
        //        enum "1535.58" {
        //          description "1535.58 nm/195.23125 THz 6.25GHz spacing";
        //        }
        //        enum "1535.53" {
        //          description "1535.53 nm/195.23750 THz 6.25/12.5GHz spacing";
        //        }
        //        enum "1535.48" {
        //          description "1535.48 nm/195.24375 THz 6.25GHz spacing";
        //        }
        //        enum "1535.43" {
        //          description "1535.43 nm/195.25000 THz 6.25/12.5/50GHz spacing";
        //        }
        //        enum "1535.38" {
        //          description "1535.38 nm/195.25625 THz 6.25GHz spacing";
        //        }
        //        enum "1535.33" {
        //          description "1535.33 nm/195.26250 THz 6.25/12.5GHz spacing";
        //        }
        //        enum "1535.28" {
        //          description "1535.28 nm/195.26875 THz 6.25GHz spacing";
        //        }
        //        enum "1535.23" {
        //          description "1535.23 nm/195.27500 THz 6.25/12.5/75GHz spacing";
        //        }
        //        enum "1535.18" {
        //          description "1535.18 nm/195.28125 THz 6.25GHz spacing";
        //        }
        //        enum "1535.13" {
        //          description "1535.13 nm/195.28750 THz 6.25/12.5GHz spacing";
        //        }
        //        enum "1535.08" {
        //          description "1535.08 nm/195.29375 THz 6.25GHz spacing";
        //        }
        //        enum "1535.04" {
        //          description "1535.04 nm/195.30000 THz 6.25/12.5/50/100GHz spacing";
        //        }
        //        enum "1534.99" {
        //          description "1534.99 nm/195.30625 THz 6.25GHz spacing";
        //        }
        //        enum "1534.94" {
        //          description "1534.94 nm/195.31250 THz 6.25/12.5GHz spacing";
        //        }
        //        enum "1534.89" {
        //          description "1534.89 nm/195.31875 THz 6.25GHz spacing";
        //        }
        //        enum "1534.84" {
        //          description "1534.84 nm/195.32500 THz 6.25/12.5GHz spacing";
        //        }
        //        enum "1534.79" {
        //          description "1534.79 nm/195.33125 THz 6.25GHz spacing";
        //        }
        //        enum "1534.74" {
        //          description "1534.74 nm/195.33750 THz 6.25/12.5GHz spacing";
        //        }
        //        enum "1534.69" {
        //          description "1534.69 nm/195.34375 THz 6.25GHz spacing";
        //        }
        //        enum "1534.64" {
        //          description "1534.64 nm/195.35000 THz 6.25/12.5/50/75GHz spacing";
        //        }
        //        enum "1534.59" {
        //          description "1534.59 nm/195.35625 THz 6.25GHz spacing";
        //        }
        //        enum "1534.54" {
        //          description "1534.54 nm/195.36250 THz 6.25/12.5GHz spacing";
        //        }
        //        enum "1534.50" {
        //          description "1534.50 nm/195.36875 THz 6.25GHz spacing";
        //        }
        //        enum "1534.45" {
        //          description "1534.45 nm/195.37500 THz 6.25/12.5GHz spacing";
        //        }
        //        enum "1534.40" {
        //          description "1534.40 nm/195.38125 THz 6.25GHz spacing";
        //        }
        //        enum "1534.35" {
        //          description "1534.35 nm/195.38750 THz 6.25/12.5GHz spacing";
        //        }
        //        enum "1534.30" {
        //          description "1534.30 nm/195.39375 THz 6.25GHz spacing";
        //        }
        //        enum "1534.25" {
        //          description "1534.25 nm/195.40000 THz 6.25/12.5/50/100GHz spacing";
        //        }
        //        enum "1534.20" {
        //          description "1534.20 nm/195.40625 THz 6.25GHz spacing";
        //        }
        //        enum "1534.15" {
        //          description "1534.15 nm/195.41250 THz 6.25/12.5GHz spacing";
        //        }
        //        enum "1534.10" {
        //          description "1534.10 nm/195.41875 THz 6.25GHz spacing";
        //        }
        //        enum "1534.05" {
        //          description "1534.05 nm/195.42500 THz 6.25/12.5/75GHz spacing";
        //        }
        //        enum "1534.00" {
        //          description "1534.00 nm/195.43125 THz 6.25GHz spacing";
        //        }
        //        enum "1533.96" {
        //          description "1533.96 nm/195.43750 THz 6.25/12.5GHz spacing";
        //        }
        //        enum "1533.91" {
        //          description "1533.91 nm/195.44375 THz 6.25GHz spacing";
        //        }
        //        enum "1533.86" {
        //          description "1533.86 nm/195.45000 THz 6.25/12.5/50GHz spacing";
        //        }
        //        enum "1533.81" {
        //          description "1533.81 nm/195.45625 THz 6.25GHz spacing";
        //        }
        //        enum "1533.76" {
        //          description "1533.76 nm/195.46250 THz 6.25/12.5GHz spacing";
        //        }
        //        enum "1533.71" {
        //          description "1533.71 nm/195.46875 THz 6.25GHz spacing";
        //        }
        //        enum "1533.66" {
        //          description "1533.66 nm/195.47500 THz 6.25/12.5GHz spacing";
        //        }
        //        enum "1533.61" {
        //          description "1533.61 nm/195.48125 THz 6.25GHz spacing";
        //        }
        //        enum "1533.56" {
        //          description "1533.56 nm/195.48750 THz 6.25/12.5GHz spacing";
        //        }
        //        enum "1533.51" {
        //          description "1533.51 nm/195.49375 THz 6.25GHz spacing";
        //        }
        //        enum "1533.47" {
        //          description "1533.47 nm/195.50000 THz 6.25/12.5/50/75/100GHz spacing";
        //        }
        //        enum "1533.42" {
        //          description "1533.42 nm/195.50625 THz 6.25GHz spacing";
        //        }
        //        enum "1533.37" {
        //          description "1533.37 nm/195.51250 THz 6.25/12.5GHz spacing";
        //        }
        //        enum "1533.32" {
        //          description "1533.32 nm/195.51875 THz 6.25GHz spacing";
        //        }
        //        enum "1533.27" {
        //          description "1533.27 nm/195.52500 THz 6.25/12.5GHz spacing";
        //        }
        //        enum "1533.22" {
        //          description "1533.22 nm/195.53125 THz 6.25GHz spacing";
        //        }
        //        enum "1533.17" {
        //          description "1533.17 nm/195.53750 THz 6.25/12.5GHz spacing";
        //        }
        //        enum "1533.12" {
        //          description "1533.12 nm/195.54375 THz 6.25GHz spacing";
        //        }
        //        enum "1533.07" {
        //          description "1533.07 nm/195.55000 THz 6.25/12.5/50GHz spacing";
        //        }
        //        enum "1533.02" {
        //          description "1533.02 nm/195.55625 THz 6.25GHz spacing";
        //        }
        //        enum "1532.98" {
        //          description "1532.98 nm/195.56250 THz 6.25/12.5GHz spacing";
        //        }
        //        enum "1532.93" {
        //          description "1532.93 nm/195.56875 THz 6.25GHz spacing";
        //        }
        //        enum "1532.88" {
        //          description "1532.88 nm/195.57500 THz 6.25/12.5/75GHz spacing";
        //        }
        //        enum "1532.83" {
        //          description "1532.83 nm/195.58125 THz 6.25GHz spacing";
        //        }
        //        enum "1532.78" {
        //          description "1532.78 nm/195.58750 THz 6.25/12.5GHz spacing";
        //        }
        //        enum "1532.73" {
        //          description "1532.73 nm/195.59375 THz 6.25GHz spacing";
        //        }
        //        enum "1532.68" {
        //          description "1532.68 nm/195.60000 THz 6.25/12.5/50/100GHz spacing";
        //        }
        //        enum "1532.63" {
        //          description "1532.63 nm/195.60625 THz 6.25GHz spacing";
        //        }
        //        enum "1532.58" {
        //          description "1532.58 nm/195.61250 THz 6.25/12.5GHz spacing";
        //        }
        //        enum "1532.53" {
        //          description "1532.53 nm/195.61875 THz 6.25GHz spacing";
        //        }
        //        enum "1532.49" {
        //          description "1532.49 nm/195.62500 THz 6.25/12.5GHz spacing";
        //        }
        //        enum "1532.44" {
        //          description "1532.44 nm/195.63125 THz 6.25GHz spacing";
        //        }
        //        enum "1532.39" {
        //          description "1532.39 nm/195.63750 THz 6.25/12.5GHz spacing";
        //        }
        //        enum "1532.34" {
        //          description "1532.34 nm/195.64375 THz 6.25GHz spacing";
        //        }
        //        enum "1532.29" {
        //          description "1532.29 nm/195.65000 THz 6.25/12.5/50/75GHz spacing";
        //        }
        //        enum "1532.24" {
        //          description "1532.24 nm/195.65625 THz 6.25GHz spacing";
        //        }
        //        enum "1532.19" {
        //          description "1532.19 nm/195.66250 THz 6.25/12.5GHz spacing";
        //        }
        //        enum "1532.14" {
        //          description "1532.14 nm/195.66875 THz 6.25GHz spacing";
        //        }
        //        enum "1532.09" {
        //          description "1532.09 nm/195.67500 THz 6.25/12.5GHz spacing";
        //        }
        //        enum "1532.04" {
        //          description "1532.04 nm/195.68125 THz 6.25GHz spacing";
        //        }
        //        enum "1532.00" {
        //          description "1532.00 nm/195.68750 THz 6.25/12.5GHz spacing";
        //        }
        //        enum "1531.95" {
        //          description "1531.95 nm/195.69375 THz 6.25GHz spacing";
        //        }
        //        enum "1531.90" {
        //          description "1531.90 nm/195.70000 THz 6.25/12.5/50/100GHz spacing";
        //        }
        //        enum "1531.85" {
        //          description "1531.85 nm/195.70625 THz 6.25GHz spacing";
        //        }
        //        enum "1531.80" {
        //          description "1531.80 nm/195.71250 THz 6.25/12.5GHz spacing";
        //        }
        //        enum "1531.75" {
        //          description "1531.75 nm/195.71875 THz 6.25GHz spacing";
        //        }
        //        enum "1531.70" {
        //          description "1531.70 nm/195.72500 THz 6.25/12.5/75GHz spacing";
        //        }
        //        enum "1531.65" {
        //          description "1531.65 nm/195.73125 THz 6.25GHz spacing";
        //        }
        //        enum "1531.60" {
        //          description "1531.60 nm/195.73750 THz 6.25/12.5GHz spacing";
        //        }
        //        enum "1531.56" {
        //          description "1531.56 nm/195.74375 THz 6.25GHz spacing";
        //        }
        //        enum "1531.51" {
        //          description "1531.51 nm/195.75000 THz 6.25/12.5/50GHz spacing";
        //        }
        //        enum "1531.46" {
        //          description "1531.46 nm/195.75625 THz 6.25GHz spacing";
        //        }
        //        enum "1531.41" {
        //          description "1531.41 nm/195.76250 THz 6.25/12.5GHz spacing";
        //        }
        //        enum "1531.36" {
        //          description "1531.36 nm/195.76875 THz 6.25GHz spacing";
        //        }
        //        enum "1531.31" {
        //          description "1531.31 nm/195.77500 THz 6.25/12.5GHz spacing";
        //        }
        //        enum "1531.26" {
        //          description "1531.26 nm/195.78125 THz 6.25GHz spacing";
        //        }
        //        enum "1531.21" {
        //          description "1531.21 nm/195.78750 THz 6.25/12.5GHz spacing";
        //        }
        //        enum "1531.16" {
        //          description "1531.16 nm/195.79375 THz 6.25GHz spacing";
        //        }
        //        enum "1531.12" {
        //          description "1531.12 nm/195.80000 THz 6.25/12.5/50/75/100GHz spacing";
        //        }
        //        enum "1531.07" {
        //          description "1531.07 nm/195.80625 THz 6.25GHz spacing";
        //        }
        //        enum "1531.02" {
        //          description "1531.02 nm/195.81250 THz 6.25/12.5GHz spacing";
        //        }
        //        enum "1530.97" {
        //          description "1530.97 nm/195.81875 THz 6.25GHz spacing";
        //        }
        //        enum "1530.92" {
        //          description "1530.92 nm/195.82500 THz 6.25/12.5GHz spacing";
        //        }
        //        enum "1530.87" {
        //          description "1530.87 nm/195.83125 THz 6.25GHz spacing";
        //        }
        //        enum "1530.82" {
        //          description "1530.82 nm/195.83750 THz 6.25/12.5GHz spacing";
        //        }
        //        enum "1530.77" {
        //          description "1530.77 nm/195.84375 THz 6.25GHz spacing";
        //        }
        //        enum "1530.72" {
        //          description "1530.72 nm/195.85000 THz 6.25/12.5/50GHz spacing";
        //        }
        //        enum "1530.68" {
        //          description "1530.68 nm/195.85625 THz 6.25GHz spacing";
        //        }
        //        enum "1530.63" {
        //          description "1530.63 nm/195.86250 THz 6.25/12.5GHz spacing";
        //        }
        //        enum "1530.58" {
        //          description "1530.58 nm/195.86875 THz 6.25GHz spacing";
        //        }
        //        enum "1530.53" {
        //          description "1530.53 nm/195.87500 THz 6.25/12.5/75GHz spacing";
        //        }
        //        enum "1530.48" {
        //          description "1530.48 nm/195.88125 THz 6.25GHz spacing";
        //        }
        //        enum "1530.43" {
        //          description "1530.43 nm/195.88750 THz 6.25/12.5GHz spacing";
        //        }
        //        enum "1530.38" {
        //          description "1530.38 nm/195.89375 THz 6.25GHz spacing";
        //        }
        //        enum "1530.33" {
        //          description "1530.33 nm/195.90000 THz 6.25/12.5/50/100GHz spacing";
        //        }
        //        enum "1530.29" {
        //          description "1530.29 nm/195.90625 THz 6.25GHz spacing";
        //        }
        //        enum "1530.24" {
        //          description "1530.24 nm/195.91250 THz 6.25/12.5GHz spacing";
        //        }
        //        enum "1530.19" {
        //          description "1530.19 nm/195.91875 THz 6.25GHz spacing";
        //        }
        //        enum "1530.14" {
        //          description "1530.14 nm/195.92500 THz 6.25/12.5GHz spacing";
        //        }
        //        enum "1530.09" {
        //          description "1530.09 nm/195.93125 THz 6.25GHz spacing";
        //        }
        //        enum "1530.04" {
        //          description "1530.04 nm/195.93750 THz 6.25/12.5GHz spacing";
        //        }
        //        enum "1529.99" {
        //          description "1529.99 nm/195.94375 THz 6.25GHz spacing";
        //        }
        //        enum "1529.94" {
        //          description "1529.94 nm/195.95000 THz 6.25/12.5/50/75GHz spacing";
        //        }
        //        enum "1529.89" {
        //          description "1529.89 nm/195.95625 THz 6.25GHz spacing";
        //        }
        //        enum "1529.85" {
        //          description "1529.85 nm/195.96250 THz 6.25/12.5GHz spacing";
        //        }
        //        enum "1529.80" {
        //          description "1529.80 nm/195.96875 THz 6.25GHz spacing";
        //        }
        //        enum "1529.75" {
        //          description "1529.75 nm/195.97500 THz 6.25/12.5GHz spacing";
        //        }
        //        enum "1529.70" {
        //          description "1529.70 nm/195.98125 THz 6.25GHz spacing";
        //        }
        //        enum "1529.65" {
        //          description "1529.65 nm/195.98750 THz 6.25/12.5GHz spacing";
        //        }
        //        enum "1529.60" {
        //          description "1529.60 nm/195.99375 THz 6.25GHz spacing";
        //        }
        //        enum "1529.55" {
        //          description "1529.55 nm/196.00000 THz 6.25/12.5/50/100GHz spacing";
        //        }
        //        enum "1529.50" {
        //          description "1529.50 nm/196.00625 THz 6.25GHz spacing";
        //        }
        //        enum "1529.46" {
        //          description "1529.46 nm/196.01250 THz 6.25/12.5GHz spacing";
        //        }
        //        enum "1529.41" {
        //          description "1529.41 nm/196.01875 THz 6.25GHz spacing";
        //        }
        //        enum "1529.36" {
        //          description "1529.36 nm/196.02500 THz 6.25/12.5/75GHz spacing";
        //        }
        //        enum "1529.31" {
        //          description "1529.31 nm/196.03125 THz 6.25GHz spacing";
        //        }
        //        enum "1529.26" {
        //          description "1529.26 nm/196.03750 THz 6.25/12.5GHz spacing";
        //        }
        //        enum "1529.21" {
        //          description "1529.21 nm/196.04375 THz 6.25GHz spacing";
        //        }
        //        enum "1529.16" {
        //          description "1529.16 nm/196.05000 THz 6.25/12.5/50GHz spacing";
        //        }
        //        enum "1529.11" {
        //          description "1529.11 nm/196.05625 THz 6.25GHz spacing";
        //        }
        //        enum "1529.07" {
        //          description "1529.07 nm/196.06250 THz 6.25/12.5GHz spacing";
        //        }
        //        enum "1529.02" {
        //          description "1529.02 nm/196.06875 THz 6.25GHz spacing";
        //        }
        //        enum "1528.97" {
        //          description "1528.97 nm/196.07500 THz 6.25/12.5GHz spacing";
        //        }
        //        enum "1528.92" {
        //          description "1528.92 nm/196.08125 THz 6.25GHz spacing";
        //        }
        //        enum "1528.87" {
        //          description "1528.87 nm/196.08750 THz 6.25/12.5GHz spacing";
        //        }
        //        enum "1528.82" {
        //          description "1528.82 nm/196.09375 THz 6.25GHz spacing";
        //        }
        //        enum "1528.77" {
        //          description "1528.77 nm/196.10000 THz 6.25/12.5/50/75/100GHz spacing";
        //        }
        //        enum "1528.38" {
        //          description "1528.38 nm/196.15040 THz 50Ghz spacing";
        //        }
        //      }
        //    }
        //    leaf tx-power {
        //      description "Transmit laser output power";
        //      units "dBm";
        //      type string {
        //      }
        //    }
        //    container loopback {
        //      presence "enable loopback";
        //      description "Put the optics in loopback mode";
        //      // uses apply-advanced;
        //      leaf loopbacktype {
        //        description "Set loopback type";
        //        type enumeration {
        //          enum "media-side-out" {
        //            description "Loop media side output back to input";
        //          }
        //          enum "media-side-in" {
        //            description "Loop media side input back to output";
        //          }
        //          enum "host-side-out" {
        //            description "Loop host side output back to input";
        //          }
        //          enum "host-side-in" {
        //            description "Loop host side input back to output";
        //          }
        //        }
        //      }
        //    }
        //    leaf los-warning-threshold {
        //      description "LOS warning threshold";
        //      units "dBm";
        //      type string;
        //    }
        //    leaf los-alarm-threshold {
        //      description "LOS alarm threshold";
        //      units "dBm";
        //      type string;
        //    }
        //    leaf modulation-format {
        //      description "Type of Modulation Format";
        //      type enumeration {
        //        enum "16qam" {
        //          description "16-QAM Modulation Format";
        //        }
        //        enum "8qam" {
        //          description "8-QAM MOdulation Format";
        //        }
        //        enum "qpsk" {
        //          description "QPSK Modulation Format";
        //        }
        //      }
        //    }
        //    choice laser-enable-choice {
        //      leaf laser-enable {
        //        description "Enable Laser";
        //        type empty;
        //      }
        //      leaf no-laser-enable {
        //        description "Don't enable Laser";
        //        type empty;
        //      }
        //    }
        //    choice is-ma-choice {
        //      leaf is-ma {
        //        description "Link is enabled with alarms masked";
        //        type empty;
        //      }
        //      leaf no-is-ma {
        //        description "Don't link is enabled with alarms masked";
        //        type empty;
        //      }
        //    }
        //    leaf encoding {
        //      description "Line encoding";
        //      type enumeration {
        //        enum "differential" {
        //          description "Differential phase line encoding";
        //        }
        //        enum "non-differential" {
        //          description "Non-differential phase line encoding";
        //        }
        //      }
        //    }
        //    leaf fec {
        //      description "Forward Error Correction mode";
        //      type enumeration {
        //        enum "sdfec" {
        //          description "Sky-Compatible Soft Decision Forward Error Correction";
        //        }
        //        enum "sdfec25" {
        //          description "Denali-Compatible Soft Decision Forward Error Correction with 25 percent overhead";
        //        }
        //        enum "hgfec" {
        //          description "High Gain Forward Error Correction";
        //        }
        //        enum "sdfec15" {
        //          description "Soft Decision Forward Error Correction with 15 percent overhead";
        //        }
        //      }
        //    }
        //    leaf high-polarization {
        //      description "High polarization tracking mode";
        //      type empty;
        //    }
        //    container application {
        //      description "Config Host and Media Code";
        //      // uses apply-advanced;
        //      leaf hostid {
        //        description "Enter Host Code";
        //        type union {
        //          type string {
        //            pattern "<.*>|$.*";
        //          }
        //          type uint32 {
        //            range "1 .. 300";
        //          }
        //        }
        //      }
        //      leaf mediaid {
        //        description "Enter Media Code";
        //        type union {
        //          type string {
        //            pattern "<.*>|$.*";
        //          }
        //          type uint32 {
        //            range "1 .. 300";
        //          }
        //        }
        //      }
        //      leaf domainid {
        //        description "Enter Domain ID";
        //        type union {
        //          type string {
        //            pattern "<.*>|$.*";
        //          }
        //          type uint32 {
        //            range "0 .. 300";
        //          }
        //        }
        //      }
        //    }
        //    container signal-degrade {
        //      description "Signal degrade thresholds";
        //      // uses apply-advanced;
        //      leaf interval {
        //        description "Time interval";
        //        default "10";
        //        units "milliseconds";
        //        type union {
        //          type string {
        //            pattern "<.*>|$.*";
        //          }
        //          type uint32 {
        //            range "1 .. 1000";
        //          }
        //        }
        //      }
        //      leaf ber-threshold-clear {
        //        description "Ber threshold for signal degrade clear (format: xe-n, example: 4.5e-3)";
        //        type string {
        //        }
        //      }
        //      leaf ber-threshold-signal-degrade {
        //        description "Ber threshold for signal-degrade (format: xe-n, example: 4.5e-3)";
        //        type string {
        //        }
        //      }
        //      leaf q-threshold-signal-degrade-clear {
        //        description "Q threshold for signal-degrade clear (e.g. 14.26)";
        //        units "dB";
        //        type string;
        //      }
        //      leaf q-threshold-signal-degrade {
        //        description "Q threshold for signal-degrade (e.g. 9.26)";
        //        units "dB";
        //        type string;
        //      }
        //    }
        //    list alarm {
        //      key name;
        //      ordered-by user;
        //      description "Set optic alarms";
        //      leaf name {
        //        type enumeration {
        //          enum "low-light-alarm" {
        //            description "Enable low light alarm";
        //          }
        //        }
        //      }
        //      // uses apply-advanced;
        //      choice actiontype {
        //        case case_1 {
        //          leaf syslog {
        //            type empty;
        //          }
        //        }
        //        case case_2 {
        //          leaf link-down {
        //            type empty;
        //          }
        //        }
        //      }
        //    }
        //    container tca {
        //      description "Set tca for optic alarms";
        //      // uses apply-advanced;
        //      container tx-power-high-tca {
        //        description "Tx power high TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute tx power high TCA in dBm";
        //          type string {
        //          }
        //        }
        //        leaf threshold-24hrs {
        //          description "Threshold for 24 hour tx power high TCA in dBm";
        //          type string {
        //          }
        //        }
        //      }
        //      container tx-power-low-tca {
        //        description "Tx power low TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute tx power low TCA in dBm";
        //          type string {
        //          }
        //        }
        //        leaf threshold-24hrs {
        //          description "Threshold for 24 hour tx power low TCA in dBm";
        //          type string {
        //          }
        //        }
        //      }
        //      container rx-power-high-tca {
        //        description "Rx power high TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute rx power high TCA in dBm";
        //          type string {
        //          }
        //        }
        //        leaf threshold-24hrs {
        //          description "Threshold for 24 hour rx power high TCA in dBm";
        //          type string {
        //          }
        //        }
        //      }
        //      container rx-power-low-tca {
        //        description "Rx power low TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute rx power low TCA in dBm";
        //          type string {
        //          }
        //        }
        //        leaf threshold-24hrs {
        //          description "Threshold for 24 hour rx power low TCA in dBm";
        //          type string {
        //          }
        //        }
        //      }
        //      container rx-signal-power-high-tca {
        //        description "Rx signal power high TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute rx signal power high TCA in dBm";
        //          type string {
        //          }
        //        }
        //        leaf threshold-24hrs {
        //          description "Threshold for 24 hour rx signal power high TCA in dBm";
        //          type string {
        //          }
        //        }
        //      }
        //      container rx-signal-power-low-tca {
        //        description "Rx signal power low TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute rx signal power low TCA in dBm";
        //          type string {
        //          }
        //        }
        //        leaf threshold-24hrs {
        //          description "Threshold for 24 hour rx signal power low TCA in dBm";
        //          type string {
        //          }
        //        }
        //      }
        //      container temperature-high-tca {
        //        description "Temperature high TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute high temperature TCA in celsius";
        //          type string {
        //          }
        //        }
        //        leaf threshold-24hrs {
        //          description "Threshold for 24 hour high temperature TCA in celsius";
        //          type string {
        //          }
        //        }
        //      }
        //      container temperature-low-tca {
        //        description "Temperature low TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute low temperature TCA in celsius";
        //          type string {
        //          }
        //        }
        //        leaf threshold-24hrs {
        //          description "Threshold for 24 hour low temperature TCA in celsius";
        //          type string {
        //          }
        //        }
        //      }
        //      container carrier-frequency-offset-high-tca {
        //        description "Carrier frequency offset high TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute frequency offset high TCA in MHz";
        //          type string {
        //          }
        //        }
        //        leaf threshold-24hrs {
        //          description "Threshold for 24 hour frequency offset high TCA in MHz";
        //          type string {
        //          }
        //        }
        //      }
        //      container carrier-frequency-offset-low-tca {
        //        description "Carrier frequency offset low TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute frequency offset low TCA in MHz";
        //          type string {
        //          }
        //        }
        //        leaf threshold-24hrs {
        //          description "Threshold for 24 hour frequency offset low TCA in MHz";
        //          type string {
        //          }
        //        }
        //      }
        //      container fec-ber {
        //        description "Optics Errored Seconds Threshold crossing defect trigger";
        //        choice enable-tca-choice {
        //          leaf enable-tca {
        //            description "Enable the Optics errored seconds threshold crossing alert";
        //            type empty;
        //          }
        //          leaf no-enable-tca {
        //            description "Don't enable the Optics errored seconds threshold crossing alert";
        //            type empty;
        //          }
        //        }
        //        leaf threshold {
        //          description "TCA threshold for BER value in format: xe-n, x is an integer or decimal number, n = 0..9";
        //          default "10e-3";
        //          type string {
        //          }
        //        }
        //        leaf threshold-24hrs {
        //          description "TCA threshold for BER value in format: xe-n, x is an integer or decimal number, n = 0..9";
        //          default "10e-3";
        //          type string {
        //          }
        //        }
        //      }
        //      container tec-current-high-tca {
        //        description "TEC Current high TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute TEC Current high TCA in mA";
        //          type string {
        //          }
        //        }
        //        leaf threshold-24hrs {
        //          description "Threshold for 24 hour TEC Current high TCA in mA";
        //          type string {
        //          }
        //        }
        //      }
        //      container tec-current-low-tca {
        //        description "TEC Current low TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute TEC Current low TCA in mA";
        //          type string {
        //          }
        //        }
        //        leaf threshold-24hrs {
        //          description "Threshold for 24 hour TEC Current low TCA in mA";
        //          type string {
        //          }
        //        }
        //      }
        //      container residual-isi-high-tca {
        //        description "Residual ISI high TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute Residual ISI high TCA in ps/nm";
        //          type string {
        //          }
        //        }
        //        leaf threshold-24hrs {
        //          description "Threshold for 24 hour Residual ISI high TCA in ps/nm";
        //          type string {
        //          }
        //        }
        //      }
        //      container residual-isi-low-tca {
        //        description "Residual ISI low TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute Residual ISI low TCA in ps/nm";
        //          type string {
        //          }
        //        }
        //        leaf threshold-24hrs {
        //          description "Threshold for 24 hour Residual ISI low TCA in ps/nm";
        //          type string {
        //          }
        //        }
        //      }
        //      container pam-histogram-high-tca {
        //        description "PAM Histogram high TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute PAM Histogram high TCA";
        //          type string {
        //          }
        //        }
        //        leaf threshold-24hrs {
        //          description "Threshold for 24 hour PAM Histogram high TCA";
        //          type string {
        //          }
        //        }
        //      }
        //      container snr-low-tca {
        //        description "SNR low TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute SNR low TCA in dBm ";
        //          type string {
        //          }
        //        }
        //        leaf threshold-24hrs {
        //          description "Threshold for 24 hour SNR low TCA in dBm";
        //          type string {
        //          }
        //        }
        //      }
        //      container fec-corrected-errors-high-tca {
        //        description "FEC Corrected Error High Threshold crossing defect trigger";
        //        // uses apply-advanced;
        //        choice enable-tca-choice {
        //          leaf enable-tca {
        //            description "Enable the FEC Corrected Errors threshold crossing alert";
        //            type empty;
        //          }
        //          leaf no-enable-tca {
        //            description "Don't enable the FEC Corrected Errors threshold crossing alert";
        //            type empty;
        //          }
        //        }
        //        leaf threshold {
        //          description "FEC Corrected-Errs value in format: xe-n, x is an integer or decimal number, n = 0..9";
        //          default "10e-3";
        //          type string {
        //          }
        //        }
        //        leaf threshold-24hrs {
        //          description "FEC Corrected-Errs value in format: xe-n, x is an integer or decimal number, n = 0..9";
        //          default "10e-3";
        //          type string {
        //          }
        //        }
        //      }
        //      container fec-ucorrected-words-high-tca {
        //        description "FEC UCorrected Words High Threshold crossing defect trigger";
        //        // uses apply-advanced;
        //        choice enable-tca-choice {
        //          leaf enable-tca {
        //            description "Enable the FEC UCorrected Words threshold crossing alert";
        //            type empty;
        //          }
        //          leaf no-enable-tca {
        //            description "Don't enable the FEC UCorrected Words threshold crossing alert";
        //            type empty;
        //          }
        //        }
        //        leaf threshold {
        //          description "FEC UCorrected-Words value in format: xe-n, x is an integer or decimal number, n = 0..9";
        //          default "10e-3";
        //          type string {
        //          }
        //        }
        //        leaf threshold-24hrs {
        //          description "FEC UCorrected-Words value in format: xe-n, x is an integer or decimal number, n = 0..9";
        //          default "10e-3";
        //          type string {
        //          }
        //        }
        //      }
        //      container laser-frequency-error-high-tca {
        //        description "Laser frequency error high TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute frequency error high TCA in MHz";
        //          type string {
        //          }
        //        }
        //        leaf threshold-24hrs {
        //          description "Threshold for 24 hour frequency error high TCA in MHz";
        //          type string {
        //          }
        //        }
        //      }
        //      container laser-frequency-error-low-tca {
        //        description "Laser frequency error low TCA";
        //        // uses apply-advanced;
        //        choice enable-tca-choice {
        //          leaf enable-tca {
        //            description "Enable tca";
        //            type empty;
        //          }
        //          leaf no-enable-tca {
        //            description "Don't enable tca";
        //            type empty;
        //          }
        //        }
        //        leaf threshold {
        //          description "Threshold for 15 minute frequency error low TCA in MHz";
        //          type string {
        //          }
        //        }
        //        leaf threshold-24hrs {
        //          description "Threshold for 24 hour frequency error low TCA in MHz";
        //          type string {
        //          }
        //        }
        //      }
        //    }
        //    list warning {
        //      key name;
        //      ordered-by user;
        //      description "Set optic warnings";
        //      leaf name {
        //        type enumeration {
        //          enum "low-light-warning" {
        //            description "Enable low light warning";
        //          }
        //        }
        //      }
        //      // uses apply-advanced;
        //      choice actiontype {
        //        case case_1 {
        //          leaf syslog {
        //            description "Set action as syslog";
        //            type empty;
        //          }
        //        }
        //        case case_2 {
        //          leaf link-down {
        //            description "Set action as link-down";
        //            type empty;
        //          }
        //        }
        //      }
        //    }
        //    leaf low-power-mode {
        //      description "Force optics to low power mode";
        //      type empty;
        //    }
        //    leaf host-side-fec {
        //      description "Host side optics FEC ON/OFF";
        //      type enumeration {
        //        enum "off" {
        //          description "Host side FEC OFF for optics";
        //        }
        //        enum "on" {
        //          description "Host side FEC ON for optics";
        //        }
        //      }
        //    }
        //    leaf media-side-fec {
        //      description "Media side FEC ON/OFF";
        //      type enumeration {
        //        enum "off" {
        //          description "Media side FEC OFF for optics";
        //        }
        //        enum "on" {
        //          description "Media side FEC ON for optics";
        //        }
        //      }
        //    }
        //    choice lane-info {
        //      case case_1 {
        //        list lane {
        //          key name;
        //          description "Media lane number";
        //          leaf name {
        //            description "Lane number";
        //            type union {
        //              type string {
        //                pattern "<.*>|$.*";
        //              }
        //              type uint32 {
        //                range "0 .. 7";
        //              }
        //            }
        //          }
        //          // uses apply-advanced;
        //          leaf tx-laser {
        //            description "Transmit Laser ON/OFF";
        //            type enumeration {
        //              enum "off" {
        //                description "Transmit laser OFF for optics";
        //              }
        //              enum "on" {
        //                description "Transmit laser ON for optics";
        //              }
        //            }
        //          }
        //          leaf rx-output {
        //            description "Receive output ON/OFF";
        //            type enumeration {
        //              enum "off" {
        //                description "Receive output OFF for optics";
        //              }
        //              enum "on" {
        //                description "Receive output ON for optics";
        //              }
        //            }
        //          }
        //          leaf tx-cdr {
        //            description "Transmit Clock and Data Recovery ON/OFF";
        //            type enumeration {
        //              enum "off" {
        //                description "Transmit Clock and Data Recovery OFF for optics";
        //              }
        //              enum "on" {
        //                description "Transmit Clock and Data Recovery ON for optics";
        //              }
        //            }
        //          }
        //          leaf rx-cdr {
        //            description "Receive Clock and Data Recovery ON/OFF";
        //            type enumeration {
        //              enum "off" {
        //                description "Receive Clock and Data Recovery OFF for optics";
        //              }
        //              enum "on" {
        //                description "Receive Clock and Data Recovery ON for optics";
        //              }
        //            }
        //          }
        //          leaf tx-input-equalization-adaptive {
        //            description "Transmit adaptive equalization ON/OFF";
        //            type enumeration {
        //              enum "off" {
        //                description "Transmit adaptive equalization OFF for optics";
        //              }
        //              enum "on" {
        //                description "Transmit adaptive equalization ON for optics";
        //              }
        //            }
        //          }
        //          leaf tx-input-equalization-manual {
        //            description "Transmit manual equalization for optics";
        //            units "dB";
        //            type union {
        //              type string {
        //                pattern "<.*>|$.*";
        //              }
        //              type int32 {
        //                range "0 .. 15";
        //              }
        //            }
        //          }
        //          leaf rx-output-emphasis {
        //            description "Receive output emphasis for optics";
        //            units "dB";
        //            type union {
        //              type string {
        //                pattern "<.*>|$.*";
        //              }
        //              type int32 {
        //                range "0 .. 15";
        //              }
        //            }
        //          }
        //          leaf rx-output-amplitude {
        //            description "Receive output amplitude setting";
        //            type enumeration {
        //              enum "400mV" {
        //                description "No equalization for 100mV - 400mV amplitude";
        //              }
        //              enum "600mV" {
        //                description "No equalization for 300mV - 600mV amplitude";
        //              }
        //              enum "800mV" {
        //                description "No equalization for 400mV - 800mV amplitude";
        //              }
        //              enum "1200mV" {
        //                description "No equalization for 600mV - 1200mV amplitude";
        //              }
        //            }
        //          }
        //          leaf tx-squelch {
        //            description "Transmit squelch ON/OFF";
        //            type enumeration {
        //              enum "off" {
        //                description "Transmit squelch OFF for optics";
        //              }
        //              enum "on" {
        //                description "Transmit squelch ON for optics";
        //              }
        //            }
        //          }
        //          leaf rx-squelch {
        //            description "Receive squelch ON/OFF";
        //            type enumeration {
        //              enum "off" {
        //                description "Receive squelch OFF for optics";
        //              }
        //              enum "on" {
        //                description "Receive squelch ON for optics";
        //              }
        //            }
        //          }
        //          leaf tx-rate-select {
        //            description "Transmit rate select for optics";
        //            type union {
        //              type string {
        //                pattern "<.*>|$.*";
        //              }
        //              type int32 {
        //                range "0 .. 3";
        //              }
        //            }
        //          }
        //          leaf rx-rate-select {
        //            description "Receive rate select for optics";
        //            type union {
        //              type string {
        //                pattern "<.*>|$.*";
        //              }
        //              type int32 {
        //                range "0 .. 3";
        //              }
        //            }
        //          }
        //        }
        //      }
        //      case case_2 {
        //        container lane-all {
        //          presence "enable lane-all";
        //          description "Apply settings to all lane";
        //          // uses apply-advanced;
        //          leaf tx-laser {
        //            description "Transmit Laser ON/OFF";
        //            type enumeration {
        //              enum "off" {
        //                description "Transmit laser OFF for optics";
        //              }
        //              enum "on" {
        //                description "Transmit laser ON for optics";
        //              }
        //            }
        //          }
        //          leaf rx-output {
        //            description "Receive output ON/OFF";
        //            type enumeration {
        //              enum "off" {
        //                description "Receive output OFF for optics";
        //              }
        //              enum "on" {
        //                description "Receive output ON for optics";
        //              }
        //            }
        //          }
        //          leaf tx-cdr {
        //            description "Transmit Clock and Data Recovery ON/OFF";
        //            type enumeration {
        //              enum "off" {
        //                description "Transmit Clock and Data Recovery OFF for optics";
        //              }
        //              enum "on" {
        //                description "Transmit Clock and Data Recovery ON for optics";
        //              }
        //            }
        //          }
        //          leaf rx-cdr {
        //            description "Receive Clock and Data Recovery ON/OFF";
        //            type enumeration {
        //              enum "off" {
        //                description "Receive Clock and Data Recovery OFF for optics";
        //              }
        //              enum "on" {
        //                description "Receive Clock and Data Recovery ON for optics";
        //              }
        //            }
        //          }
        //          leaf tx-input-equalization-adaptive {
        //            description "Transmit adaptive equalization ON/OFF";
        //            type enumeration {
        //              enum "off" {
        //                description "Transmit adaptive equalization OFF for optics";
        //              }
        //              enum "on" {
        //                description "Transmit adaptive equalization ON for optics";
        //              }
        //            }
        //          }
        //          leaf tx-input-equalization-manual {
        //            description "Transmit manual equalization for optics";
        //            units "dB";
        //            type union {
        //              type string {
        //                pattern "<.*>|$.*";
        //              }
        //              type int32 {
        //                range "0 .. 15";
        //              }
        //            }
        //          }
        //          leaf rx-output-emphasis {
        //            description "Receive output emphasis for optics";
        //            units "dB";
        //            type union {
        //              type string {
        //                pattern "<.*>|$.*";
        //              }
        //              type int32 {
        //                range "0 .. 15";
        //              }
        //            }
        //          }
        //          leaf rx-output-amplitude {
        //            description "Receive output amplitude setting";
        //            type enumeration {
        //              enum "400mV" {
        //                description "No equalization for 100mV - 400mV amplitude";
        //              }
        //              enum "600mV" {
        //                description "No equalization for 300mV - 600mV amplitude";
        //              }
        //              enum "800mV" {
        //                description "No equalization for 400mV - 800mV amplitude";
        //              }
        //              enum "1200mV" {
        //                description "No equalization for 600mV - 1200mV amplitude";
        //              }
        //            }
        //          }
        //          leaf tx-squelch {
        //            description "Transmit squelch ON/OFF";
        //            type enumeration {
        //              enum "off" {
        //                description "Transmit squelch OFF for optics";
        //              }
        //              enum "on" {
        //                description "Transmit squelch ON for optics";
        //              }
        //            }
        //          }
        //          leaf rx-squelch {
        //            description "Receive squelch ON/OFF";
        //            type enumeration {
        //              enum "off" {
        //                description "Receive squelch OFF for optics";
        //              }
        //              enum "on" {
        //                description "Receive squelch ON for optics";
        //              }
        //            }
        //          }
        //          leaf tx-rate-select {
        //            description "Transmit rate select for optics";
        //            type union {
        //              type string {
        //                pattern "<.*>|$.*";
        //              }
        //              type int32 {
        //                range "0 .. 3";
        //              }
        //            }
        //          }
        //          leaf rx-rate-select {
        //            description "Receive rate select for optics";
        //            type union {
        //              type string {
        //                pattern "<.*>|$.*";
        //              }
        //              type int32 {
        //                range "0 .. 3";
        //              }
        //            }
        //          }
        //        }
        //      }
        //    }
        //  }
        //  container otn-options {
        //    description "Optical Transmission Network interface-specific options";
        //    uses otn_options_type;
        //  }
        //  container tdm-options {
        //    description "Time division multiplexing (TDM) interface-specific options";
        //    uses tdm_options_type;
        //  }
        //  container och-options {
        //    description "Optical channel configuration options";
        //    uses och-attributes;
        //  }
        //  container otu-options {
        //    description "Optical transmission unit configuration options";
        //    uses otu-attributes;
        //  }
        //  container odu-options {
        //    description "Optical data unit configuration options";
        //    uses odu-attributes;
        //  }
        //  container ett-options {
        //    description "Transport ethernet client configuration options";
        //    uses ett-attributes;
        //  }
        //  container fastether-options {
        //    description "Fast Ethernet interface-specific options";
        //    // uses apply-advanced;
        //    choice loopback-choice {
        //      leaf loopback {
        //        description "Enable loopback";
        //        type empty;
        //      }
        //      leaf no-loopback {
        //        description "Don't enable loopback";
        //        type empty;
        //      }
        //    }
        //    choice flow-control-choice {
        //      leaf flow-control {
        //        description "Enable flow control";
        //        type empty;
        //      }
        //      leaf no-flow-control {
        //        description "Don't enable flow control";
        //        type empty;
        //      }
        //    }
        //    choice source-filtering-choice {
        //      leaf source-filtering {
        //        description "Enable source address filtering";
        //        type empty;
        //      }
        //      leaf no-source-filtering {
        //        description "Don't enable source address filtering";
        //        type empty;
        //      }
        //    }
        //    leaf ingress-rate-limit {
        //      description "Ingress rate at port";
        //      units "megabits per second";
        //      type union {
        //        type string {
        //          pattern "<.*>|$.*";
        //        }
        //        type uint32 {
        //          range "1 .. 100";
        //        }
        //      }
        //    }
        //    list source-address-filter {
        //      key name;
        //      ordered-by user;
        //      description "Source address filters";
        //      leaf name {
        //        description "Remote MAC address";
        //        type jt:mac-addr;
        //      }
        //    }
        //    container redundant-parent {
        //      description " Parent of this interface";
        //      // uses apply-advanced;
        //      leaf parent {
        //        description "Join a redundant ethernet interface";
        //        type union {
        //          type jt:interface-device;
        //          type string {
        //            pattern "<.*>|$.*";
        //          }
        //        }
        //      }
        //    }
        //    container ieee-802.3ad {
        //      description "IEEE 802.3ad";
        //      // uses apply-advanced;
        //      container lacp {
        //        description "Link Aggregation Control Protocol configuration";
        //        // uses apply-advanced;
        //        leaf port-priority {
        //          description "Priority of the port (0 ... 65535)";
        //          type union {
        //            type uint16;
        //            type string {
        //              pattern "<.*>|$.*";
        //            }
        //          }
        //        }
        //      }
        //      leaf bundle {
        //        description "Join an aggregated Ethernet interface";
        //        type union {
        //          type jt:interface-device;
        //          type string {
        //            pattern "<.*>|$.*";
        //          }
        //        }
        //      }
        //      choice type {
        //        case case_1 {
        //          leaf primary {
        //            description "Primary interface for link-protection mode";
        //            type empty;
        //          }
        //        }
        //        case case_2 {
        //          leaf backup {
        //            description "Backup interface for link-protection mode";
        //            type empty;
        //          }
        //        }
        //      }
        //    }
        //    container mpls {
        //      description "MPLS options";
        //      uses mpls_ifd_options;
        //    }
        //    leaf ignore-l3-incompletes {
        //      description "Ignore L3 incomplete errors";
        //      type empty;
        //    }
        //  }
        //  container redundant-ether-options {
        //    description "Ethernet redundancy options";
        //    // uses apply-advanced;
        //    leaf redundancy-group {
        //      description "Redundancy group of this interface";
        //      type union {
        //        type string {
        //          pattern "<.*>|$.*";
        //        }
        //        type uint16 {
        //          range "1 .. 128";
        //        }
        //      }
        //    }
        //    choice loopback-choice {
        //      leaf loopback {
        //        description "Enable loopback";
        //        type empty;
        //      }
        //      leaf no-loopback {
        //        description "Don't enable loopback";
        //        type empty;
        //      }
        //    }
        //    choice flow-control-choice {
        //      leaf flow-control {
        //        description "Enable flow control";
        //        type empty;
        //      }
        //      leaf no-flow-control {
        //        description "Don't enable flow control";
        //        type empty;
        //      }
        //    }
        //    choice source-filtering-choice {
        //      leaf source-filtering {
        //        description "Enable source address filtering";
        //        type empty;
        //      }
        //      leaf no-source-filtering {
        //        description "Don't enable source address filtering";
        //        type empty;
        //      }
        //    }
        //    list source-address-filter {
        //      key name;
        //      ordered-by user;
        //      description "Source address filters";
        //      leaf name {
        //        description "Remote MAC address";
        //        type jt:mac-addr;
        //      }
        //    }
        //    leaf link-speed {
        //      description "Link speed of individual interface that joins the RETH";
        //      type enumeration {
        //        enum "10m" {
        //          description "Links are 10M";
        //        }
        //        enum "100m" {
        //          description "Links are 100M";
        //        }
        //        enum "1g" {
        //          description "Links are 1G";
        //        }
        //        enum "10g" {
        //          description "Links are 10G";
        //        }
        //        enum "25g" {
        //          description "Links are 25G";
        //        }
        //      }
        //    }
        //    leaf minimum-links {
        //      description "Minimum number of active links";
        //      default "1";
        //      type union {
        //        type string {
        //          pattern "<.*>|$.*";
        //        }
        //        type uint16 {
        //          range "1 .. 8";
        //        }
        //      }
        //    }
        //    container lacp {
        //      description "Link Aggregation Control Protocol configuration";
        //      // uses apply-advanced;
        //      choice mode {
        //        case case_1 {
        //          leaf active {
        //            description "Initiate transmission of LACP packets";
        //            type empty;
        //          }
        //        }
        //        case case_2 {
        //          leaf passive {
        //            description "Respond to LACP packets";
        //            type empty;
        //          }
        //        }
        //      }
        //      leaf periodic {
        //        description "Timer interval for periodic transmission of LACP packets";
        //        type enumeration {
        //          enum "fast" {
        //            description "Receive packets every second";
        //          }
        //          enum "slow" {
        //            description "Receive packets every 30 seconds";
        //          }
        //        }
        //      }
        //    }
        //  }
         container aggregated-ether-options {
           description "Aggregated Ethernet interface-specific options";
           // uses apply-advanced;
           choice loopback-choice {
             leaf loopback {
               description "Enable loopback";
               type empty;
             }
             leaf no-loopback {
               description "Don't enable loopback";
               type empty;
             }
           }
          //  choice flow-control-choice {
          //    leaf flow-control {
          //      description "Enable flow control";
          //      type empty;
          //    }
          //    leaf no-flow-control {
          //      description "Don't enable flow control";
          //      type empty;
          //    }
          //  }
           choice source-filtering-choice {
             leaf source-filtering {
               description "Enable source address filtering";
               type empty;
             }
             leaf no-source-filtering {
               description "Don't enable source address filtering";
               type empty;
             }
           }
           leaf autostate-exclude {
             description "Interface will not contribute to IRB state";
             type empty;
           }
          //  container link-protection {
          //    presence "enable link-protection";
          //    description "Enable link protection mode";
          //    // uses apply-advanced;
          //    leaf revertive {
          //      description "Revert back from active backup link to primary, if primary is UP";
          //      type empty;
          //    }
          //    leaf non-revertive {
          //      description "Do not revert back (default mode) from active backup link to primary, if primary is UP";
          //      type empty;
          //    }
          //    leaf backup-state {
          //      description "Link protection backup link state";
          //      default "accept-data";
          //      type enumeration {
          //        enum "accept-data" {
          //          description "Accept data on receive channel of backup link";
          //        }
          //        enum "discard-data" {
          //          description "Discard data on receive channel of backup link";
          //        }
          //        enum "down" {
          //          description "Backup link is marked down";
          //        }
          //      }
          //    }
          //    container rtg-config {
          //      presence "enable rtg-config";
          //      description "RTG enable on AE";
          //      // uses apply-advanced;
          //      leaf preempt-cutover-timer {
          //        description "RTG preempt-cutover-timer in seconds";
          //        default "1";
          //        type union {
          //          type string {
          //            pattern "<.*>|$.*";
          //          }
          //          type uint32 {
          //            range "0 .. 255";
          //          }
          //        }
          //      }
          //    }
          //  }
          //  choice fcoe-lag-choice {
          //    leaf fcoe-lag {
          //      description "Enable FIP/FCoE LAG";
          //      type empty;
          //    }
          //    leaf no-fcoe-lag {
          //      description "Don't enable FIP/FCoE LAG";
          //      type empty;
          //    }
          //  }
           list source-address-filter {
             key name;
             ordered-by user;
             description "Source address filters";
             leaf name {
               description "Remote MAC address";
               type jt:mac-addr;
             }
           }
          //  container load-balance {
          //    uses aggregate-load-balance;
          //  }
           container bfd-liveness-detection {
             description "Bidirectional Forwarding Detection (BFD) options";
             // uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 9000";
                 }
               }
             }
             choice adaptation-choice {
               case case_1 {
                 leaf no-adaptation {
                   description "Disable adaptation";
                   type empty;
                 }
               }
             }
             container transmit-interval {
               description "Transmit-interval options";
               // uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               // uses apply-advanced;
               leaf threshold {
                 description "High detection-time triggering a trap";
                 units "milliseconds";
                 type union {
                   type uint32;
                   type string {
                     pattern "<.*>|$.*";
                   }
                 }
               }
             }
             container authentication {
               description "Authentication options";
               // uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container damping {
               description "BFD flap damping parameters";
               // uses apply-advanced;
               leaf suppress {
                 description "Suppress threshold for figure-of-merit value";
                 default "5000";
                 type union {
                   type string {
                     pattern "<.*>|$.*";
                   }
                   type uint32 {
                     range "1000 .. 200000";
                   }
                 }
               }
               leaf reuse {
                 description "Reuse threshold for figure-of-merit value";
                 default "1000";
                 type union {
                   type string {
                     pattern "<.*>|$.*";
                   }
                   type uint32 {
                     range "1000 .. 200000";
                   }
                 }
               }
               leaf max-suppress-time {
                 description "Maximum hold-down time";
                 default "600";
                 units "seconds";
                 type union {
                   type string {
                     pattern "<.*>|$.*";
                   }
                   type uint32 {
                     range "1 .. 20000";
                   }
                 }
               }
               leaf half-life-interval {
                 description "Decay half life interval";
                 default "30";
                 units "seconds";
                 type union {
                   type string {
                     pattern "<.*>|$.*";
                   }
                   type uint32 {
                     range "1 .. 600";
                   }
                 }
               }
               leaf increment {
                 description "Increments applied to figure-of-merit value for every flap";
                 default "1000";
                 type union {
                   type string {
                     pattern "<.*>|$.*";
                   }
                   type uint32 {
                     range "1000 .. 20000";
                   }
                 }
               }
             }
             leaf neighbor {
               description "BFD neighbor address";
               type jt:ipaddr;
             }
             leaf local-address {
               description "BFD local address";
               type jt:ipaddr;
             }
             leaf holddown-interval {
               description "Time to hold the session-UP notification to the client";
               units "milliseconds";
               type union {
                 type string {
                   pattern "<.*>|$.*";
                 }
                 type uint32 {
                   range "0 .. 255000";
                 }
               }
             }
           }
           leaf minimum-links {
             description "Minimum number of aggregated links";
             type union {
               type string {
                 pattern "<.*>|$.*";
               }
               type uint16;
             }
           }
          //  container minimum-bandwidth {
          //    presence "enable minimum-bandwidth";
          //    description "Minimum bandwidth configured for aggregated bundle";
          //    // uses apply-advanced;
          //    leaf bw-value {
          //      description "Bandwidth value";
          //      default "1";
          //      type union {
          //        type uint64;
          //        type string {
          //          pattern "<.*>|$.*";
          //        }
          //      }
          //    }
          //    leaf bw-unit {
          //      description "Bandwidth unit";
          //      type enumeration {
          //        enum "bps" {
          //          description "Links are in bits per sec";
          //        }
          //        enum "kbps" {
          //          description "Links are in kilo bits per sec";
          //        }
          //        enum "mbps" {
          //          description "Links are in mega bits per sec";
          //        }
          //        enum "gbps" {
          //          description "Links are in giga bits per sec ";
          //        }
          //      }
          //    }
          //  }
          //  container targeted-options {
          //    presence "enable targeted-options";
          //    description "Targeting specific options";
          //    // uses apply-advanced;
          //    leaf type {
          //      description "Targeting type of AE bundle";
          //      type enumeration {
          //        enum "auto" {
          //          description "Targeting type is Auto";
          //        }
          //        enum "manual" {
          //          description "Targeting type is Manual";
          //        }
          //      }
          //    }
          //    choice redundancy_choice {
          //      case case_1 {
          //        leaf logical-interface-fpc-redundancy {
          //          description "Enable FPC redundancy for logical interfaces";
          //          type empty;
          //        }
          //      }
          //      case case_2 {
          //        leaf logical-interface-chassis-redundancy {
          //          description "Enable CHASSIS redundancy for logical interfaces";
          //          type empty;
          //        }
          //      }
          //    }
          //    container rebalance-periodic {
          //      presence "enable rebalance-periodic";
          //      // uses apply-advanced;
          //      leaf start-time {
          //        description "Start time of the rebalance operation ( Wall clock time )";
          //        type jt:time-of-day;
          //      }
          //      leaf interval {
          //        description "Interval of the rebalance operation in hrs";
          //        type union {
          //          type string {
          //            pattern "<.*>|$.*";
          //          }
          //          type uint32 {
          //            range "1 .. 24";
          //          }
          //        }
          //      }
          //    }
          //    leaf rebalance-subscriber-granularity {
          //      description "Max subscriber aggregate weight";
          //      type union {
          //        type string {
          //          pattern "<.*>|$.*";
          //        }
          //        type uint32 {
          //          range "1 .. 65535";
          //        }
          //      }
          //    }
          //  }
          //  choice redundancy_choice {
          //    case case_1 {
          //      leaf logical-interface-fpc-redundancy {
          //        description "Enable FPC redundancy for logical interfaces";
          //        type empty;
          //      }
          //    }
          //    case case_2 {
          //      leaf logical-interface-chassis-redundancy {
          //        description "Enable CHASSIS redundancy for logical interfaces";
          //        type empty;
          //      }
          //    }
          //  }
          //  container rebalance-periodic {
          //    // uses apply-advanced;
          //    leaf start-time {
          //      description "Start time of the rebalance operation ( Wall clock time )";
          //      type jt:time-of-day;
          //    }
          //    leaf interval {
          //      description "Interval of the rebalance operation in hrs";
          //      type union {
          //        type string {
          //          pattern "<.*>|$.*";
          //        }
          //        type uint32 {
          //          range "1 .. 24";
          //        }
          //      }
          //    }
          //  }
          //  leaf pad-to-minimum-frame-size {
          //    description "Pad Tx vlan tagged frame to minimum of 68 bytes";
          //    type empty;
          //  }
           leaf link-speed {
             description "Link speed of individual interface that joins the AE";
             type enumeration {
               enum "10m" {
                 description "Links are 10M";
               }
               enum "100m" {
                 description "Links are 100M";
               }
               enum "1g" {
                 description "Links are 1G";
               }
               enum "2.5g" {
                 description "Links are 2.5G";
               }
               enum "5g" {
                 description "Links are 5G";
               }
               enum "8g" {
                 description "Links are 8G";
               }
               enum "10g" {
                 description "Links are 10G";
               }
               enum "25g" {
                 description "Links are 25G";
               }
               enum "40g" {
                 description "Links are 40G";
               }
               enum "50g" {
                 description "Links are 50G";
               }
               enum "80g" {
                 description "Links are 80G";
               }
               enum "100g" {
                 description "Links are 100G";
               }
               enum "200g" {
                 description "Links are 200G";
               }
               enum "400g" {
                 description "Links are 400G";
               }
               enum "800g" {
                 description "Links are 800G";
               }
               enum "oc192" {
                 description "Links are OC-192";
               }
               enum "mixed" {
                 description "Links are various speeds";
               }
             }
           }
          //  container local-bias {
          //    presence "enable local-bias";
          //    description "Turn on local bias functionality";
          //    // uses apply-advanced;
          //    leaf disable {
          //      description "Disable local-bias";
          //      type empty;
          //    }
          //  }
          //  leaf resilient-hash {
          //    description "Turn on resilient-hash";
          //    type empty;
          //  }
          //  container dlb {
          //    description "Enable DLB on LAG";
          //    // uses apply-advanced;
          //    choice mode {
          //      case case_1 {
          //        leaf per-packet {
          //          description "Per-packet link assignment";
          //          type empty;
          //        }
          //      }
          //      case case_2 {
          //        leaf assigned-flow {
          //          description "Fixed link assignment";
          //          type empty;
          //        }
          //      }
          //      case case_3 {
          //        container flowlet {
          //          presence "enable flowlet";
          //          description "Inactivity-based link assignment";
          //          // uses apply-advanced;
          //          leaf inactivity-interval {
          //            description " Minimum inactivity interval in micro-seconds for link re-assignment";
          //            default "256";
          //            type union {
          //              type string {
          //                pattern "<.*>|$.*";
          //              }
          //              type uint32;
          //            }
          //          }
          //        }
          //      }
          //    }
          //  }
           container lacp {
             description "Link Aggregation Control Protocol configuration";
             // uses apply-advanced;
             choice mode {
               case case_1 {
                 leaf active {
                   description "Initiate transmission of LACP packets";
                   type empty;
                 }
               }
               case case_2 {
                 leaf passive {
                   description "Respond to LACP packets";
                   type empty;
                 }
               }
             }
             leaf periodic {
               description "Timer interval for periodic transmission of LACP packets";
               type enumeration {
                 enum "fast" {
                   description "Receive packets every second";
                 }
                 enum "slow" {
                   description "Receive packets every 30 seconds";
                 }
               }
             }
             leaf multiplier {
               description "LACP timeout detection multiplier";
               type union {
                 type string {
                   pattern "<.*>|$.*";
                 }
                 type uint32 {
                   range "3 .. 30";
                 }
               }
             }
             leaf fast-failover {
               description "To turn on LACP fast-failover";
               type empty;
             }
             container link-protection {
               presence "enable link-protection";
               // uses apply-advanced;
               leaf disable {
                 description "To turn off LACP link-protection";
                 type empty;
               }
               choice mode {
                 case case_1 {
                   leaf revertive {
                     description "Switch links when better priority link comes up";
                     type empty;
                   }
                 }
                 case case_2 {
                   leaf non-revertive {
                     description "Do not switch links when better priority link comes up";
                     type empty;
                   }
                 }
               }
               container rtg-config {
                 presence "enable rtg-config";
                 description "RTG Feature enable on AE";
                 // uses apply-advanced;
                 leaf preempt-cutover-timer {
                   description "RTG preempt-cutover-timer in seconds";
                   default "1";
                   type union {
                     type string {
                       pattern "<.*>|$.*";
                     }
                     type uint32 {
                       range "0 .. 255";
                     }
                   }
                 }
               }
             }
             leaf accept-data {
               description "Keep receiving traffic even when LACP goes down";
               type empty;
             }
             leaf sync-reset {
               description "On minimum-link failure notify out of sync to peer";
               type enumeration {
                 enum "disable" {
                   description "To disable minimum-link failure handling at LACP level";
                 }
                 enum "enable" {
                   description "To enable minimum-link failure handling at LACP level";
                 }
               }
             }
             leaf system-priority {
               description "Priority of the system (0 ... 65535)";
               type string;
             }
             leaf system-id {
               description "Node's System ID, encoded as a MAC address";
               type jt:mac-addr;
             }
             leaf admin-key {
               description "Node's administrative key";
               type union {
                 type uint16;
                 type string {
                   pattern "<.*>|$.*";
                 }
               }
             }
             container hold-time {
               description "Hold time for link up and link down for AE link members";
               leaf up {
                 description "Link up hold time for the AE link members";
                 units "seconds";
                 type union {
                   type string {
                     pattern "<.*>|$.*";
                   }
                   type uint16 {
                     range "1 .. 6000";
                   }
                 }
               }
             }
             leaf aggregate-wait-time {
               description "Aggregate wait time for the AE";
               units "seconds";
               type union {
                 type string {
                   pattern "<.*>|$.*";
                 }
                 type uint16 {
                   range "0 .. 1800";
                 }
               }
             }
             leaf force-up {
               description "Forceup AE interface with LACP";
               type empty;
             }
             leaf no-peer-loopback-validation {
               description "Skip MCLAG peer loop back validation for LACP PDUs on Forceup AE interface";
               type empty;
             }
           }
           list link-protection-sub-group {
             key name;
             ordered-by user;
             description "Link Protection subgroup configuration";
             leaf name {
               description "Name of the subgroup";
               type string {
                 length "2 .. 64";
               }
             }
             // uses apply-advanced;
             choice type {
               case case_1 {
                 leaf primary {
                   description "Primary subgroup for N:N link-protection mode";
                   type empty;
                 }
               }
               case case_2 {
                 leaf backup {
                   description "Backup subgroup for N:N link-protection mode";
                   type empty;
                 }
               }
             }
           }
           container ethernet-switch-profile {
             description "Ethernet virtual LAN/media access control-level options";
             // uses apply-advanced;
             leaf-list tag-protocol-id {
               ordered-by user;
               description "IEEE 802.1q Tag Protocol Identifier values for VLAN-tagged frames";
               type string;
             }
             container storm-control {
               description "Storm control profile name to bind";
               // uses apply-advanced;
               leaf profile-name {
                 description "Profile name";
                 type string;
               }
             }
             leaf mac-learn-enable {
               description "Learn MAC addresses dynamically";
               type empty;
             }
           }
           container mc-ae {
             description "Multi-chassis aggregation (MC-AE) network device configuration";
             // uses apply-advanced;
             leaf mc-ae-id {
               description "MC-AE group id";
               type union {
                 type string {
                   pattern "<.*>|$.*";
                 }
                 type uint16 {
                   range "1 .. 65535";
                 }
               }
             }
             leaf redundancy-group {
               description "Redundancy group id";
               type union {
                 type string {
                   pattern "<.*>|$.*";
                 }
                 type uint32 {
                   range "1 .. 4294967294";
                 }
               }
             }
             leaf chassis-id {
               description "Chassis id of MC-AE network device";
               type union {
                 type string {
                   pattern "<.*>|$.*";
                 }
                 type uint16 {
                   range "0 .. 1";
                 }
               }
             }
             leaf mode {
               description "Mode of the MC-AE";
               type enumeration {
                 enum "active-standby" {
                   description "MC-AE in active-standby mode";
                 }
                 enum "active-active" {
                   description "MC-AE in active-active mode";
                 }
               }
             }
             leaf status-control {
               description "Status of the MC-AE chassis";
               type enumeration {
                 enum "active" {
                   description "Chassis is Active";
                 }
                 enum "standby" {
                   description "Chassis is Standby";
                 }
               }
             }
             leaf switchover-mode {
               description "Switchover mode";
               type enumeration {
                 enum "revertive" {
                   description "Switch mcae node when preferred link comes up";
                 }
                 enum "non-revertive" {
                   description "Do not switch mcae node when preferred link comes up";
                 }
               }
             }
             leaf revert-time {
               description "Wait interval before performing switchover";
               default "3";
               units "minute";
               type union {
                 type string {
                   pattern "<.*>|$.*";
                 }
                 type uint32 {
                   range "1 .. 10";
                 }
               }
             }
             leaf init-delay-time {
               description "Init delay timer for mcae sm for min traffic loss";
               units "seconds";
               type union {
                 type string {
                   pattern "<.*>|$.*";
                 }
                 type uint16 {
                   range "1 .. 6000";
                 }
               }
             }
             leaf recovery-delay-time {
               description "Delay timer for bringing up ICL, ICCP";
               units "seconds";
               type union {
                 type string {
                   pattern "<.*>|$.*";
                 }
                 type uint16 {
                   range "1 .. 6000";
                 }
               }
             }
             leaf enhanced-convergence {
               description "Optimized convergence time for mcae";
               type empty;
             }
             container events {
               presence "enable events";
               description "MCAE related events";
               // uses apply-advanced;
               container iccp-peer-down {
                 presence "enable iccp-peer-down";
                 description "Define behavior in the event of ICCP peer down";
                 // uses apply-advanced;
                 leaf force-icl-down {
                   description "Bring down ICL logical interface";
                   type empty;
                 }
                 leaf prefer-status-control-active {
                   description "Keep this node up (recommended only on status-control active)";
                   type empty;
                 }
               }
             }
           }
           leaf share-standby {
             description "Share the resources with standby ports, needs FPC reboot to take effect";
             type empty;
           }
         }
        //  container es-options {
        //    description "ES PIC interface-specific options";
        //    // uses apply-advanced;
        //    leaf backup-interface {
        //      description "Name of backup interface";
        //      type union {
        //        type jt:interface-device;
        //        type string {
        //          pattern "<.*>|$.*";
        //        }
        //      }
        //    }
        //  }
        //  container dsl-options {
        //    description "DSL interface-specific options";
        //    // uses apply-advanced;
        //    leaf operating-mode {
        //      description "DSL operating mode";
        //      type enumeration {
        //        enum "auto" {
        //          description "Autonegotiate mode";
        //        }
        //        enum "ansi-dmt" {
        //          description "ANSI T1.413 Issue II mode";
        //        }
        //        enum "itu-dmt" {
        //          description "ITU G.992.1 mode";
        //        }
        //        enum "etsi" {
        //          description "ETSI TS 101 388 V1.3.1 mode";
        //        }
        //        enum "itu-annexb-ur2" {
        //          description "ITU G.992.1 UR-2 mode";
        //        }
        //        enum "itu-annexb-non-ur2" {
        //          description "ITU G.992.1 Non UR-2 mode";
        //        }
        //        enum "itu-dmt-bis" {
        //          description "ITU G.992.3 mode";
        //        }
        //        enum "adsl2plus" {
        //          description "ITU G.992.5 mode";
        //        }
        //        enum "annexm-itu-dmt-bis" {
        //          description "AnnexM ITU G.992.3 mode";
        //        }
        //        enum "annexm-adsl2plus" {
        //          description "AnnexM ITU G.992.5 mode";
        //        }
        //      }
        //    }
        //  }
        //  container vdsl-options {
        //    description "VDSL interface-specific options";
        //    // uses apply-advanced;
        //    leaf vdsl-profile {
        //      description "VDSL profile";
        //      type enumeration {
        //        enum "auto" {
        //          description "Auto";
        //        }
        //        enum "8a" {
        //          description "Profile 8a";
        //        }
        //        enum "8b" {
        //          description "Profile 8b";
        //        }
        //        enum "8c" {
        //          description "Profile 8c";
        //        }
        //        enum "8d" {
        //          description "Profile 8d";
        //        }
        //        enum "12a" {
        //          description "Profile 12a";
        //        }
        //        enum "12b" {
        //          description "Profile 12b";
        //        }
        //        enum "17a" {
        //          description "Profile 17a";
        //        }
        //      }
        //    }
        //    leaf sra {
        //      description "DSL SRA";
        //      default "disable";
        //      type enumeration {
        //        enum "enable" {
        //          description "Enable SRA";
        //        }
        //        enum "disable" {
        //          description "Disable SRA";
        //        }
        //      }
        //    }
        //    leaf v43 {
        //      description "DSL V43 tones";
        //      default "enable";
        //      type enumeration {
        //        enum "enable" {
        //          description "Enable V43";
        //        }
        //        enum "disable" {
        //          description "Disable V43";
        //        }
        //      }
        //    }
        //    leaf sos {
        //      description "Enable SOS";
        //      type empty;
        //    }
        //  }
        //  container dsl-sfp-options {
        //    description "DSL SFP options";
        //    // uses apply-advanced;
        //    container adsl-options {
        //      description "ADSL options";
        //      // uses apply-advanced;
        //      leaf vpi {
        //        description "Virtual path identifier";
        //        type union {
        //          type string {
        //            pattern "<.*>|$.*";
        //          }
        //          type uint32 {
        //            range "0 .. 255";
        //          }
        //        }
        //      }
        //      leaf vci {
        //        description "Virtual circuit identifier";
        //        type union {
        //          type string {
        //            pattern "<.*>|$.*";
        //          }
        //          type uint32 {
        //            range "32 .. 65535";
        //          }
        //        }
        //      }
        //      leaf encap {
        //        description "Encapsulation";
        //        type enumeration {
        //          enum "bypass" {
        //            description "Bypass";
        //          }
        //          enum "llcsnap-bridged-802dot1q" {
        //            description "LLCSNAP bridged 802.1q";
        //          }
        //          enum "llcsnap-routed-ip" {
        //            description "LLCSNAP routed ip";
        //          }
        //          enum "vc-mux-bridged" {
        //            description "VC MUX bridged";
        //          }
        //          enum "vc-mux-routed-ip" {
        //            description "VC MUX routed ip";
        //          }
        //          enum "generic" {
        //            description "Generic";
        //          }
        //        }
        //      }
        //      leaf annex {
        //        description "Annex type";
        //        type enumeration {
        //          enum "auto" {
        //            description "Annex type auto";
        //          }
        //          enum "annexj-off" {
        //            description "Annex type annexj turn off";
        //          }
        //        }
        //      }
        //    }
        //    container vdsl-options {
        //      description "VDSL options";
        //      // uses apply-advanced;
        //      leaf profile {
        //        description "VDSL profile";
        //        type enumeration {
        //          enum "auto" {
        //            description "Automatic";
        //          }
        //          enum "8a" {
        //            description "Profile 8a";
        //          }
        //          enum "8b" {
        //            description "Profile 8b";
        //          }
        //          enum "8c" {
        //            description "Profile 8c";
        //          }
        //          enum "8d" {
        //            description "Profile 8d";
        //          }
        //          enum "12a" {
        //            description "Profile 12a";
        //          }
        //          enum "12b" {
        //            description "Profile 12b";
        //          }
        //          enum "17a" {
        //            description "Profile 17a";
        //          }
        //          enum "30a" {
        //            description "Profile 30a";
        //          }
        //        }
        //      }
        //      leaf carrier {
        //        description "Carrier setting";
        //        type enumeration {
        //          enum "auto" {
        //            description "Automatic";
        //          }
        //          enum "a43" {
        //            description "Carrier A43";
        //          }
        //          enum "b43" {
        //            description "Carrier B43";
        //          }
        //        }
        //      }
        //    }
        //    container gfast-options {
        //      description "G.fast options";
        //      // uses apply-advanced;
        //      leaf carrier {
        //        description "Carrier setting";
        //        type enumeration {
        //          enum "a43" {
        //            description "Carrier A43";
        //          }
        //          enum "a43c" {
        //            description "Carrier A43C";
        //          }
        //          enum "b43" {
        //            description "Carrier B43";
        //          }
        //          enum "b43c" {
        //            description "Carrier B43C";
        //          }
        //        }
        //      }
        //    }
        //  }
        //  container shdsl-options {
        //    description "SHDSL interface-specific options";
        //    // uses apply-advanced;
        //    leaf annex {
        //      description "Type of SHDSL annex";
        //      default "annex-b";
        //      type enumeration {
        //        enum "annex-a" {
        //          description "Annex-a PIC";
        //        }
        //        enum "annex-b" {
        //          description "Annex-b PIC";
        //        }
        //        enum "annex-f" {
        //          description "Annex-f PIC";
        //        }
        //        enum "annex-g" {
        //          description "Annex-g PIC";
        //        }
        //        enum "annex-auto" {
        //          description "Annex-auto PIC";
        //        }
        //      }
        //    }
        //    leaf line-rate {
        //      description "SHDSL line rate";
        //      type string;
        //    }
        //    leaf loopback {
        //      description "Loopback mode";
        //      type enumeration {
        //        enum "local" {
        //          description "Local loopback";
        //        }
        //        enum "remote" {
        //          description "Remote loopback";
        //        }
        //      }
        //    }
        //    container snr-margin {
        //      presence "enable snr-margin";
        //      description "Signal to noise ratio margin";
        //      // uses apply-advanced;
        //      leaf current {
        //        description "Current signal to noise ratio margin";
        //        units "dB";
        //        type string;
        //      }
        //      leaf snext {
        //        description "SNEXT signal to noise ratio margin";
        //        units "dB";
        //        type string;
        //      }
        //    }
        //  }
        //  container data-input {
        //    description "Configuration for drop-insert data input";
        //    // uses apply-advanced;
        //    choice input-choice {
        //      case case_1 {
        //        leaf system {
        //          description "Data sourced from system";
        //          type empty;
        //        }
        //      }
        //      case case_2 {
        //        leaf interface {
        //          description "Interface that acts as data source";
        //          type union {
        //            type jt:interface-device;
        //            type string {
        //              pattern "<.*>|$.*";
        //            }
        //          }
        //        }
        //      }
        //    }
        //  }
        //  container switch-options {
        //    description "Front end ports configuration";
        //    // uses apply-advanced;
        //    list switch-port {
        //      key name;
        //      leaf name {
        //        description "Front end port number";
        //        type union {
        //          type string {
        //            pattern "<.*>|$.*";
        //          }
        //          type uint32 {
        //            range "0 .. 15";
        //          }
        //        }
        //      }
        //      // uses apply-advanced;
        //      choice auto-negotiation-choice {
        //        leaf auto-negotiation {
        //          description "Enable auto-negotiation";
        //          type empty;
        //        }
        //        leaf no-auto-negotiation {
        //          description "Don't enable auto-negotiation";
        //          type empty;
        //        }
        //      }
        //      leaf link-mode {
        //        description "Link operational mode";
        //        type enumeration {
        //          enum "half-duplex" {
        //            description "Half-duplex operation";
        //          }
        //          enum "full-duplex" {
        //            description "Full-duplex operation";
        //          }
        //        }
        //      }
        //      leaf speed {
        //        description "Link speed";
        //        type enumeration {
        //          enum "10m" {
        //          }
        //          enum "100m" {
        //          }
        //          enum "1g" {
        //          }
        //        }
        //      }
        //      leaf vlan-id {
        //        description "VLAN ID for this port";
        //        type union {
        //          type string {
        //            pattern "<.*>|$.*";
        //          }
        //          type uint32 {
        //            range "0 .. 4094";
        //          }
        //        }
        //      }
        //      leaf cascade-port {
        //        description "Port externally connected to another cascade port";
        //        type empty;
        //      }
        //    }
        //  }
        //  container container-options {
        //    description "Container interface specific options";
        //    // uses apply-advanced;
        //    container container-type {
        //      presence "enable container-type";
        //      description "Protocol type of the container interface";
        //      // uses apply-advanced;
        //      choice container-type-choice {
        //        case case_1 {
        //          container aps {
        //            description "APS options on the container";
        //            presence "enable aps";
        //            uses aps_type;
        //          }
        //        }
        //      }
        //    }
        //    container member-interface-type {
        //      description "Link type of members of container";
        //      // uses apply-advanced;
        //      choice member_interface_type_choice {
        //        case case_1 {
        //          container sonet {
        //            // uses apply-advanced;
        //            leaf member-interface-speed {
        //              description "Link speed of members of container";
        //              type enumeration {
        //                enum "oc3" {
        //                  description "Links are OC-3";
        //                }
        //                enum "oc12" {
        //                  description "Links are OC-12";
        //                }
        //                enum "oc48" {
        //                  description "Links are OC-48";
        //                }
        //                enum "oc192" {
        //                  description "Links are OC-192";
        //                }
        //                enum "oc768" {
        //                  description "Links are OC-768";
        //                }
        //                enum "mixed" {
        //                  description "Links are of different speeds";
        //                }
        //              }
        //            }
        //          }
        //        }
        //        case case_2 {
        //          container atm {
        //            // uses apply-advanced;
        //            leaf member-interface-speed {
        //              description "Link speed of members of container";
        //              type enumeration {
        //                enum "oc3" {
        //                  description "Links are OC-3";
        //                }
        //                enum "oc12" {
        //                  description "Links are OC-12";
        //                }
        //                enum "oc48" {
        //                  description "Links are OC-48";
        //                }
        //              }
        //            }
        //          }
        //        }
        //        case case_3 {
        //          container channelized-sonet {
        //            // uses apply-advanced;
        //            leaf member-interface-speed {
        //              description "Link speed of members of container";
        //              type enumeration {
        //                enum "coc3" {
        //                  description "Links are COC-3";
        //                }
        //                enum "coc12" {
        //                  description "Links are COC-12";
        //                }
        //                enum "coc48" {
        //                  description "Links are COC-48";
        //                }
        //                enum "coc192" {
        //                  description "Links are COC-192";
        //                }
        //                enum "coc768" {
        //                  description "Links are COC-768";
        //                }
        //              }
        //            }
        //          }
        //        }
        //        case case_4 {
        //          container channelized-sdh {
        //            // uses apply-advanced;
        //            leaf member-interface-speed {
        //              description "Link speed of members of container";
        //              type enumeration {
        //                enum "cstm1" {
        //                  description "Links are cstm-1";
        //                }
        //                enum "cstm4" {
        //                  description "Links are cstm-4";
        //                }
        //                enum "cstm16" {
        //                  description "Links are cstm-16";
        //                }
        //                enum "coc64" {
        //                  description "Links are cstm-64";
        //                }
        //                enum "cstm256" {
        //                  description "Links are cstm256";
        //                }
        //              }
        //            }
        //          }
        //        }
        //      }
        //    }
        //    container redundancy {
        //      description "Container interface redundancy options";
        //      // uses apply-advanced;
        //      container hold-time {
        //        description "Hold time for link up and link down";
        //        leaf up {
        //          description "Link up hold time";
        //          units "milliseconds";
        //          type union {
        //            type string {
        //              pattern "<.*>|$.*";
        //            }
        //            type uint32 {
        //              range "0 .. 65534";
        //            }
        //          }
        //        }
        //        leaf down {
        //          description "Link down hold time";
        //          units "milliseconds";
        //          type union {
        //            type string {
        //              pattern "<.*>|$.*";
        //            }
        //            type uint32 {
        //              range "0 .. 65534";
        //            }
        //          }
        //        }
        //      }
        //    }
        //    leaf-list container-list {
        //      ordered-by user;
        //      description "List of container interfaces this member link is associated to";
        //      type union {
        //        type jt:interface-device;
        //        type string {
        //          pattern "<.*>|$.*";
        //        }
        //      }
        //    }
        //    choice redundancy-type {
        //      case case_1 {
        //        choice aps-redundancy {
        //          case case_1 {
        //            leaf primary {
        //              description "This member link is primary interface of the container";
        //              type empty;
        //            }
        //          }
        //          case case_2 {
        //            leaf standby {
        //              description "This member link is standby interface of the container";
        //              type empty;
        //            }
        //          }
        //        }
        //      }
        //    }
        //    leaf fast-aps {
        //      description "Fast APS switch";
        //      type empty;
        //    }
        //    leaf allow-configuration-override {
        //      description "Allow physical configuration of member link to override container configuration";
        //      type empty;
        //    }
        //  }
        //  container layer2-policer {
        //    description "Layer2 policing for interface";
        //    // uses apply-advanced;
        //    choice layer2-input-policer-choice {
        //      case case_1 {
        //        leaf input-policer {
        //          description "Two-color policer for received packets";
        //          type string;
        //        }
        //      }
        //      case case_2 {
        //        leaf input-hierarchical-policer {
        //          description "Hierarchical policer for received packets";
        //          type string;
        //        }
        //      }
        //    }
        //  }
        //  list unit {
        //    key name;
        //    description "Logical interface";
        //    leaf name {
        //      type string;
        //    }
        //    // uses apply-advanced;
        //    leaf interface-tag {
        //      description "Interface tag name";
        //      type string {
        //        length "1 .. 64";
        //      }
        //    }
        //    container policer-overhead {
        //      description "Policer overhead adjustment for this unit";
        //      // uses apply-advanced;
        //      leaf policer-overhead-value {
        //        description "Policer overhead bytes to be accounted in ingress and egress";
        //        units "bytes";
        //        type union {
        //          type string {
        //            pattern "<.*>|$.*";
        //          }
        //          type int32;
        //        }
        //      }
        //      leaf ingress {
        //        description "Ingress value in bytes";
        //        units "bytes";
        //        type union {
        //          type string {
        //            pattern "<.*>|$.*";
        //          }
        //          type int32 {
        //            range "-64 .. 64";
        //          }
        //        }
        //      }
        //      leaf egress {
        //        description "Egress value in bytes";
        //        units "bytes";
        //        type union {
        //          type string {
        //            pattern "<.*>|$.*";
        //          }
        //          type int32 {
        //            range "-64 .. 64";
        //          }
        //        }
        //      }
        //    }
        //    leaf alias {
        //      description "Interface alias";
        //      type string;
        //    }
        //    leaf enhanced-convergence {
        //      description "Optimize convergence time for L3";
        //      type empty;
        //    }
        //    leaf proxy-macip-advertisement {
        //      description "Proxy advertisement of type 2 MAC+IP route for EVPN";
        //      type empty;
        //    }
        //    leaf virtual-gateway-accept-data {
        //      description "Accept packets destined for virtual gateway address";
        //      type empty;
        //    }
        //    container peer-psd {
        //      presence "enable peer-psd";
        //      description "Peer psd";
        //      leaf psd-name {
        //        description "Peer psd name";
        //        type string;
        //      }
        //    }
        //    container peer-interface {
        //      presence "enable peer-interface";
        //      description "Peer interface";
        //      // uses apply-advanced;
        //      leaf interface-name {
        //        description "Peer interface name";
        //        type union {
        //          type jt:interface-unit;
        //          type string {
        //            pattern "<.*>|$.*";
        //          }
        //        }
        //      }
        //    }
        //    container interface-shared-with {
        //      presence "enable interface-shared-with";
        //      description "Specify which PSD owns this logical interface";
        //      // uses apply-advanced;
        //      leaf psd-name {
        //        description "Name of protected system domain (psd[1-31], ex. psd2)";
        //        type string {
        //        }
        //      }
        //    }
        //    choice enable-disable {
        //      case case_1 {
        //        leaf disable {
        //          description "Disable this logical interface";
        //          type empty;
        //        }
        //      }
        //    }
        //    leaf passive-monitor-mode {
        //      description "Use interface to tap packets from another router";
        //      type empty;
        //    }
        //    leaf per-session-scheduler {
        //      description "Enable per-session queuing on an IQ2 interface";
        //      type empty;
        //    }
        //    container account-layer2-overhead {
        //      presence "enable account-layer2-overhead";
        //      description "Account layer2 overhead in IFL byte statistics";
        //      // uses apply-advanced;
        //      leaf overhead-value {
        //        description "Layer2 overhead bytes to be accounted in ingress and egress";
        //        units "bytes";
        //        type union {
        //          type string {
        //            pattern "<.*>|$.*";
        //          }
        //          type int8 {
        //            range "-128 .. 127";
        //          }
        //        }
        //      }
        //      leaf ingress {
        //        description "Layer2 overhead bytes to be accounted in ingress";
        //        units "bytes";
        //        type union {
        //          type string {
        //            pattern "<.*>|$.*";
        //          }
        //          type int8 {
        //            range "-128 .. 127";
        //          }
        //        }
        //      }
        //      leaf egress {
        //        description "Layer2 overhead bytes to be accounted in egress";
        //        units "bytes";
        //        type union {
        //          type string {
        //            pattern "<.*>|$.*";
        //          }
        //          type int8 {
        //            range "-128 .. 127";
        //          }
        //        }
        //      }
        //    }
        //    container forwarding-class-accounting {
        //      presence "enable forwarding-class-accounting";
        //      description "Configure Forwarding-class-accounting parameters for IFL ";
        //      // uses apply-advanced;
        //      leaf direction {
        //        description "Direction of the traffic to be accounted for IFL";
        //        type enumeration {
        //          enum "ingress" {
        //            description "Enable forwarding-class-accounting for ingress traffic";
        //          }
        //          enum "egress" {
        //            description "Enable forwarding-class-accounting for egress traffic";
        //          }
        //          enum "both" {
        //            description "Enable forwarding-class-accounting for both directions";
        //          }
        //        }
        //      }
        //      container enhanced {
        //        presence "enable enhanced";
        //        // uses apply-advanced;
        //        leaf traffic-type {
        //          description "Traffic-type to be accounted for forwarding-class-accounting for IFL";
        //          type enumeration {
        //            enum "unicast-statistics" {
        //              description "Count only unicast traffic for forwarding-class-accounting for IFL ";
        //            }
        //            enum "multicast-statistics" {
        //              description "Count only multicast traffic for forwarding-class-accounting for IFL";
        //            }
        //          }
        //        }
        //        leaf family {
        //          description "Protocol traffic to be accounted for forwarding-class-accounting for IFL";
        //          type enumeration {
        //            enum "inet" {
        //              description "Enable forwarding-class-accounting for IPv4 family only for IFL";
        //            }
        //            enum "inet6" {
        //              description "Enable forwarding-class-accounting for IPv6 family only for IFL";
        //            }
        //            enum "both" {
        //              description "Enable forwarding-class-accounting for both IPv4 and IPv6 family for IFL";
        //            }
        //          }
        //        }
        //        leaf direction {
        //          description "Direction of the traffic to be accounted for forwarding-class-accounting for IFL";
        //          type enumeration {
        //            enum "ingress" {
        //              description "Enable forwarding-class-accounting for ingress traffic for IFL";
        //            }
        //            enum "egress" {
        //              description "Enable forwarding-class-accounting for egress traffic for IFL";
        //            }
        //            enum "both" {
        //              description "Enable forwarding-class-accounting for both ingress and egress traffic for IFL";
        //            }
        //          }
        //        }
        //        leaf overhead-bytes {
        //          description "Per octet overhead bytes to be accounted for forwarding-class-accounting for IFL ";
        //          default "0";
        //          type union {
        //            type string {
        //              pattern "<.*>|$.*";
        //            }
        //            type uint32 {
        //              range "0 .. 255";
        //            }
        //          }
        //        }
        //      }
        //    }
        //    leaf clear-dont-fragment-bit {
        //      description "Clear DF bit in packet (AS PIC and J-series only as well as MIF)";
        //      type empty;
        //    }
        //    leaf packet-inject-enable {
        //      description "Enable packet inject functionality on this IFL";
        //      type empty;
        //    }
        //    leaf reassemble-packets {
        //      description "Do reassembly of fragmented tunnel packets";
        //      type empty;
        //    }
        //    container ip-address-owner {
        //      description "Define the owner for IP addresses hosted on this interface";
        //      choice ip-address-owner-options {
        //        case case_1 {
        //          leaf service-plane {
        //            description "IP address defined on this interface is hosted by service plane";
        //            type empty;
        //          }
        //        }
        //        case case_2 {
        //          leaf routing-engine {
        //            description "IP address defined on this interface is hosted by routing engine";
        //            type empty;
        //          }
        //        }
        //      }
        //    }
        //    container services-options {
        //      description "Services interface-specific options";
        //      // uses apply-advanced;
        //    }
        //    container rpm {
        //      description "Enable RPM service on this interface";
        //      // uses apply-advanced;
        //      choice rpm_or_twamp {
        //        case case_1 {
        //          choice rpm-type {
        //            case case_1 {
        //              leaf client {
        //                description "Client mode";
        //                type empty;
        //              }
        //            }
        //            case case_2 {
        //              leaf server {
        //                description "Server mode";
        //                type empty;
        //              }
        //            }
        //            case case_3 {
        //              leaf client-delegate-probes {
        //                description "Client delegate probe mode";
        //                type empty;
        //              }
        //            }
        //          }
        //        }
        //        case case_2 {
        //          leaf twamp-server {
        //            description "Set TWAMP server mode on this interface";
        //            type empty;
        //          }
        //        }
        //        case case_3 {
        //          leaf twamp-client {
        //            description "Set TWAMP client mode on this interface";
        //            type empty;
        //          }
        //        }
        //      }
        //    }
        //    leaf description {
        //      description "Text description of interface";
        //      type string;
        //    }
        //    container dial-options {
        //      description "Dial options";
        //      // uses apply-advanced;
        //      choice interface_id_choice {
        //        case case_1 {
        //          leaf l2tp-interface-id {
        //            description "Identifier for group of PPP sessions";
        //            type string {
        //              length "1 .. 63";
        //            }
        //          }
        //        }
        //        case case_2 {
        //          leaf ipsec-interface-id {
        //            description "Identifier for group of dynamic peers";
        //            type string {
        //              length "1 .. 63";
        //            }
        //          }
        //        }
        //      }
        //      choice ifl_type {
        //        case case_1 {
        //          leaf dedicated {
        //            description "Use this unit for only one PPP/IPSec session";
        //            type empty;
        //          }
        //        }
        //        case case_2 {
        //          leaf shared {
        //            description "Share this unit for multiple PPP/IPSec sessions";
        //            type empty;
        //          }
        //        }
        //      }
        //    }
        //    container actual-transit-statistics {
        //      presence "enable actual-transit-statistics";
        //      description "Actual transit statistics";
        //    }
        //    list demux-source {
        //      key name;
        //      ordered-by user;
        //      description "Demux based on source address";
        //      uses demux_options_table;
        //    }
        //    list demux-destination {
        //      key name;
        //      ordered-by user;
        //      description "Demux based on destination address";
        //      uses demux_options_table;
        //    }
        //    container demux {
        //      description "Demux based on source or destination address";
        //      // uses apply-advanced;
        //      container inet {
        //        presence "enable inet";
        //        description "Family inet";
        //        // uses apply-advanced;
        //        leaf address {
        //          description "Address type";
        //          type enumeration {
        //            enum "source" {
        //              description "Demux based on source address";
        //            }
        //            enum "destination" {
        //              description "Demux based on destination address";
        //            }
        //          }
        //        }
        //        container auto-configure {
        //          description "Auto configuration";
        //          uses dynamic_ipv4_type;
        //        }
        //      }
        //      container inet6 {
        //        presence "enable inet6";
        //        description "Family inet6";
        //        // uses apply-advanced;
        //        leaf address {
        //          description "Address type";
        //          type enumeration {
        //            enum "source" {
        //              description "Demux based on source address";
        //            }
        //            enum "destination" {
        //              description "Demux based on destination address";
        //            }
        //          }
        //        }
        //        container auto-configure {
        //          description "Auto configuration";
        //          uses dynamic_ipv6_type;
        //        }
        //      }
        //    }
        //    leaf encapsulation {
        //      description "Logical link-layer encapsulation";
        //      type enumeration {
        //        enum "atm-nlpid" {
        //          description "ATM NLPID encapsulation";
        //        }
        //        enum "atm-cisco-nlpid" {
        //          description "Cisco-compatible ATM NLPID encapsulation";
        //        }
        //        enum "atm-snap" {
        //          description "ATM LLC/SNAP encapsulation";
        //        }
        //        enum "atm-vc-mux" {
        //          description "ATM VC multiplexing";
        //        }
        //        enum "atm-ccc-vc-mux" {
        //          description "ATM VC for CCC";
        //        }
        //        enum "atm-tcc-vc-mux" {
        //          description "ATM VC for translational cross-connect";
        //        }
        //        enum "atm-tcc-snap" {
        //          description "ATM LLC/SNAP for translational cross-connect";
        //        }
        //        enum "atm-ccc-cell-relay" {
        //          description "ATM cell relay for CCC";
        //        }
        //        enum "vlan-vci-ccc" {
        //          description "CCC for VLAN Q-in-Q and ATM VPI/VCI interworking";
        //        }
        //        enum "ether-over-atm-llc" {
        //          description "Ethernet over ATM (LLC/SNAP) encapsulation";
        //        }
        //        enum "ether-vpls-over-atm-llc" {
        //          description "Ethernet VPLS over ATM (bridging) encapsulation";
        //        }
        //        enum "ppp-over-ether-over-atm-llc" {
        //          description "PPPoE over ATM (LLC/SNAP) encapsulation";
        //        }
        //        enum "ppp-over-ether" {
        //          description "PPPoE encapsulation";
        //        }
        //        enum "atm-ppp-vc-mux" {
        //          description "ATM PPP over raw AAL5";
        //        }
        //        enum "atm-ppp-llc" {
        //          description "ATM PPP over AAL5/LLC";
        //        }
        //        enum "atm-mlppp-llc" {
        //          description "ATM MLPPP over AAL5/LLC";
        //        }
        //        enum "frame-relay-ppp" {
        //          description "PPP over Frame Relay";
        //        }
        //        enum "frame-relay-ccc" {
        //          description "Frame Relay DLCI for CCC";
        //        }
        //        enum "frame-relay" {
        //          description "Frame Relay DLCI";
        //        }
        //        enum "frame-relay-tcc" {
        //          description "Frame Relay DLCI for translational cross-connect";
        //        }
        //        enum "frame-relay-ether-type" {
        //          description "Cisco-compatible Frame Relay Encapsulation DLCI";
        //        }
        //        enum "frame-relay-ether-type-tcc" {
        //          description "Cisco-compatible Frame Relay Encapsulation DLCI for TCC";
        //        }
        //        enum "ether-vpls-fr" {
        //          description "Ethernet VPLS over Frame Relay (bridging) encapsulation";
        //        }
        //        enum "vlan-ccc" {
        //          description "802.1q tagging for a cross-connect";
        //        }
        //        enum "ethernet-ccc" {
        //          description "Ethernet for a cross-connect";
        //        }
        //        enum "vlan-vpls" {
        //          description "VLAN virtual private LAN service";
        //        }
        //        enum "vlan-bridge" {
        //          description "VLAN layer-2 bridging";
        //        }
        //        enum "ethernet-tcc" {
        //          description "Ethernet translational cross-connect";
        //        }
        //        enum "dix" {
        //          description "Ethernet DIXv2 (RFC 894)";
        //        }
        //        enum "ethernet" {
        //          description "Ethernet II (RFC 894)";
        //        }
        //        enum "ethernet-vpls" {
        //          description "Ethernet II virtual private LAN service";
        //        }
        //        enum "ethernet-bridge" {
        //          description "Ethernet II bridging";
        //        }
        //        enum "vlan" {
        //          description "802.1q-tagged Ethernet";
        //        }
        //        enum "vlan-tcc" {
        //          description "802.1q tagging for a translational cross-connect";
        //        }
        //        enum "multilink-ppp" {
        //          description "Multilink PPP";
        //        }
        //        enum "multilink-frame-relay-end-to-end" {
        //          description "Multilink Frame Relay end-to-end (FRF.15)";
        //        }
        //        enum "ppp-ccc" {
        //          description "Serial PPP device for a cross-connect";
        //        }
        //      }
        //    }
        //    leaf gre {
        //      description "Allow GRE packets";
        //      type empty;
        //    }
        //    leaf mtu {
        //      description "Maximum transmission unit packet size";
        //      type union {
        //        type string {
        //          pattern "<.*>|$.*";
        //        }
        //        type uint32;
        //      }
        //    }
        //    choice pointedness {
        //      case case_1 {
        //        leaf point-to-point {
        //          description "Point-to-point connection";
        //          type empty;
        //        }
        //      }
        //      case case_2 {
        //        leaf multipoint {
        //          description "Multipoint connection";
        //          type empty;
        //        }
        //      }
        //    }
        //    leaf bandwidth {
        //      description "Logical unit bandwidth (informational only)";
        //      type string;
        //    }
        //    container radio-router {
        //      description "Parameters for dynamic link cost management";
        //      presence "enable radio-router";
        //      uses dynamic_ifbw_parms_type;
        //    }
        //    choice traps-choice {
        //      leaf traps {
        //        description "Enable SNMP notifications on state changes";
        //        type empty;
        //      }
        //      leaf no-traps {
        //        description "Don't enable SNMP notifications on state changes";
        //        type empty;
        //      }
        //    }
        //    choice routing-services-choice {
        //      leaf routing-services {
        //        description "Enable routing services";
        //        status deprecated;
        //        type empty;
        //      }
        //      leaf no-routing-services {
        //        description "Don't enable routing services";
        //        status deprecated;
        //        type empty;
        //      }
        //    }
        //    container routing-service {
        //      description "Routing Services on this interface";
        //      // uses apply-advanced;
        //      choice enable-disable {
        //        case case_1 {
        //          leaf enable {
        //            description "Enable Routing Service";
        //            type empty;
        //          }
        //        }
        //        case case_2 {
        //          leaf disable {
        //            description "Disable Routing Service";
        //            type empty;
        //          }
        //        }
        //      }
        //    }
        //    container arp-resp {
        //      presence "enable arp-resp";
        //      description "Knob to control ARP response on the interface, default is restricted";
        //      choice arp-response-options {
        //        case case_1 {
        //          leaf unrestricted {
        //            description "Enable unrestricted ARP respone on the interface";
        //            type empty;
        //          }
        //        }
        //        case case_2 {
        //          leaf restricted {
        //            description "Enable restricted proxy ARP response on the interface";
        //            type empty;
        //          }
        //        }
        //      }
        //    }
        //    container proxy-arp {
        //      presence "enable proxy-arp";
        //      description "Enable proxy ARP on the interface, default is unrestricted";
        //      choice proxyarp-options {
        //        case case_1 {
        //          leaf unrestricted {
        //            description "Enable unrestricted proxy ARP on the interface";
        //            type empty;
        //          }
        //        }
        //        case case_2 {
        //          leaf restricted {
        //            description "Enable restricted proxy ARP on the interface";
        //            type empty;
        //          }
        //        }
        //      }
        //    }
        //    choice vlan_choice {
        //      case case_1 {
        //        leaf vlan-id {
        //          description "Virtual LAN identifier value for 802.1q VLAN tags";
        //          type string;
        //        }
        //      }
        //      case case_2 {
        //        leaf vlan-id-range {
        //          description "Virtual LAN identifier range of form vid1-vid2";
        //          type jt:vlan-range;
        //        }
        //      }
        //      case case_3 {
        //        leaf-list inner-vlan-id-swap-ranges {
        //          description "Inner vlan-id swap range(s) of form vid1-vid2 for dynamic L2 VLANs";
        //          type jt:vlan-range;
        //        }
        //      }
        //      case case_4 {
        //        leaf-list vlan-id-list {
        //          description "List of VLAN identifiers";
        //          type jt:vlan-range;
        //        }
        //      }
        //      case case_5 {
        //        leaf-list vlan-tag {
        //          ordered-by user;
        //          description "IEEE 802.1q tag list for VLAN tagged frames";
        //          status deprecated;
        //          type string;
        //        }
        //      }
        //      case case_6 {
        //        container vlan-tags {
        //          presence "enable vlan-tags";
        //          description "IEEE 802.1q tags";
        //          leaf outer {
        //            description "[tpid.]vlan-id, tpid format is 0xNNNN and is optional";
        //            type string;
        //          }
        //          choice inner_choice {
        //            case case_1 {
        //              leaf inner {
        //                description "[tpid.]vlan-id, tpid format is 0xNNNN and is optional";
        //                type string;
        //              }
        //            }
        //            case case_2 {
        //              leaf inner-range {
        //                description "[tpid.]vid1-vid2, tpid format is 0xNNNN and is optional";
        //                type string {
        //                }
        //              }
        //            }
        //            case case_3 {
        //              leaf-list inner-list {
        //                description "List of VLAN identifiers";
        //                type jt:vlan-range;
        //              }
        //            }
        //          }
        //        }
        //      }
        //    }
        //    leaf deep-vlan-qualified-learning {
        //      description "Enable qualified MAC-address learning on the specified vlan tag";
        //      type union {
        //        type string {
        //          pattern "<.*>|$.*";
        //        }
        //        type uint32 {
        //          range 3;
        //        }
        //      }
        //    }
        //    leaf native-inner-vlan-id {
        //      description "Native virtual LAN identifier for singly tagged frames";
        //      type union {
        //        type string {
        //          pattern "<.*>|$.*";
        //        }
        //        type uint32 {
        //          range "0 .. 4094";
        //        }
        //      }
        //    }
        //    container inner-vlan-id-range {
        //      description "Inner vlan-id range start <start-vlan-id> end <end-vlan-id>";
        //      leaf start {
        //        description "Inner vlan-id range's start value";
        //        type union {
        //          type string {
        //            pattern "<.*>|$.*";
        //          }
        //          type uint32 {
        //            range "32 .. 4094";
        //          }
        //        }
        //      }
        //      leaf end {
        //        description "Inner vlan-id range's end value";
        //        type union {
        //          type string {
        //            pattern "<.*>|$.*";
        //          }
        //          type uint32 {
        //            range "32 .. 4094";
        //          }
        //        }
        //      }
        //    }
        //    container accept-source-mac {
        //      description "Remote media access control address to/from which to accept traffic";
        //      // uses apply-advanced;
        //      list mac-address {
        //        key name;
        //        description "Remote MAC address";
        //        uses mac_list;
        //      }
        //    }
        //    container input-vlan-map {
        //      description "VLAN map operation on input";
        //      uses vlan_map;
        //    }
        //    container output-vlan-map {
        //      description "VLAN map operation on output";
        //      uses vlan_map;
        //    }
        //    leaf swap-by-poppush {
        //      description "Pop original vlan tag and then push a new vlan tag";
        //      type empty;
        //    }
        //    leaf receive-lsp {
        //      description "Name of incoming label-switched path";
        //      type string;
        //    }
        //    leaf transmit-lsp {
        //      description "Name of outgoing label-switched path";
        //      type string;
        //    }
        //    leaf dlci {
        //      description "Frame Relay data-link control identifier";
        //      type union {
        //        type string {
        //          pattern "<.*>|$.*";
        //        }
        //        type uint32 {
        //          range "1 .. 1022";
        //        }
        //      }
        //    }
        //    leaf multicast-dlci {
        //      description "Frame Relay data-link control identifier for multicast packets";
        //      type union {
        //        type string {
        //          pattern "<.*>|$.*";
        //        }
        //        type uint32 {
        //          range "1 .. 1022";
        //        }
        //      }
        //    }
        //    choice vci_type {
        //      case case_1 {
        //        leaf vci {
        //          description "ATM point-to-point virtual circuit identifier ([vpi.]vci)";
        //          type jt:atm-vci;
        //        }
        //      }
        //      case case_2 {
        //        leaf allow-any-vci {
        //          description "Allow all VCIs to open in atm-ccc-cell-relay mode";
        //          type empty;
        //        }
        //      }
        //      case case_3 {
        //        leaf vpi {
        //          description "ATM point-to-point virtual path identifier (vpi)";
        //          type union {
        //            type string {
        //              pattern "<.*>|$.*";
        //            }
        //            type uint32 {
        //              range "0 .. 255";
        //            }
        //          }
        //        }
        //      }
        //      case case_4 {
        //        leaf trunk-id {
        //          description "ATM trunk identifier";
        //          type union {
        //            type string {
        //              pattern "<.*>|$.*";
        //            }
        //            type uint32 {
        //              range "0 .. 31";
        //            }
        //          }
        //        }
        //      }
        //    }
        //    leaf no-vpivci-swapping {
        //      description "Do not swap VPI/VCI for Cell Relay";
        //      type empty;
        //    }
        //    choice psn_vci_type {
        //      case case_1 {
        //        leaf psn-vci {
        //          description "PSN VCI";
        //          type jt:atm-vci;
        //        }
        //      }
        //      case case_2 {
        //        leaf psn-vpi {
        //          description "PSN VPI";
        //          type union {
        //            type string {
        //              pattern "<.*>|$.*";
        //            }
        //            type uint32 {
        //              range "0 .. 255";
        //            }
        //          }
        //        }
        //      }
        //    }
        //    container atm-l2circuit-mode {
        //      description "Select ATM Layer 2 circuit transport mode";
        //      choice mode_choice {
        //        case case_1 {
        //          leaf cell {
        //            description "ATM Layer 2 circuit cell mode";
        //            type empty;
        //          }
        //        }
        //        case case_2 {
        //          leaf aal5 {
        //            description "ATM Layer 2 circuit AAL5 mode";
        //            type empty;
        //          }
        //        }
        //      }
        //    }
        //    container vci-range {
        //      description "ATM VCI range start <start-vci> end <end-vci>";
        //      leaf start {
        //        description "ATM VCI range's start value";
        //        type union {
        //          type string {
        //            pattern "<.*>|$.*";
        //          }
        //          type uint16 {
        //            range "32 .. 4094";
        //          }
        //        }
        //      }
        //      leaf end {
        //        description "ATM VCI range's end value";
        //        type union {
        //          type string {
        //            pattern "<.*>|$.*";
        //          }
        //          type uint16 {
        //            range "32 .. 4094";
        //          }
        //        }
        //      }
        //    }
        //    leaf trunk-bandwidth {
        //      description "ATM trunk bandwidth";
        //      units "bits per second";
        //      type string;
        //    }
        //    leaf multicast-vci {
        //      description "ATM virtual circuit identifier for multicast packets";
        //      type jt:atm-vci;
        //    }
        //    container shaping {
        //      description "Virtual circuit traffic-shaping options";
        //      uses dcd_shaping_config;
        //    }
        //    container oam-period {
        //      description "OAM cell period";
        //      choice oam_period_choices {
        //        case case_1 {
        //          leaf oam-period {
        //            description "OAM cell period";
        //            units "seconds";
        //            type union {
        //              type string {
        //                pattern "<.*>|$.*";
        //              }
        //              type uint32 {
        //                range "1 .. 900";
        //              }
        //            }
        //          }
        //        }
        //        case case_2 {
        //          container disable {
        //            presence "enable disable";
        //            description "Disable F5 OAM loopback";
        //          }
        //        }
        //      }
        //    }
        //    container oam-liveness {
        //      description "OAM virtual circuit liveness parameters";
        //      // uses apply-advanced;
        //      leaf up-count {
        //        description "Number of OAM cells to consider VC up";
        //        type union {
        //          type string {
        //            pattern "<.*>|$.*";
        //          }
        //          type uint32 {
        //            range "1 .. 255";
        //          }
        //        }
        //      }
        //      leaf down-count {
        //        description "Number of OAM cells to consider VC down";
        //        type union {
        //          type string {
        //            pattern "<.*>|$.*";
        //          }
        //          type uint32 {
        //            range "1 .. 255";
        //          }
        //        }
        //      }
        //    }
        //    container ppp-options {
        //      description "Point-to-Point Protocol interface-specific options";
        //      uses ppp_options_type;
        //    }
        //    container pppoe-options {
        //      description "PPP over Ethernet interface-specific options";
        //      uses pppoe_options_type;
        //    }
        //    container pppoe-underlying-options {
        //      description "PPP over Ethernet underlying interface-specific options";
        //      uses pppoe_underlying_options_type;
        //    }
        //    container advisory-options {
        //      description "Interface-specific recommendations";
        //      uses advisory_options_type;
        //    }
        //    container auto-configure {
        //      description "Auto configuration";
        //      uses auto_configure_vlan_type;
        //    }
        //    container demux-options {
        //      description "IP demux interface-specific options";
        //      uses demux_options_type;
        //    }
        //    container targeted-distribution {
        //      presence "enable targeted-distribution";
        //      description "Interface participates in targeted-distribution";
        //      // uses apply-advanced;
        //      leaf primary-list {
        //        description "Primary targeted distribution list";
        //        type string {
        //          length "1 .. 20";
        //        }
        //      }
        //      leaf backup-list {
        //        description "Backup targeted distribution list";
        //        type string {
        //          length "1 .. 20";
        //        }
        //      }
        //      leaf standby-list {
        //        description "Standby targeted distribution list";
        //        type string {
        //          length "1 .. 20";
        //        }
        //      }
        //    }
        //    container targeted-options {
        //      presence "enable targeted-options";
        //      description "Targeting specific options";
        //      // uses apply-advanced;
        //      leaf weight {
        //        description "Targeting weight for subscriber";
        //        type string;
        //      }
        //      leaf primary {
        //        description "Primary link for the subscriber";
        //        type union {
        //          type jt:interface-device;
        //          type string {
        //            pattern "<.*>|$.*";
        //          }
        //        }
        //      }
        //      leaf backup {
        //        description "Backup link for the subscriber";
        //        type union {
        //          type jt:interface-device;
        //          type string {
        //            pattern "<.*>|$.*";
        //          }
        //        }
        //      }
        //      leaf group {
        //        description "Group name to which the subscriber is associated";
        //        type string {
        //        }
        //      }
        //    }
        //    choice keepalive_choices {
        //      case case_1 {
        //        container keepalives {
        //          description "Send or demand keepalive messages";
        //          presence "enable keepalives";
        //          uses keepalives_type;
        //        }
        //      }
        //      case case_2 {
        //        leaf no-keepalives {
        //          description "Do not send or demand keepalive messages";
        //          type empty;
        //        }
        //      }
        //    }
        //    leaf inverse-arp {
        //      description "Enable inverse ARP";
        //      type empty;
        //    }
        //    leaf transmit-weight {
        //      description "ATM2 transmit weight for VC under VP tunnel";
        //      type union {
        //        type string {
        //          pattern "<.*>|$.*";
        //        }
        //        type uint16 {
        //          range "1 .. 32767";
        //        }
        //      }
        //    }
        //    container epd-threshold {
        //      description "Early packet discard threshold for ATM2";
        //      uses epd_threshold_config;
        //    }
        //    leaf cell-bundle-size {
        //      description "L2 circuit cell bundle size";
        //      units "cells";
        //      type union {
        //        type string {
        //          pattern "<.*>|$.*";
        //        }
        //        type uint32 {
        //          range "1 .. 176";
        //        }
        //      }
        //    }
        //    leaf cell-bundle-timeout {
        //      description "L2 circuit cell bundle timeout";
        //      units "microseconds";
        //      type union {
        //        type string {
        //          pattern "<.*>|$.*";
        //        }
        //        type uint32 {
        //          range "1 .. 512";
        //        }
        //      }
        //    }
        //    leaf plp-to-clp {
        //      description "Enable ATM2 PLP to CLP copy";
        //      type empty;
        //    }
        //    leaf atm-scheduler-map {
        //      description "Assign ATM2 CoS scheduling map";
        //      type union {
        //        type string {
        //          pattern "default";
        //        }
        //        type string;
        //      }
        //    }
        //    leaf mrru {
        //      description "Maximum received reconstructed unit";
        //      units "bytes";
        //      type union {
        //        type string {
        //          pattern "<.*>|$.*";
        //        }
        //        type uint16 {
        //          range "1500 .. 4500";
        //        }
        //      }
        //    }
        //    leaf short-sequence {
        //      description "Short sequence number header format (MLPPP only)";
        //      type empty;
        //    }
        //    leaf fragment-threshold {
        //      description "Fragmentation threshold";
        //      units "bytes";
        //      type union {
        //        type string {
        //          pattern "<.*>|$.*";
        //        }
        //        type uint32 {
        //          range "64 .. 4500";
        //        }
        //      }
        //    }
        //    leaf drop-timeout {
        //      description "Drop timeout";
        //      units "milliseconds";
        //      type union {
        //        type string {
        //          pattern "<.*>|$.*";
        //        }
        //        type uint16 {
        //          range "0 .. 2000";
        //        }
        //      }
        //    }
        //    leaf disable-mlppp-inner-ppp-pfc {
        //      description "Disable compression for inner PPP header in MLPPP payload";
        //      type empty;
        //    }
        //    leaf minimum-links {
        //      description "Minimum number of links to sustain the bundle";
        //      type union {
        //        type string {
        //          pattern "<.*>|$.*";
        //        }
        //        type uint16;
        //      }
        //    }
        //    leaf multilink-max-classes {
        //      description "Number of multilink classes";
        //      type union {
        //        type string {
        //          pattern "<.*>|$.*";
        //        }
        //        type uint16;
        //      }
        //    }
        //    container compression {
        //      presence "enable compression";
        //      description "Various packet header compressions";
        //      // uses apply-advanced;
        //      container rtp {
        //        presence "enable rtp";
        //        description "Compress and decompress RTP";
        //        // uses apply-advanced;
        //        leaf f-max-period {
        //          description "Maximum number of compressed packets between transmission of full headers";
        //          type union {
        //            type string {
        //              pattern "<.*>|$.*";
        //            }
        //            type uint32 {
        //              range "1 .. 65535";
        //            }
        //          }
        //        }
        //        leaf-list queues {
        //          ordered-by user;
        //          description "Queue holding RTP packets. Default is queue 1";
        //          type enumeration {
        //            enum "q0" {
        //              description "RTP packets assigned to queue 0";
        //            }
        //            enum "q1" {
        //              description "RTP packets assigned to queue 1";
        //            }
        //            enum "q2" {
        //              description "RTP packets assigned to queue 2";
        //            }
        //            enum "q3" {
        //              description "RTP packets assigned to queue 3";
        //            }
        //          }
        //        }
        //        container port {
        //          presence "enable port";
        //          description "UDP destination ports reserved for RTP packets";
        //          leaf minimum {
        //            type union {
        //              type string {
        //                pattern "<.*>|$.*";
        //              }
        //              type uint32 {
        //                range "0 .. 65535";
        //              }
        //            }
        //          }
        //          leaf maximum {
        //            type union {
        //              type string {
        //                pattern "<.*>|$.*";
        //              }
        //              type uint32 {
        //                range "0 .. 65535";
        //              }
        //            }
        //          }
        //        }
        //        container maximum-contexts {
        //          description "Maximum number of simultaneous RTP contexts";
        //          leaf number {
        //            description "Maximum number of simultaneous RTP contexts";
        //            type union {
        //              type string {
        //                pattern "<.*>|$.*";
        //              }
        //              type uint32 {
        //                range "16 .. 2048";
        //              }
        //            }
        //          }
        //        }
        //      }
        //    }
        //    leaf interleave-fragments {
        //      description "Interleave long packets with high priority ones";
        //      type empty;
        //    }
        //    leaf link-layer-overhead {
        //      description "Link layer bit stuffing overhead (0.0 .. 50.0 percent)";
        //      type jt:unsigned-float;
        //    }
        //    leaf accounting-profile {
        //      description "Accounting profile name";
        //      type string;
        //    }
        //    leaf peer-unit {
        //      description "Peer unit number";
        //      type union {
        //        type string {
        //          pattern "<.*>|$.*";
        //        }
        //        type uint32 {
        //          range "0 .. 16385";
        //        }
        //      }
        //    }
        //    container tunnel {
        //      description "Tunnel parameters";
        //      // uses apply-advanced;
        //      container encapsulation {
        //        presence "enable encapsulation";
        //        description "Encapsulation over tunnel";
        //        container vxlan-gpe {
        //          presence "enable vxlan-gpe";
        //          // uses apply-advanced;
        //          container source {
        //            // uses apply-advanced;
        //            leaf address {
        //              description "Interface address prefix";
        //              type jt:ipv4addr;
        //            }
        //            leaf mac-address {
        //              description "Interface source mac address";
        //              type jt:mac-addr;
        //            }
        //            leaf interface {
        //              description "Name of the interface";
        //              type union {
        //                type jt:interface-name;
        //                type string {
        //                  pattern "<.*>|$.*";
        //                }
        //              }
        //            }
        //          }
        //          container destination {
        //            // uses apply-advanced;
        //            leaf address {
        //              description "Interface address prefix";
        //              type jt:ipv4addr;
        //            }
        //            leaf mac-address {
        //              description "Interface destination mac address";
        //              type jt:mac-addr;
        //            }
        //          }
        //          leaf tunnel-endpoint {
        //            description "Tunnel end point type";
        //            type enumeration {
        //              enum "vxlan" {
        //                description "To configure vxlan tunnel-end-point";
        //              }
        //            }
        //          }
        //          container source-udp-port-range {
        //            description "Value range for source-udp-port";
        //            leaf min {
        //              description "Minimum range value";
        //              type union {
        //                type string {
        //                  pattern "<.*>|$.*";
        //                }
        //                type uint32 {
        //                  range "1 .. 65535";
        //                }
        //              }
        //            }
        //            leaf max {
        //              description "Maximum range value";
        //              type union {
        //                type string {
        //                  pattern "<.*>|$.*";
        //                }
        //                type uint32 {
        //                  range "1 .. 65535";
        //                }
        //              }
        //            }
        //          }
        //          leaf destination-udp-port {
        //            description "Value to write to the destination-udp-port field";
        //            type union {
        //              type string {
        //                pattern "<.*>|$.*";
        //              }
        //              type uint32 {
        //                range "1 .. 65535";
        //              }
        //            }
        //          }
        //          leaf vni {
        //            description "Value to write to the vni field";
        //            type union {
        //              type string {
        //                pattern "<.*>|$.*";
        //              }
        //              type uint32 {
        //                range "0 .. 16777214";
        //              }
        //            }
        //          }
        //        }
        //        container udp {
        //          presence "enable udp";
        //          description "Family for tunnel encapsulation udp";
        //          // uses apply-advanced;
        //          container source {
        //            // uses apply-advanced;
        //            leaf address {
        //              description "Interface address prefix";
        //              type jt:ipv4addr;
        //            }
        //            leaf interface {
        //              description "Name of the interface";
        //              type union {
        //                type jt:interface-name;
        //                type string {
        //                  pattern "<.*>|$.*";
        //                }
        //              }
        //            }
        //          }
        //          container destination {
        //            // uses apply-advanced;
        //            leaf address {
        //              description "Interface address prefix";
        //              type jt:ipv4addr;
        //            }
        //          }
        //        }
        //        container ipip {
        //          presence "enable ipip";
        //          description "Family for tunnel encapsulation ipip";
        //          // uses apply-advanced;
        //          container source {
        //            // uses apply-advanced;
        //            leaf address {
        //              description "Interface address prefix";
        //              type jt:ipv4addr;
        //            }
        //            leaf interface {
        //              description "Name of the interface";
        //              type union {
        //                type jt:interface-name;
        //                type string {
        //                  pattern "<.*>|$.*";
        //                }
        //              }
        //            }
        //          }
        //          container destination {
        //            // uses apply-advanced;
        //            leaf address {
        //              description "Interface address prefix";
        //              type jt:ipv4addr;
        //            }
        //          }
        //        }
        //      }
        //      leaf encap-type {
        //        description "Tunnel encapsulation type";
        //        type enumeration {
        //          enum "ipv4" {
        //            description "Tunnel IPv4 encapsulation";
        //          }
        //          enum "ipv6" {
        //            description "Tunnel IPv6 encapsulation";
        //          }
        //        }
        //      }
        //      choice source_type {
        //        case case_1 {
        //          leaf source {
        //            description "Tunnel source address";
        //            type jt:ipaddr;
        //          }
        //        }
        //        case case_2 {
        //          leaf source-hostname {
        //            description "Tunnel source hostname";
        //            type string;
        //          }
        //        }
        //        case case_3 {
        //          leaf source-interface {
        //            description "Tunnel source interface";
        //            type union {
        //              type jt:interface-name;
        //              type string {
        //                pattern "<.*>|$.*";
        //              }
        //            }
        //          }
        //        }
        //      }
        //      choice destination_type {
        //        case case_1 {
        //          leaf destination {
        //            description "Tunnel destination address";
        //            type jt:ipaddr;
        //          }
        //        }
        //        case case_2 {
        //          leaf destination-hostname {
        //            description "Tunnel destination hostname";
        //            type string;
        //          }
        //        }
        //      }
        //      leaf key {
        //        description "Tunnel key";
        //        type union {
        //          type string {
        //            pattern "<.*>|$.*";
        //          }
        //          type uint32 {
        //            range "0 .. 4294967295";
        //          }
        //        }
        //      }
        //      leaf backup-destination {
        //        description "Backup tunnel destination";
        //        type jt:ipaddr;
        //      }
        //      choice fragmentation {
        //        case case_1 {
        //          leaf allow-fragmentation {
        //            description "Do not set DF bit on packets";
        //            type empty;
        //          }
        //        }
        //        case case_2 {
        //          leaf do-not-fragment {
        //            description "Set DF bit on packets";
        //            type empty;
        //          }
        //        }
        //      }
        //      leaf ttl {
        //        description "Time to live";
        //        type union {
        //          type string {
        //            pattern "<.*>|$.*";
        //          }
        //          type uint32 {
        //            range "1 .. 255";
        //          }
        //        }
        //      }
        //      leaf traffic-class {
        //        description "TOS/Traffic class field of IP-header";
        //        type union {
        //          type string {
        //            pattern "<.*>|$.*";
        //          }
        //          type uint32 {
        //            range "0 .. 255";
        //          }
        //        }
        //      }
        //      leaf flow-label {
        //        description "Flow label field of IP6-header";
        //        type union {
        //          type string {
        //            pattern "<.*>|$.*";
        //          }
        //          type uint32 {
        //            range "0 .. 1048575";
        //          }
        //        }
        //      }
        //      choice path-mtu-discovery-choice {
        //        leaf path-mtu-discovery {
        //          description "Enable path MTU discovery for tunnels";
        //          type empty;
        //        }
        //        leaf no-path-mtu-discovery {
        //          description "Don't enable path MTU discovery for tunnels";
        //          type empty;
        //        }
        //      }
        //      container routing-instance {
        //        description "Routing instance to which tunnel ends belong";
        //        // uses apply-advanced;
        //        leaf destination {
        //          description "Routing instance of tunnel destination";
        //          type string {
        //          }
        //        }
        //      }
        //    }
        //    leaf compression-device {
        //      description "Logical interface used for compression";
        //      type union {
        //        type jt:interface-unit;
        //        type string {
        //          pattern "<.*>|$.*";
        //        }
        //      }
        //    }
        //    container atm-policer {
        //      description "ATM policing for logical interface";
        //      // uses apply-advanced;
        //      leaf input-atm-policer {
        //        description "Input atm policer";
        //        type string;
        //      }
        //    }
        //    container layer2-policer {
        //      description "Layer2 policing for logical interface";
        //      // uses apply-advanced;
        //      choice layer2-input-policer-choice {
        //        case case_1 {
        //          leaf input-policer {
        //            description "Two-color policer for received packets";
        //            type string;
        //          }
        //        }
        //        case case_2 {
        //          leaf input-hierarchical-policer {
        //            description "Hierarchical policer for received packets";
        //            type string;
        //          }
        //        }
        //        case case_3 {
        //          leaf input-three-color {
        //            description "Color-blind three-color policer for received packets";
        //            type string;
        //          }
        //        }
        //      }
        //      choice layer2-output-policer-choice {
        //        case case_1 {
        //          leaf output-policer {
        //            description "Two-color policer for transmitted packets";
        //            type string;
        //          }
        //        }
        //        case case_2 {
        //          leaf output-three-color {
        //            description "Three-color policer for transmitted packets";
        //            type string;
        //          }
        //        }
        //      }
        //    }
        //    container filter {
        //      description "Filters to apply to all families configured under this logical interface";
        //      // uses apply-advanced;
        //      choice chain_choice {
        //        case case_1 {
        //          leaf-list chain {
        //            ordered-by user;
        //            description "List of filter modules applied to TAG packets ";
        //            type string;
        //            max-elements 6;
        //          }
        //        }
        //      }
        //      choice input_choice {
        //        case case_1 {
        //          container input {
        //            description "Name of filter to be applied to received packets";
        //            leaf filter-name {
        //              description "Name of the filter";
        //              type string;
        //            }
        //            leaf shared-name {
        //              description "Filter shared-name of instances of interface-shared filter";
        //              type string;
        //            }
        //            leaf precedence {
        //              description "Precedence of the filter";
        //              type union {
        //                type string {
        //                  pattern "<.*>|$.*";
        //                }
        //                type uint32 {
        //                  range "0 .. 255";
        //                }
        //              }
        //            }
        //          }
        //        }
        //      }
        //      choice output_choice {
        //        case case_1 {
        //          container output {
        //            description "Name of filter to be applied to transmitted packets";
        //            leaf filter-name {
        //              description "Name of the filter";
        //              type string;
        //            }
        //            leaf shared-name {
        //              description "Filter shared-name of instances of interface-shared filter";
        //              type string;
        //            }
        //            leaf precedence {
        //              description "Precedence of the filter";
        //              type union {
        //                type string {
        //                  pattern "<.*>|$.*";
        //                }
        //                type uint32 {
        //                  range "0 .. 255";
        //                }
        //              }
        //            }
        //          }
        //        }
        //      }
        //    }
        //    list multi-chassis-protection {
        //      key name;
        //      description "Inter-Chassis protection configuration";
        //      uses multi-chassis-protection-group-ifl;
        //    }
        //    leaf statistics {
        //      description "Enable statistics collection in PFE";
        //      type empty;
        //    }
        //    container esi {
        //      presence "enable esi";
        //      description "ESI configuration of logical interface";
        //      // uses apply-advanced;
        //      container auto-derive {
        //        description "Auto-derive ESI value for the interface";
        //        // uses apply-advanced;
        //        choice esitype {
        //          case case_1 {
        //            leaf lacp-pe-system-id-and-admin-key {
        //              description "Auto-derive ESI from lacp";
        //              type empty;
        //            }
        //          }
        //        }
        //      }
        //      leaf identifier {
        //        description "ESI value for the interface";
        //        type jt:esi;
        //      }
        //      choice mode {
        //        case case_1 {
        //          leaf single-active {
        //            description "Single-active mode";
        //            type empty;
        //          }
        //        }
        //        case case_2 {
        //          leaf all-active {
        //            description "All-active mode";
        //            type empty;
        //          }
        //        }
        //      }
        //      container df-election-granularity {
        //        presence "enable df-election-granularity";
        //        description "DF Election Granularity Selection ";
        //        // uses apply-advanced;
        //        choice mode {
        //          case case_1 {
        //            container per-esi {
        //              presence "enable per-esi";
        //              description "DF Election Granularity Per Esi";
        //              // uses apply-advanced;
        //              leaf lacp-oos-on-ndf {
        //                description "Lacp Oos";
        //                type empty;
        //              }
        //            }
        //          }
        //          case case_2 {
        //            leaf per-esi-vlan {
        //              description "Per Esi Vlan";
        //              type empty;
        //            }
        //          }
        //        }
        //      }
        //      container df-election-type {
        //        presence "enable df-election-type";
        //        description "DF Election Type";
        //        // uses apply-advanced;
        //        choice pref_choice {
        //          case case_1 {
        //            container preference {
        //              presence "enable preference";
        //              description "Preference based DF election";
        //              // uses apply-advanced;
        //              leaf value {
        //                description "Preference value for EVPN Multihoming DF election";
        //                default "32767";
        //                type union {
        //                  type string {
        //                    pattern "<.*>|$.*";
        //                  }
        //                  type uint32 {
        //                    range "0 .. 65535";
        //                  }
        //                }
        //              }
        //            }
        //          }
        //        }
        //        choice mod_choice {
        //          case case_1 {
        //            container mod {
        //              presence "enable mod";
        //              description "MOD based DF election";
        //            }
        //          }
        //        }
        //      }
        //      leaf source-bmac {
        //        description "Unicast Source B-MAC address per ESI for PBB-EVPN";
        //        type jt:mac-unicast;
        //      }
        //    }
        //    choice virtual-gateway {
        //      case case_1 {
        //        leaf no-auto-virtual-gateway-esi {
        //          description "Disable auto ESI generation for virtual gateway address";
        //          type empty;
        //        }
        //      }
        //      case case_2 {
        //        container virtual-gateway-esi {
        //          description "ESI configuration of virtual gateway";
        //          // uses apply-advanced;
        //          leaf identifier {
        //            description "ESI value for the interface";
        //            type jt:esi;
        //          }
        //          choice mode {
        //            case case_1 {
        //              leaf single-active {
        //                description "Single-active mode";
        //                type empty;
        //              }
        //            }
        //            case case_2 {
        //              leaf all-active {
        //                description "All-active mode";
        //                type empty;
        //              }
        //            }
        //          }
        //        }
        //      }
        //    }
        //    container service {
        //      description "Service operations";
        //      // uses apply-advanced;
        //      list pcef {
        //        key name;
        //        ordered-by user;
        //        description "PCEF configuration";
        //        leaf name {
        //          description "PCEF Profile name";
        //          type string;
        //        }
        //        // uses apply-advanced;
        //        leaf activate-all {
        //          description "Activate all rules and rulebases in the pcef profile";
        //          type empty;
        //        }
        //        list activate {
        //          key name;
        //          ordered-by user;
        //          description "Name of pcef profile rule or rulebase to activate";
        //          leaf name {
        //            description "Name of pcef profile rule or rulebase to activate";
        //            type string;
        //          }
        //          // uses apply-advanced;
        //        }
        //      }
        //    }
        //    choice generate-eui64-choice {
        //      leaf generate-eui64 {
        //        description "To generate Link Local EUI-64 addresses";
        //        type empty;
        //      }
        //      leaf no-generate-eui64 {
        //        description "Don't to generate Link Local EUI-64 addresses";
        //        type empty;
        //      }
        //    }
        //    container family {
        //      description "Protocol family";
        //      container inet {
        //        presence "enable inet";
        //        description "IPv4 parameters";
        //        // uses apply-advanced;
        //        container dhcp {
        //          description "Dynamic Host Configuration Protocol client configuration";
        //          presence "enable dhcp";
        //          uses dhcp-client-type;
        //        }
        //        container targeted-broadcast {
        //          presence "enable targeted-broadcast";
        //          description "Directed broadcast";
        //          // uses apply-advanced;
        //          choice targeted-bcast-choice {
        //            case case_1 {
        //              leaf forward-and-send-to-re {
        //                description "Allow packets to be forwarded and sent to re";
        //                type empty;
        //              }
        //            }
        //            case case_2 {
        //              leaf forward-only {
        //                description "Allow packets only to be forwarded";
        //                type empty;
        //              }
        //            }
        //          }
        //        }
        //        leaf destination-class-usage {
        //          description "Enable destination class usage on this interface";
        //          status deprecated;
        //          type empty;
        //        }
        //        leaf transit-options-packets {
        //          description "Transit IP options packets (don't send to Routing Engine)";
        //          status deprecated;
        //          type empty;
        //        }
        //        leaf transit-ttl-exceeded {
        //          description "Transit IP TTL-exceeded packets (don't send to Routing Engine)";
        //          status deprecated;
        //          type empty;
        //        }
        //        leaf receive-options-packets {
        //          description "Receive IP options packets (don't send to Routing Engine)";
        //          type empty;
        //        }
        //        leaf receive-ttl-exceeded {
        //          description "Receive IP TTL-exceeded packets (don't send to Routing Engine)";
        //          type empty;
        //        }
        //        container accounting {
        //          description "Configure interface-based accounting options";
        //          // uses apply-advanced;
        //          container source-class-usage {
        //            description "Enable source class usage on this interface";
        //            // uses apply-advanced;
        //            leaf input {
        //              description "Specify this interface for source-class-usage input";
        //              type empty;
        //            }
        //            leaf output {
        //              description "Specify this interface for source-class-usage output";
        //              type empty;
        //            }
        //          }
        //          leaf destination-class-usage {
        //            description "Enable destination class usage on this interface";
        //            type empty;
        //          }
        //        }
        //        leaf mac-validate {
        //          description "Validate source MAC address";
        //          type enumeration {
        //            enum "strict" {
        //              description "Strict mac-validation";
        //            }
        //            enum "loose" {
        //              description "Loose mac-validation";
        //            }
        //          }
        //        }
        //        container rpf-check {
        //          presence "enable rpf-check";
        //          description "Enable reverse-path-forwarding checks on this interface";
        //          // uses apply-advanced;
        //          leaf fail-filter {
        //            description "Name of filter applied to packets failing RPF check";
        //            type string;
        //          }
        //          container mode {
        //            description "Mode for reverse path forwarding";
        //            leaf loose {
        //              description "Reverse-path-forwarding loose mode";
        //              type empty;
        //            }
        //          }
        //        }
        //        leaf mtu {
        //          description "Protocol family maximum transmission unit";
        //          type union {
        //            type uint32;
        //            type string {
        //              pattern "<.*>|$.*";
        //            }
        //          }
        //        }
        //        leaf arp-max-cache {
        //          description "Max interface ARP nexthop cache size";
        //          type union {
        //            type string {
        //              pattern "<.*>|$.*";
        //            }
        //            type uint32 {
        //              range "1 .. 2000000";
        //            }
        //          }
        //        }
        //        leaf arp-new-hold-limit {
        //          description "Max no. of new unresolved nexthops";
        //          type union {
        //            type string {
        //              pattern "<.*>|$.*";
        //            }
        //            type uint32 {
        //              range "1 .. 2000000";
        //            }
        //          }
        //        }
        //        leaf tcp-mss {
        //          description "Protocol family tcp maximum segment size";
        //          type union {
        //            type string {
        //              pattern "<.*>|$.*";
        //            }
        //            type uint32 {
        //              range "1 .. 65535";
        //            }
        //          }
        //        }
        //        leaf no-redirects {
        //          description "Do not redirect traffic";
        //          type empty;
        //        }
        //        leaf no-neighbor-learn {
        //          description "Disable neighbor address learning on interface";
        //          type empty;
        //        }
        //        leaf unconditional-src-learn {
        //          description "Glean from arp packets even when source cannot be validated";
        //          type empty;
        //        }
        //        leaf multicast-only {
        //          description "Allow only multicast traffic (tunnels only)";
        //          type empty;
        //        }
        //        leaf primary {
        //          description "Candidate for primary interface in system";
        //          type empty;
        //        }
        //        leaf ipsec-sa {
        //          description "Name of security association";
        //          type string {
        //            length "1 .. 32";
        //          }
        //        }
        //        list demux-source {
        //          key name;
        //          ordered-by user;
        //          description "Demux based on source prefix";
        //          leaf name {
        //            type string;
        //          }
        //          // uses apply-advanced;
        //        }
        //        list demux-destination {
        //          key name;
        //          ordered-by user;
        //          description "Demux based on destination prefix";
        //          leaf name {
        //            type string;
        //          }
        //          // uses apply-advanced;
        //        }
        //        container filter {
        //          description "Packet filtering";
        //          // uses apply-advanced;
        //          choice input_choice {
        //            case case_1 {
        //              container input {
        //                description "Filter to be applied to received packets";
        //                leaf filter-name {
        //                  description "Name of the filter";
        //                  type string;
        //                }
        //                leaf shared-name {
        //                  description "Filter shared-name of instances of interface-shared filter";
        //                  type string;
        //                }
        //                leaf precedence {
        //                  description "Precedence of the filter";
        //                  type union {
        //                    type string {
        //                      pattern "<.*>|$.*";
        //                    }
        //                    type uint32 {
        //                      range "0 .. 255";
        //                    }
        //                  }
        //                }
        //              }
        //            }
        //            case case_2 {
        //              leaf-list input-list {
        //                ordered-by user;
        //                description "List of filter modules applied to received packets ";
        //                type string;
        //              }
        //            }
        //          }
        //          leaf-list input-chain {
        //            ordered-by user;
        //            description "List of filter modules applied to received packets ";
        //            type string;
        //          }
        //          leaf-list output-chain {
        //            ordered-by user;
        //            description "List of filter modules applied to transmitted packets ";
        //            type string;
        //          }
        //          choice output_choice {
        //            case case_1 {
        //              container output {
        //                description "Filter to be applied to transmitted packets";
        //                leaf filter-name {
        //                  description "Name of the filter";
        //                  type string;
        //                }
        //                leaf shared-name {
        //                  description "Filter shared-name of instances of interface-shared filter";
        //                  type string;
        //                }
        //                leaf precedence {
        //                  description "Precedence of the filter";
        //                  type union {
        //                    type string {
        //                      pattern "<.*>|$.*";
        //                    }
        //                    type uint32 {
        //                      range "0 .. 255";
        //                    }
        //                  }
        //                }
        //              }
        //            }
        //            case case_2 {
        //              leaf-list output-list {
        //                ordered-by user;
        //                description "List of filter modules applied to transmitted packets ";
        //                type string;
        //              }
        //            }
        //          }
        //          container adf {
        //            description "Ascend Data Filter definition";
        //            // uses apply-advanced;
        //            list rule {
        //              key name;
        //              ordered-by user;
        //              description "Set of ADF rules";
        //              leaf name {
        //                description "Value for a single rule";
        //                type string;
        //              }
        //              // uses apply-advanced;
        //            }
        //            leaf counter {
        //              description "Add a counter to each rule";
        //              type empty;
        //            }
        //            leaf input-precedence {
        //              description "Precedence of the input rules";
        //              type union {
        //                type string {
        //                  pattern "<.*>|$.*";
        //                }
        //                type uint32 {
        //                  range "0 .. 255";
        //                }
        //              }
        //            }
        //            leaf not-mandatory {
        //              description "No errors will be reported if no rules are present";
        //              type empty;
        //            }
        //            leaf output-precedence {
        //              description "Precedence of the output rules";
        //              type union {
        //                type string {
        //                  pattern "<.*>|$.*";
        //                }
        //                type uint32 {
        //                  range "0 .. 255";
        //                }
        //              }
        //            }
        //          }
        //          leaf group {
        //            description "Group to which interface belongs";
        //            type union {
        //              type string {
        //                pattern "<.*>|$.*";
        //              }
        //              type uint32;
        //            }
        //          }
        //        }
        //        container ingress-queuing-filter {
        //          description "Protocol family ingress-queuing-filter";
        //          leaf filter-name {
        //            description "Name of the ingress-queuing-filter";
        //            type string;
        //          }
        //        }
        //        container iq-policing-filter {
        //          description "Protocol family ingress-queuing-policing-filter";
        //          leaf filter-name {
        //            description "Name of the ingress-queuing-policing-filter";
        //            type string;
        //          }
        //        }
        //        container simple-filter {
        //          description "Filter for doing multifield classification";
        //          // uses apply-advanced;
        //          leaf input {
        //            description "Name of simple filter applied to received packets";
        //            type string;
        //          }
        //        }
        //        leaf input-hierarchical-policer {
        //          description "Hierarchical policer for received packets";
        //          type string;
        //        }
        //        container policer {
        //          description "Interface policing";
        //          // uses apply-advanced;
        //          leaf disable-arp-policer {
        //            description "Disable the arp policer for the interface";
        //            type empty;
        //          }
        //          leaf arp {
        //            description "Name of policer applied to received ARP packets";
        //            type string;
        //          }
        //          leaf input {
        //            description "Name of policer applied to received packets";
        //            type string;
        //          }
        //          leaf output {
        //            description "Name of policer applied to transmitted packets";
        //            type string;
        //          }
        //        }
        //        container sampling {
        //          description "Interface sampling";
        //          // uses apply-advanced;
        //          leaf input {
        //            description "Sample all packets input on this interface";
        //            type empty;
        //          }
        //          leaf output {
        //            description "Sample all packets output on this interface";
        //            type empty;
        //          }
        //        }
        //        container service {
        //          description "Service operations";
        //          // uses apply-advanced;
        //          container input {
        //            description "Service sets to consider for received packets";
        //            // uses apply-advanced;
        //            list service-set {
        //              key name;
        //              ordered-by user;
        //              description "Service set to consider for received packets";
        //              leaf name {
        //                description "Name of service set";
        //                type string {
        //                }
        //              }
        //              // uses apply-advanced;
        //              leaf service-filter {
        //                description "Name of service filter";
        //                type string;
        //              }
        //            }
        //            leaf post-service-filter {
        //              description "Post-service filter to apply to received packets";
        //              type string;
        //            }
        //          }
        //          container output {
        //            description "Service sets to consider for transmitted packets";
        //            // uses apply-advanced;
        //            list service-set {
        //              key name;
        //              ordered-by user;
        //              description "Service set to consider for transmitted packets";
        //              leaf name {
        //                description "Name of service set";
        //                type string {
        //                }
        //              }
        //              // uses apply-advanced;
        //              leaf service-filter {
        //                description "Name of service filter";
        //                type string;
        //              }
        //            }
        //          }
        //        }
        //        list next-hop-tunnel {
        //          key name;
        //          ordered-by user;
        //          description "One or more next-hop tunnel tables";
        //          leaf name {
        //            description "Next-hop tunnel gateway address";
        //            type string;
        //          }
        //          // uses apply-advanced;
        //          leaf ipsec-vpn {
        //            description "Name of IPSec VPN";
        //            type string;
        //          }
        //        }
        //        choice tunnel-termination-status {
        //          case case_1 {
        //            leaf tunnel-termination {
        //              description "Tunnel termination";
        //              type empty;
        //            }
        //          }
        //          case case_2 {
        //            leaf no-tunnel-termination {
        //              description "No Tunnel termination";
        //              type empty;
        //            }
        //          }
        //        }
        //        leaf tunnel-loopback {
        //          description "Allows tunnel packet processing on IRB underlay using the loopback path";
        //          type empty;
        //        }
        //        list address {
        //          key name;
        //          ordered-by user;
        //          description "Interface address/destination prefix";
        //          leaf name {
        //            description "Interface address/destination prefix";
        //            type jt:ipv4prefix;
        //          }
        //          // uses apply-advanced;
        //          leaf destination {
        //            description "Destination address";
        //            type jt:ipv4addr;
        //          }
        //          leaf destination-profile {
        //            description "Profile to use for destination address";
        //            type string;
        //          }
        //          leaf broadcast {
        //            description "Broadcast address";
        //            type jt:ipv4addr;
        //          }
        //          leaf primary {
        //            description "Candidate for primary address in system";
        //            type empty;
        //          }
        //          leaf preferred {
        //            description "Preferred address on interface";
        //            type empty;
        //          }
        //          leaf master-only {
        //            description "Master management IP address for router";
        //            type empty;
        //          }
        //          list multipoint-destination {
        //            key name;
        //            ordered-by user;
        //            description "Multipoint NBMA destination";
        //            leaf name {
        //              description "Destination address";
        //              type jt:ipv4addr;
        //            }
        //            // uses apply-advanced;
        //            choice link-address {
        //              case case_1 {
        //                leaf dlci {
        //                  description "Frame Relay data-link control identifier";
        //                  type union {
        //                    type string {
        //                      pattern "<.*>|$.*";
        //                    }
        //                    type uint32 {
        //                      range "1 .. 1022";
        //                    }
        //                  }
        //                }
        //              }
        //              case case_2 {
        //                leaf vci {
        //                  description "ATM virtual circuit identifier ([vpi.]vci)";
        //                  type jt:atm-vci;
        //                }
        //              }
        //            }
        //            container shaping {
        //              description "Virtual circuit traffic-shaping options";
        //              uses dcd_shaping_config;
        //            }
        //            container oam-period {
        //              description "OAM cell period";
        //              choice oam_period_choices {
        //                case case_1 {
        //                  leaf oam_period {
        //                    description "OAM cell period";
        //                    units "seconds";
        //                    type union {
        //                      type string {
        //                        pattern "<.*>|$.*";
        //                      }
        //                      type uint32 {
        //                        range "1 .. 900";
        //                      }
        //                    }
        //                  }
        //                }
        //                case case_2 {
        //                  container disable {
        //                    presence "enable disable";
        //                    description "Disable OAM loopback";
        //                  }
        //                }
        //              }
        //            }
        //            container oam-liveness {
        //              description "OAM virtual circuit liveness parameters";
        //              // uses apply-advanced;
        //              leaf up-count {
        //                description "Number of OAM cells to consider VC up";
        //                type union {
        //                  type string {
        //                    pattern "<.*>|$.*";
        //                  }
        //                  type uint32 {
        //                    range "1 .. 255";
        //                  }
        //                }
        //              }
        //              leaf down-count {
        //                description "Number of OAM cells to consider VC down";
        //                type union {
        //                  type string {
        //                    pattern "<.*>|$.*";
        //                  }
        //                  type uint32 {
        //                    range "1 .. 255";
        //                  }
        //                }
        //              }
        //            }
        //            leaf inverse-arp {
        //              description "Enable inverse ARP reply messages";
        //              type empty;
        //            }
        //            leaf transmit-weight {
        //              description "ATM2 transmit weight for VC under VP tunnel";
        //              type union {
        //                type string {
        //                  pattern "<.*>|$.*";
        //                }
        //                type uint16 {
        //                  range "1 .. 32767";
        //                }
        //              }
        //            }
        //            container epd-threshold {
        //              description "Early packet discard threshold for ATM2";
        //              uses epd_threshold_config;
        //            }
        //          }
        //          list arp {
        //            key name;
        //            ordered-by user;
        //            description "Static Address Resolution Protocol entries";
        //            leaf name {
        //              description "Destination IP address";
        //              type jt:ipv4addr;
        //            }
        //            leaf l2-interface {
        //              description "Layer 2 interface name for ARP entry";
        //              type union {
        //                type jt:interface-name;
        //                type string {
        //                  pattern "<.*>|$.*";
        //                }
        //              }
        //            }
        //            choice mac_address_type {
        //              case case_1 {
        //                leaf mac {
        //                  description "MAC address";
        //                  type jt:mac-unicast;
        //                }
        //              }
        //              case case_2 {
        //                leaf multicast-mac {
        //                  description "Multicast MAC address";
        //                  type jt:mac-multicast;
        //                }
        //              }
        //            }
        //            leaf publish {
        //              description "Reply to ARP requests for this entry";
        //              type empty;
        //            }
        //            leaf flood-as-unknown-unicast {
        //              description "Broadcast the packet with unicast MAC";
        //              type empty;
        //            }
        //          }
        //          container web-authentication {
        //            description "Parameters for web-based firewall-user authentication";
        //            // uses apply-advanced;
        //            leaf http {
        //              description "Enable authentication via HTTP";
        //              type empty;
        //            }
        //            leaf https {
        //              description "Enable authentication via HTTPS";
        //              type empty;
        //            }
        //            leaf redirect-to-https {
        //              description "Web authentication redirect to HTTPS";
        //              type empty;
        //            }
        //          }
        //          list vrrp-group {
        //            key name;
        //            ordered-by user;
        //            description "VRRP group";
        //            uses vrrp-group;
        //          }
        //          leaf virtual-gateway-address {
        //            description "Virtual Gateway IP address";
        //            type jt:ipv4addr;
        //          }
        //        }
        //        container unnumbered-address {
        //          description "Unnumbered interface address/destination prefix";
        //          leaf source {
        //            description "Interface from which to take local address";
        //            type union {
        //              type jt:interface-unit;
        //              type string {
        //                pattern "<.*>|$.*";
        //              }
        //            }
        //          }
        //          leaf preferred-source-address {
        //            description "Preferred address on the donor interface";
        //            type string;
        //          }
        //          leaf destination {
        //            description "Destination address";
        //            type jt:ipv4addr;
        //          }
        //          leaf destination-profile {
        //            description "Profile to use for destination address";
        //            type string;
        //          }
        //        }
        //        leaf negotiate-address {
        //          description "Negotiate address with remote";
        //          type empty;
        //        }
        //        leaf destination-udp-port {
        //          description "Choose destination UDP port number";
        //          type union {
        //            type string {
        //              pattern "<.*>|$.*";
        //            }
        //            type uint32 {
        //              range "10000 .. 10009";
        //            }
        //          }
        //        }
        //        container auto-configure {
        //          description "Auto configuration";
        //          uses dynamic_ipv4_type;
        //        }
        //        leaf clear-dont-fragment-bit {
        //          description "Clear DF bit in packet (AS PIC and J-series only as well as MIF)";
        //          type empty;
        //        }
        //      }
        //      container iso {
        //        presence "enable iso";
        //        description "OSI ISO protocol parameters";
        //        // uses apply-advanced;
        //        list address {
        //          key name;
        //          ordered-by user;
        //          description "Interface address";
        //          leaf name {
        //            description "Interface address";
        //            type jt:isoaddr;
        //          }
        //          // uses apply-advanced;
        //        }
        //        leaf mtu {
        //          description "Protocol family maximum transmission unit";
        //          type union {
        //            type uint32;
        //            type string {
        //              pattern "<.*>|$.*";
        //            }
        //          }
        //        }
        //        leaf destination-udp-port {
        //          description "Choose destination UDP port number";
        //          type union {
        //            type string {
        //              pattern "<.*>|$.*";
        //            }
        //            type uint32 {
        //              range "10030 .. 10039";
        //            }
        //          }
        //        }
        //      }
        //      container inet6 {
        //        presence "enable inet6";
        //        description "IPv6 protocol parameters";
        //        // uses apply-advanced;
        //        container dhcpv6-client {
        //          description "Dynamic Host Configuration Protocol DHCPv6 client configuration";
        //          // uses apply-advanced;
        //          leaf client-type {
        //            description "DHCPv6 client type";
        //            type enumeration {
        //              enum "stateful" {
        //                description "Stateful client type for address assignment.";
        //              }
        //              enum "autoconfig" {
        //                description "Autoconfig  client type for router-advertisement";
        //              }
        //            }
        //          }
        //          list client-ia-type {
        //            key name;
        //            ordered-by user;
        //            description "DHCPv6 client identity association type";
        //            leaf name {
        //              type enumeration {
        //                enum "ia-na" {
        //                  description "Identity Association-Non-temporary Address";
        //                }
        //                enum "ia-pd" {
        //                  description "Identity Association-Prefix Address";
        //                }
        //              }
        //            }
        //            // uses apply-advanced;
        //          }
        //          container rapid-commit {
        //            presence "enable rapid-commit";
        //            description "Option is used to signal the use of the two message exchange for address assignment";
        //          }
        //          leaf interface-identifier {
        //            description "Identifier for this interface";
        //            type jt:ipv6addr;
        //          }
        //          leaf use-ra-prefix {
        //            description "Assign interface IP from RA prefix when ia-na address not received";
        //            type empty;
        //          }
        //          container prefix-delegating {
        //            description "Prefix delegating parameters";
        //            // uses apply-advanced;
        //            leaf preferred-prefix-length {
        //              description "Client preferred prefix length";
        //              type union {
        //                type string {
        //                  pattern "<.*>|$.*";
        //                }
        //                type uint32 {
        //                  range "0 .. 64";
        //                }
        //              }
        //            }
        //            leaf sub-prefix-length {
        //              description "The sub prefix length for LAN interfaces";
        //              type union {
        //                type string {
        //                  pattern "<.*>|$.*";
        //                }
        //                type uint32 {
        //                  range "1 .. 127";
        //                }
        //              }
        //            }
        //          }
        //          container client-identifier {
        //            description "DHCP Server identifies a client by client-identifier value ";
        //            leaf duid-type {
        //              description "DUID identifying a client";
        //              type enumeration {
        //                enum "duid-llt" {
        //                  description "Link-layer address plus time";
        //                }
        //                enum "vendor" {
        //                  description "Vendor-assigned unique ID based on Enterprise Number";
        //                }
        //                enum "duid-ll" {
        //                  description "Link-layer address";
        //                }
        //              }
        //            }
        //          }
        //          leaf vendor-id {
        //            description "Vendor class id for the dhcpv6 client";
        //            type string {
        //              length "1 .. 60";
        //            }
        //          }
        //          list req-option {
        //            key name;
        //            ordered-by user;
        //            description "DHCPV6 client requested option configuration";
        //            leaf name {
        //              type enumeration {
        //                enum "dns-server" {
        //                  description "Dns-server option";
        //                }
        //                enum "domain" {
        //                  description "Dns-server option";
        //                }
        //                enum "ntp-server" {
        //                  description "Ntp-server option";
        //                }
        //                enum "time-zone" {
        //                  description "Time-zone option";
        //                }
        //                enum "sip-server" {
        //                  description "Sip-server option";
        //                }
        //                enum "sip-domain" {
        //                  description "Sip-domain option";
        //                }
        //                enum "nis-server" {
        //                  description "Nis-server option";
        //                }
        //                enum "nis-domain" {
        //                  description "Nis-domain option";
        //                }
        //                enum "fqdn" {
        //                  description "Fully-qualified-domain option";
        //                }
        //                enum "vendor-spec" {
        //                  description "Vendor-spec option";
        //                }
        //                enum "zero-touch-redirect" {
        //                  description "Zero-touch-redirect";
        //                }
        //                enum "bootfile-url" {
        //                  description "Bootfile url";
        //                }
        //                enum "bootfile-param" {
        //                  description "Bootfile param";
        //                }
        //              }
        //            }
        //            // uses apply-advanced;
        //          }
        //          container options {
        //            description "DHCP options";
        //            // uses apply-advanced;
        //            list number {
        //              key name;
        //              description "DHCP option code";
        //              leaf name {
        //                description "DHCP option identifier code";
        //                type union {
        //                  type string {
        //                    pattern "<.*>|$.*";
        //                  }
        //                  type uint32 {
        //                    range "1 .. 254";
        //                  }
        //                }
        //              }
        //              choice option-type-choice {
        //                case case_1 {
        //                  leaf hex-string {
        //                    description "Hexadecimal string";
        //                    type string {
        //                      length "1 .. 510";
        //                    }
        //                  }
        //                }
        //              }
        //            }
        //          }
        //          leaf retransmission-attempt {
        //            description "Number of attempts to retransmit the DHCPV6 client protocol packet";
        //            default "9";
        //            type union {
        //              type string {
        //                pattern "<.*>|$.*";
        //              }
        //              type uint32 {
        //                range "0 .. 50000";
        //              }
        //            }
        //          }
        //          container no-dns-install {
        //            presence "enable no-dns-install";
        //            description "Not propagate DNS to kernel";
        //          }
        //          container update-router-advertisement {
        //            description "Dhcpv6 client update rpd for prefix delegation";
        //            // uses apply-advanced;
        //            list interface {
        //              key name;
        //              ordered-by user;
        //              description "Interfaces on which to delegate prefix";
        //              max-elements 3;
        //              leaf name {
        //                description "Interfaces-name on which to delegate prefix";
        //                type union {
        //                  type jt:interface-name;
        //                  type string {
        //                    pattern "<.*>|$.*";
        //                  }
        //                }
        //              }
        //              // uses apply-advanced;
        //              leaf interface-identifier {
        //                description "Identifier for this interface";
        //                type jt:ipv6addr;
        //              }
        //              leaf prefix-identifier {
        //                description "Prefix identifier for prefix used in this interface";
        //                type jt:ipv6addr;
        //              }
        //              choice managed-configuration-choice {
        //                leaf managed-configuration {
        //                  description "Set managed address configuration";
        //                  type empty;
        //                }
        //                leaf no-managed-configuration {
        //                  description "Don't set managed address configuration";
        //                  type empty;
        //                }
        //              }
        //              choice other-stateful-configuration-choice {
        //                leaf other-stateful-configuration {
        //                  description "Set other stateful configuration";
        //                  type empty;
        //                }
        //                leaf no-other-stateful-configuration {
        //                  description "Don't set other stateful configuration";
        //                  type empty;
        //                }
        //              }
        //              leaf max-advertisement-interval {
        //                description "Maximum advertisement interval";
        //                units "seconds";
        //                type union {
        //                  type string {
        //                    pattern "<.*>|$.*";
        //                  }
        //                  type uint32 {
        //                    range "4 .. 1800";
        //                  }
        //                }
        //              }
        //              leaf min-advertisement-interval {
        //                description "Minimum advertisement interval";
        //                units "seconds";
        //                type union {
        //                  type string {
        //                    pattern "<.*>|$.*";
        //                  }
        //                  type uint32 {
        //                    range "3 .. 1350";
        //                  }
        //                }
        //              }
        //              choice enable-recursive-dns-server-option-choice {
        //                leaf enable-recursive-dns-server-option {
        //                  description "Enables the recursive DNS server option";
        //                  type empty;
        //                }
        //                leaf no-enable-recursive-dns-server-option {
        //                  description "Don't enables the recursive DNS server option";
        //                  type empty;
        //                }
        //              }
        //            }
        //          }
        //          leaf update-server {
        //            description "Propagate TCP/IP settings to DHCP server";
        //            type empty;
        //          }
        //        }
        //        container rpf-check {
        //          presence "enable rpf-check";
        //          description "Enable reverse-path-forwarding checks on this interface";
        //          // uses apply-advanced;
        //          leaf fail-filter {
        //            description "Name of filter applied to packets failing RPF check";
        //            type string;
        //          }
        //          container mode {
        //            description "Mode for reverse path forwarding";
        //            leaf loose {
        //              description "Reverse-path-forwarding loose mode";
        //              type empty;
        //            }
        //          }
        //        }
        //        container accounting {
        //          description "Interface-based accounting options";
        //          // uses apply-advanced;
        //          container source-class-usage {
        //            // uses apply-advanced;
        //            leaf input {
        //              description "Interface for source-class-usage input";
        //              type empty;
        //            }
        //            leaf output {
        //              description "Interface for source-class-usage output";
        //              type empty;
        //            }
        //          }
        //          leaf destination-class-usage {
        //            description "Enable destination class usage on this interface";
        //            type empty;
        //          }
        //        }
        //        leaf mtu {
        //          description "Protocol family maximum transmission unit";
        //          type union {
        //            type uint32;
        //            type string {
        //              pattern "<.*>|$.*";
        //            }
        //          }
        //        }
        //        leaf tcp-mss {
        //          description "Protocol family tcp maximum segment size";
        //          type union {
        //            type string {
        //              pattern "<.*>|$.*";
        //            }
        //            type uint32 {
        //              range "1 .. 65535";
        //            }
        //          }
        //        }
        //        leaf nd6-stale-time {
        //          description "Stale time to reconfirm reachability with inet6 neighbour";
        //          units "seconds";
        //          type union {
        //            type string {
        //              pattern "<.*>|$.*";
        //            }
        //            type uint32 {
        //              range "1 .. 18000";
        //            }
        //          }
        //        }
        //        leaf no-neighbor-learn {
        //          description "Disable neighbor address learning on interface";
        //          type empty;
        //        }
        //        leaf slaac-enable {
        //          description "Enable slaac on management interface";
        //          type empty;
        //        }
        //        container ndp-proxy {
        //          description "Enable ndp proxy on interface";
        //          // uses apply-advanced;
        //          leaf interface-restricted {
        //            description "Enable ndp interface proxy restricted to interface";
        //            type empty;
        //          }
        //          leaf interface-unrestricted {
        //            description "Enable ndp interface proxy unrestricted to interface";
        //            type empty;
        //          }
        //        }
        //        container dad-proxy {
        //          description "DAD proxy on interface";
        //          // uses apply-advanced;
        //          leaf interface-restricted {
        //            description "Enable DAD interface proxy restricted to interface";
        //            type empty;
        //          }
        //          leaf interface-unrestricted {
        //            description "Enable DAD interface proxy unrestricted to interface";
        //            type empty;
        //          }
        //        }
        //        leaf nd6-max-cache {
        //          description "Max interface ND nexthop cache size";
        //          type union {
        //            type string {
        //              pattern "<.*>|$.*";
        //            }
        //            type uint32 {
        //              range "1 .. 2000000";
        //            }
        //          }
        //        }
        //        leaf nd6-new-hold-limit {
        //          description "Max no. of new unresolved nexthops";
        //          type union {
        //            type string {
        //              pattern "<.*>|$.*";
        //            }
        //            type uint32 {
        //              range "1 .. 2000000";
        //            }
        //          }
        //        }
        //        leaf no-redirects {
        //          description "Do not redirect traffic";
        //          type empty;
        //        }
        //        container filter {
        //          description "Packet filtering";
        //          // uses apply-advanced;
        //          choice input_choice {
        //            case case_1 {
        //              container input {
        //                description "Filter to be applied to received packets";
        //                leaf filter-name {
        //                  description "Name of the filter";
        //                  type string;
        //                }
        //                leaf shared-name {
        //                  description "Filter shared-name of instances of interface-shared filter";
        //                  type string;
        //                }
        //                leaf precedence {
        //                  description "Precedence of the filter";
        //                  type union {
        //                    type string {
        //                      pattern "<.*>|$.*";
        //                    }
        //                    type uint32 {
        //                      range "0 .. 255";
        //                    }
        //                  }
        //                }
        //              }
        //            }
        //            case case_2 {
        //              leaf-list input-list {
        //                ordered-by user;
        //                description "List of filter modules applied to received packets ";
        //                type string;
        //              }
        //            }
        //          }
        //          choice output_choice {
        //            case case_1 {
        //              container output {
        //                description "Filter to be applied to transmitted packets";
        //                leaf filter-name {
        //                  description "Name of the filter";
        //                  type string;
        //                }
        //                leaf shared-name {
        //                  description "Filter shared-name of instances of interface-shared filter";
        //                  type string;
        //                }
        //                leaf precedence {
        //                  description "Precedence of the filter";
        //                  type union {
        //                    type string {
        //                      pattern "<.*>|$.*";
        //                    }
        //                    type uint32 {
        //                      range "0 .. 255";
        //                    }
        //                  }
        //                }
        //              }
        //            }
        //            case case_2 {
        //              leaf-list output-list {
        //                ordered-by user;
        //                description "List of filter modules applied to transmitted packets ";
        //                type string;
        //              }
        //            }
        //          }
        //          leaf-list input-chain {
        //            ordered-by user;
        //            description "List of filter modules applied to received packets ";
        //            type string;
        //          }
        //          leaf-list output-chain {
        //            ordered-by user;
        //            description "List of filter modules applied to transmitted packets ";
        //            type string;
        //          }
        //          container adf {
        //            description "Ascend Data Filter definition";
        //            // uses apply-advanced;
        //            list rule {
        //              key name;
        //              ordered-by user;
        //              description "Set of ADF rules";
        //              leaf name {
        //                description "Value for a single rule";
        //                type string;
        //              }
        //              // uses apply-advanced;
        //            }
        //            leaf counter {
        //              description "Add a counter to each rule";
        //              type empty;
        //            }
        //            leaf input-precedence {
        //              description "Precedence of the input rules";
        //              type union {
        //                type string {
        //                  pattern "<.*>|$.*";
        //                }
        //                type uint32 {
        //                  range "0 .. 255";
        //                }
        //              }
        //            }
        //            leaf not-mandatory {
        //              description "No errors will be reported if no rules are present";
        //              type empty;
        //            }
        //            leaf output-precedence {
        //              description "Precedence of the output rules";
        //              type union {
        //                type string {
        //                  pattern "<.*>|$.*";
        //                }
        //                type uint32 {
        //                  range "0 .. 255";
        //                }
        //              }
        //            }
        //          }
        //          leaf group {
        //            description "Group to which interface belongs";
        //            type union {
        //              type string {
        //                pattern "<.*>|$.*";
        //              }
        //              type uint32;
        //            }
        //          }
        //        }
        //        container ingress-queuing-filter {
        //          description "Protocol family ingress-queuing-filter";
        //          leaf filter-name {
        //            description "Name of the ingress-queuing-filter";
        //            type string;
        //          }
        //        }
        //        leaf input-hierarchical-policer {
        //          description "Hierarchical policer for received packets";
        //          type string;
        //        }
        //        container policer {
        //          description "Interface policing";
        //          // uses apply-advanced;
        //          leaf input {
        //            description "Name of policer applied to received packets";
        //            type string;
        //          }
        //          leaf output {
        //            description "Name of policer applied to transmitted packets";
        //            type string;
        //          }
        //        }
        //        container sampling {
        //          description "Interface sampling";
        //          // uses apply-advanced;
        //          leaf input {
        //            description "Sample all packets input on this interface";
        //            type empty;
        //          }
        //          leaf output {
        //            description "Sample all packets output on this interface";
        //            type empty;
        //          }
        //        }
        //        container service {
        //          description "Service operations";
        //          // uses apply-advanced;
        //          container input {
        //            description "Service sets to consider for received packets";
        //            // uses apply-advanced;
        //            list service-set {
        //              key name;
        //              ordered-by user;
        //              description "Service set to consider for received packets";
        //              leaf name {
        //                description "Name of service set";
        //                type string {
        //                }
        //              }
        //              // uses apply-advanced;
        //              leaf service-filter {
        //                description "Name of service filter";
        //                type string;
        //              }
        //            }
        //            leaf post-service-filter {
        //              description "Post-service filter to apply to received packets";
        //              type string;
        //            }
        //          }
        //          container output {
        //            description "Service sets to consider for transmitted packets";
        //            // uses apply-advanced;
        //            list service-set {
        //              key name;
        //              ordered-by user;
        //              description "Service set to consider for transmitted packets";
        //              leaf name {
        //                description "Name of service set";
        //                type string {
        //                }
        //              }
        //              // uses apply-advanced;
        //              leaf service-filter {
        //                description "Name of service filter";
        //                type string;
        //              }
        //            }
        //          }
        //        }
        //        choice tunnel-termination-status {
        //          case case_1 {
        //            leaf tunnel-termination {
        //              description "Tunnel termination";
        //              type empty;
        //            }
        //          }
        //          case case_2 {
        //            leaf no-tunnel-termination {
        //              description "No Tunnel termination";
        //              type empty;
        //            }
        //          }
        //        }
        //        list address {
        //          key name;
        //          ordered-by user;
        //          description "Interface address or destination prefix";
        //          leaf name {
        //            description "Interface address or destination prefix";
        //            type jt:ipv6prefix;
        //          }
        //          // uses apply-advanced;
        //          leaf destination {
        //            description "Destination address";
        //            type jt:ipv6addr;
        //          }
        //          leaf eui-64 {
        //            description "Generate EUI-64 interface ID";
        //            type empty;
        //          }
        //          leaf primary {
        //            description "Candidate for primary address in system";
        //            type empty;
        //          }
        //          leaf preferred {
        //            description "Preferred address on interface";
        //            type empty;
        //          }
        //          leaf master-only {
        //            description "Master management IP address for router";
        //            type empty;
        //          }
        //          list ndp {
        //            key name;
        //            ordered-by user;
        //            description "Static Neighbor Discovery Protocol  entries";
        //            leaf name {
        //              description "Destination IP address";
        //              type jt:ipv6addr;
        //            }
        //            leaf l2-interface {
        //              description "Layer 2 interface name for NDP entry";
        //              type union {
        //                type jt:interface-name;
        //                type string {
        //                  pattern "<.*>|$.*";
        //                }
        //              }
        //            }
        //            choice mac_address_type {
        //              case case_1 {
        //                leaf mac {
        //                  description "MAC address";
        //                  type jt:mac-unicast;
        //                }
        //              }
        //              case case_2 {
        //                leaf multicast-mac {
        //                  description "Multicast MAC address";
        //                  type jt:mac-multicast;
        //                }
        //              }
        //            }
        //            leaf publish {
        //              description "Reply to NDP requests for this entry";
        //              type empty;
        //            }
        //          }
        //          list vrrp-inet6-group {
        //            key name;
        //            ordered-by user;
        //            description "VRRP group";
        //            uses vrrp-group;
        //          }
        //          container web-authentication {
        //            description "Parameters for web-based firewall-user authentication";
        //            // uses apply-advanced;
        //            leaf http {
        //              description "Enable authentication via HTTP";
        //              type empty;
        //            }
        //            leaf https {
        //              description "Enable authentication via HTTPS";
        //              type empty;
        //            }
        //            leaf redirect-to-https {
        //              description "Web authentication redirect to HTTPS";
        //              type empty;
        //            }
        //          }
        //          leaf virtual-gateway-address {
        //            description "Virtual Gateway IP address";
        //            type jt:ipv6addr;
        //          }
        //          leaf subnet-router-anycast {
        //            description "Create a subnet roter anycast address for this address.";
        //            type empty;
        //          }
        //        }
        //        list demux-source {
        //          key name;
        //          ordered-by user;
        //          description "Demux based on source prefix";
        //          leaf name {
        //            type string;
        //          }
        //          // uses apply-advanced;
        //        }
        //        list demux-destination {
        //          key name;
        //          ordered-by user;
        //          description "Demux based on destination prefix";
        //          leaf name {
        //            type string;
        //          }
        //          // uses apply-advanced;
        //        }
        //        container unnumbered-address {
        //          description "Unnumbered interface address/destination prefix";
        //          leaf source {
        //            description "Interface from which to take local address";
        //            type union {
        //              type jt:interface-unit;
        //              type string {
        //                pattern "<.*>|$.*";
        //              }
        //            }
        //          }
        //          leaf preferred-source-address {
        //            description "Preferred address on the donor interface";
        //            type string;
        //          }
        //        }
        //        choice dad-disable-choice {
        //          leaf dad-disable {
        //            description "Disable duplicate-address-detection";
        //            type empty;
        //          }
        //          leaf no-dad-disable {
        //            description "Don't disable duplicate-address-detection";
        //            type empty;
        //          }
        //        }
        //        leaf destination-udp-port {
        //          description "Choose destination UDP port number";
        //          type union {
        //            type string {
        //              pattern "<.*>|$.*";
        //            }
        //            type uint32 {
        //              range "10010 .. 10019";
        //            }
        //          }
        //        }
        //        container auto-configure {
        //          description "Auto configuration";
        //          uses dynamic_ipv6_type;
        //        }
        //      }
        //      container mpls {
        //        presence "enable mpls";
        //        description "MPLS protocol parameters";
        //        // uses apply-advanced;
        //        leaf mtu {
        //          description "Protocol family maximum transmission unit";
        //          type union {
        //            type uint32;
        //            type string {
        //              pattern "<.*>|$.*";
        //            }
        //          }
        //        }
        //        leaf maximum-labels {
        //          description "Protocol family maximum number of labels";
        //          type union {
        //            type string {
        //              pattern "<.*>|$.*";
        //            }
        //            type uint32;
        //          }
        //        }
        //        container filter {
        //          description "Packet filtering";
        //          // uses apply-advanced;
        //          choice input_choice {
        //            case case_1 {
        //              leaf input {
        //                description "Name of filter applied to received packets";
        //                type string;
        //              }
        //            }
        //            case case_2 {
        //              leaf-list input-list {
        //                ordered-by user;
        //                description "List of filter modules applied to received packets ";
        //                type string;
        //              }
        //            }
        //          }
        //          leaf-list input-chain {
        //            ordered-by user;
        //            description "List of filter modules applied to received packets ";
        //            type string;
        //          }
        //          choice output_choice {
        //            case case_1 {
        //              leaf output {
        //                description "Name of filter applied to transmitted packets";
        //                type string;
        //              }
        //            }
        //            case case_2 {
        //              leaf-list output-list {
        //                ordered-by user;
        //                description "List of filter modules applied to transmitted packets ";
        //                type string;
        //              }
        //            }
        //          }
        //          leaf-list output-chain {
        //            ordered-by user;
        //            description "List of filter modules applied to transmitted packets ";
        //            type string;
        //          }
        //          leaf group {
        //            description "Interface group to which interface belongs";
        //            type union {
        //              type string {
        //                pattern "<.*>|$.*";
        //              }
        //              type uint32 {
        //                range "1 .. 255";
        //              }
        //            }
        //          }
        //        }
        //        container ingress-queuing-filter {
        //          description "Protocol family ingress-queuing-filter";
        //          leaf filter-name {
        //            description "Name of the ingress-queuing-filter";
        //            type string;
        //          }
        //        }
        //        leaf input-hierarchical-policer {
        //          description "Hierarchical policer for received packets";
        //          type string;
        //        }
        //        container policer {
        //          description "Interface policing";
        //          // uses apply-advanced;
        //          leaf input {
        //            description "Name of policer applied to received packets";
        //            type string;
        //          }
        //          leaf output {
        //            description "Name of policer applied to transmitted packets";
        //            type string;
        //          }
        //        }
        //        leaf destination-udp-port {
        //          description "Choose destination UDP port number";
        //          type union {
        //            type string {
        //              pattern "<.*>|$.*";
        //            }
        //            type uint32 {
        //              range "10020 .. 10029";
        //            }
        //          }
        //        }
        //      }
        //      container mlppp {
        //        description "Multilink PPP protocol parameters";
        //        // uses apply-advanced;
        //        leaf bundle {
        //          description "Logical interface name this link will join";
        //          type string;
        //        }
        //        choice anchor-points {
        //          case case_1 {
        //            leaf service-interface {
        //              description "Services interface to use";
        //              type union {
        //                type jt:interface-device;
        //                type string {
        //                  pattern "<.*>|$.*";
        //                }
        //              }
        //            }
        //          }
        //          case case_2 {
        //            leaf service-device-pool {
        //              description "Service interface pool name to use";
        //              type string {
        //                length "1 .. 63";
        //              }
        //            }
        //          }
        //        }
        //        leaf dynamic-profile {
        //          description " dynamic profile for interface to use";
        //          type string {
        //            length "1 .. 80";
        //          }
        //        }
        //      }
        //      container mlfr-end-to-end {
        //        presence "enable mlfr-end-to-end";
        //        description "Multilink Frame Relay end-to-end protocol parameters";
        //        // uses apply-advanced;
        //        leaf bundle {
        //          description "Logical interface name this link will join";
        //          type union {
        //            type jt:interface-unit;
        //            type string {
        //              pattern "<.*>|$.*";
        //            }
        //          }
        //        }
        //      }
        //      container mlfr-uni-nni {
        //        presence "enable mlfr-uni-nni";
        //        description "Multilink Frame Relay UNI NNI protocol parameters";
        //        // uses apply-advanced;
        //        leaf bundle {
        //          description "Logical interface name this link will join";
        //          type union {
        //            type jt:interface-unit;
        //            type string {
        //              pattern "<.*>|$.*";
        //            }
        //          }
        //        }
        //      }
        //      container ccc {
        //        presence "enable ccc";
        //        description "Circuit cross-connect parameters";
        //        // uses apply-advanced;
        //        leaf mtu {
        //          description "Protocol family maximum transmission unit";
        //          type union {
        //            type uint32;
        //            type string {
        //              pattern "<.*>|$.*";
        //            }
        //          }
        //        }
        //        container filter {
        //          description "Packet filtering";
        //          // uses apply-advanced;
        //          choice input_choice {
        //            case case_1 {
        //              leaf input {
        //                description "Name of filter applied to received packets";
        //                type string;
        //              }
        //            }
        //            case case_2 {
        //              leaf-list input-list {
        //                ordered-by user;
        //                description "List of filter modules applied to received packets ";
        //                type string;
        //              }
        //            }
        //          }
        //          leaf-list input-chain {
        //            ordered-by user;
        //            description "List of filter modules applied to received packets ";
        //            type string;
        //          }
        //          choice output_choice {
        //            case case_1 {
        //              leaf output {
        //                description "Name of filter applied to transmitted packets";
        //                type string;
        //              }
        //            }
        //            case case_2 {
        //              leaf-list output-list {
        //                ordered-by user;
        //                description "List of filter modules applied to transmitted packets ";
        //                type string;
        //              }
        //            }
        //          }
        //          leaf-list output-chain {
        //            ordered-by user;
        //            description "List of filter modules applied to transmitted packets ";
        //            type string;
        //          }
        //          leaf group {
        //            description "Interface group to which interface belongs";
        //            type union {
        //              type string {
        //                pattern "<.*>|$.*";
        //              }
        //              type uint32 {
        //                range "1 .. 255";
        //              }
        //            }
        //          }
        //        }
        //        container ingress-queuing-filter {
        //          description "Protocol family ingress-queuing-filter";
        //          leaf filter-name {
        //            description "Name of the ingress-queuing-filter";
        //            type string;
        //          }
        //        }
        //        container policer {
        //          description "Interface policing";
        //          // uses apply-advanced;
        //          leaf input {
        //            description "Name of policer applied to received packets";
        //            type string;
        //          }
        //          leaf output {
        //            description "Name of policer applied to transmitted packets";
        //            type string;
        //          }
        //        }
        //        leaf translate-fecn-and-becn {
        //          description "Translate FECN and BECN bits";
        //          type empty;
        //        }
        //        choice de-or-plp {
        //          case case_1 {
        //            leaf translate-discard-eligible {
        //              description "Translate DE bit";
        //              type empty;
        //            }
        //          }
        //          case case_2 {
        //            leaf translate-plp-control-word-de {
        //              description "Translate PLP to/from Martini Control DE bit";
        //              type empty;
        //            }
        //          }
        //        }
        //        leaf keep-address-and-control {
        //          description "Don't strip PPP address and control bytes";
        //          type empty;
        //        }
        //      }
        //      container tcc {
        //        presence "enable tcc";
        //        description "Translational cross-connect parameters";
        //        // uses apply-advanced;
        //        container policer {
        //          description "Interface policing";
        //          // uses apply-advanced;
        //          leaf input {
        //            description "Name of policer applied to received packets";
        //            type string;
        //          }
        //          leaf output {
        //            description "Name of policer applied to transmitted packets";
        //            type string;
        //          }
        //        }
        //        container proxy {
        //          presence "enable proxy";
        //          // uses apply-advanced;
        //          leaf inet-address {
        //            description "Remote host address on non-Ethernet side of Ethernet TCC";
        //            type jt:ipv4addr;
        //          }
        //        }
        //        container remote {
        //          presence "enable remote";
        //          // uses apply-advanced;
        //          leaf inet-address {
        //            description "Remote host address on Ethernet side of Ethernet TCC";
        //            type jt:ipv4addr;
        //          }
        //          leaf mac-address {
        //            description "Remote host MAC address on Ethernet side of Ethernet TCC";
        //            type jt:mac-addr;
        //          }
        //        }
        //        leaf-list protocols {
        //          ordered-by user;
        //          description "Protocols supported on TCC interface";
        //          type enumeration {
        //            enum "mpls" {
        //              description "Multiprotocol Label Switching";
        //            }
        //            enum "inet" {
        //              description "IP version 4";
        //            }
        //            enum "iso" {
        //              description "International Organization for Standardization";
        //            }
        //            enum "inet6" {
        //              description "IP version 6";
        //            }
        //          }
        //        }
        //      }
        //      container vpls {
        //        presence "enable vpls";
        //        description "Virtual private LAN service parameters";
        //        // uses apply-advanced;
        //        leaf core-facing {
        //          description "Interface is core facing";
        //          type empty;
        //        }
        //        container filter {
        //          description "Packet filtering";
        //          // uses apply-advanced;
        //          choice input_choice {
        //            case case_1 {
        //              container input {
        //                description "Filter to be applied to received packets";
        //                leaf filter-name {
        //                  description "Name of the filter";
        //                  type string;
        //                }
        //                leaf shared-name {
        //                  description "Filter shared-name of instances of interface-shared filter";
        //                  type string;
        //                }
        //                leaf precedence {
        //                  description "Precedence of the filter";
        //                  type union {
        //                    type string {
        //                      pattern "<.*>|$.*";
        //                    }
        //                    type uint32 {
        //                      range "0 .. 255";
        //                    }
        //                  }
        //                }
        //              }
        //            }
        //            case case_2 {
        //              leaf-list input-list {
        //                ordered-by user;
        //                description "List of filter modules applied to received packets ";
        //                type string;
        //              }
        //            }
        //          }
        //          leaf-list input-chain {
        //            ordered-by user;
        //            description "List of filter modules applied to received packets ";
        //            type string;
        //          }
        //          leaf-list output-chain {
        //            ordered-by user;
        //            description "List of filter modules applied to transmitted packets ";
        //            type string;
        //          }
        //          choice output_choice {
        //            case case_1 {
        //              container output {
        //                description "Filter to be applied to transmitted packets";
        //                leaf filter-name {
        //                  description "Name of the filter";
        //                  type string;
        //                }
        //                leaf shared-name {
        //                  description "Filter shared-name of instances of interface-shared filter";
        //                  type string;
        //                }
        //                leaf precedence {
        //                  description "Precedence of the filter";
        //                  type union {
        //                    type string {
        //                      pattern "<.*>|$.*";
        //                    }
        //                    type uint32 {
        //                      range "0 .. 255";
        //                    }
        //                  }
        //                }
        //              }
        //            }
        //            case case_2 {
        //              leaf-list output-list {
        //                ordered-by user;
        //                description "List of filter modules applied to transmitted packets ";
        //                type string;
        //              }
        //            }
        //          }
        //          container adf {
        //            description "Ascend Data Filter definition";
        //            // uses apply-advanced;
        //            list rule {
        //              key name;
        //              ordered-by user;
        //              description "Set of ADF rules";
        //              leaf name {
        //                description "Value for a single rule";
        //                type string;
        //              }
        //              // uses apply-advanced;
        //            }
        //            leaf counter {
        //              description "Add a counter to each rule";
        //              type empty;
        //            }
        //            leaf input-precedence {
        //              description "Precedence of the input rules";
        //              type union {
        //                type string {
        //                  pattern "<.*>|$.*";
        //                }
        //                type uint32 {
        //                  range "0 .. 255";
        //                }
        //              }
        //            }
        //            leaf not-mandatory {
        //              description "No errors will be reported if no rules are present";
        //              type empty;
        //            }
        //            leaf output-precedence {
        //              description "Precedence of the output rules";
        //              type union {
        //                type string {
        //                  pattern "<.*>|$.*";
        //                }
        //                type uint32 {
        //                  range "0 .. 255";
        //                }
        //              }
        //            }
        //          }
        //          leaf group {
        //            description "Group to which interface belongs";
        //            type union {
        //              type string {
        //                pattern "<.*>|$.*";
        //              }
        //              type uint32 {
        //                range "1 .. 255";
        //              }
        //            }
        //          }
        //        }
        //        container ingress-queuing-filter {
        //          description "Protocol family ingress-queuing-filter";
        //          leaf filter-name {
        //            description "Name of the ingress-queuing-filter";
        //            type string;
        //          }
        //        }
        //        container iq-policing-filter {
        //          description "Protocol family ingress-queuing-policing-filter";
        //          leaf filter-name {
        //            description "Name of the ingress-queuing-policing-filter";
        //            type string;
        //          }
        //        }
        //        container policer {
        //          description "Interface policing";
        //          // uses apply-advanced;
        //          leaf input {
        //            description "Name of policer applied to received packets";
        //            type string;
        //          }
        //          leaf output {
        //            description "Name of policer applied to transmitted packets";
        //            type string;
        //          }
        //        }
        //        container sampling {
        //          description "Interface sampling";
        //          // uses apply-advanced;
        //          leaf input {
        //            description "Sample all packets input on this interface";
        //            type empty;
        //          }
        //          leaf output {
        //            description "Sample all packets output on this interface";
        //            type empty;
        //          }
        //        }
        //      }
        //      container bridge {
        //        presence "enable bridge";
        //        description "Layer-2 bridging parameters";
        //        // uses apply-advanced;
        //        leaf core-facing {
        //          description "Interface is core facing";
        //          type empty;
        //        }
        //        container filter {
        //          description "Packet filtering";
        //          // uses apply-advanced;
        //          choice input_choice {
        //            case case_1 {
        //              container input {
        //                description "Filter to be applied to received packets";
        //                leaf filter-name {
        //                  description "Name of the filter";
        //                  type string;
        //                }
        //                leaf shared-name {
        //                  description "Filter shared-name of instances of interface-shared filter";
        //                  type string;
        //                }
        //                leaf precedence {
        //                  description "Precedence of the filter";
        //                  type union {
        //                    type string {
        //                      pattern "<.*>|$.*";
        //                    }
        //                    type uint32 {
        //                      range "0 .. 255";
        //                    }
        //                  }
        //                }
        //              }
        //            }
        //            case case_2 {
        //              leaf-list input-list {
        //                ordered-by user;
        //                description "List of filter modules applied to received packets ";
        //                type string;
        //              }
        //            }
        //          }
        //          leaf-list input-chain {
        //            ordered-by user;
        //            description "List of filter modules applied to received packets ";
        //            type string;
        //          }
        //          leaf-list output-chain {
        //            ordered-by user;
        //            description "List of filter modules applied to transmitted packets ";
        //            type string;
        //          }
        //          choice output_choice {
        //            case case_1 {
        //              container output {
        //                description "Filter to be applied to transmitted packets";
        //                leaf filter-name {
        //                  description "Name of the filter";
        //                  type string;
        //                }
        //                leaf shared-name {
        //                  description "Filter shared-name of instances of interface-shared filter";
        //                  type string;
        //                }
        //                leaf precedence {
        //                  description "Precedence of the filter";
        //                  type union {
        //                    type string {
        //                      pattern "<.*>|$.*";
        //                    }
        //                    type uint32 {
        //                      range "0 .. 255";
        //                    }
        //                  }
        //                }
        //              }
        //            }
        //            case case_2 {
        //              leaf-list output-list {
        //                ordered-by user;
        //                description "List of filter modules applied to transmitted packets ";
        //                type string;
        //              }
        //            }
        //          }
        //          container adf {
        //            description "Ascend Data Filter definition";
        //            // uses apply-advanced;
        //            list rule {
        //              key name;
        //              ordered-by user;
        //              description "Set of ADF rules";
        //              leaf name {
        //                description "Value for a single rule";
        //                type string;
        //              }
        //              // uses apply-advanced;
        //            }
        //            leaf counter {
        //              description "Add a counter to each rule";
        //              type empty;
        //            }
        //            leaf input-precedence {
        //              description "Precedence of the input rules";
        //              type union {
        //                type string {
        //                  pattern "<.*>|$.*";
        //                }
        //                type uint32 {
        //                  range "0 .. 255";
        //                }
        //              }
        //            }
        //            leaf not-mandatory {
        //              description "No errors will be reported if no rules are present";
        //              type empty;
        //            }
        //            leaf output-precedence {
        //              description "Precedence of the output rules";
        //              type union {
        //                type string {
        //                  pattern "<.*>|$.*";
        //                }
        //                type uint32 {
        //                  range "0 .. 255";
        //                }
        //              }
        //            }
        //          }
        //          leaf group {
        //            description "Group to which interface belongs";
        //            type union {
        //              type string {
        //                pattern "<.*>|$.*";
        //              }
        //              type uint32 {
        //                range "1 .. 255";
        //              }
        //            }
        //          }
        //        }
        //        container ingress-queuing-filter {
        //          description "Protocol family ingress-queuing-filter";
        //          leaf filter-name {
        //            description "Name of the ingress-queuing-filter";
        //            type string;
        //          }
        //        }
        //        container iq-policing-filter {
        //          description "Protocol family ingress-queuing-policing-filter";
        //          leaf filter-name {
        //            description "Name of the ingress-queuing-policing-filter";
        //            type string;
        //          }
        //        }
        //        container policer {
        //          description "Interface policing";
        //          // uses apply-advanced;
        //          leaf input {
        //            description "Name of policer applied to received packets";
        //            type string;
        //          }
        //          leaf output {
        //            description "Name of policer applied to transmitted packets";
        //            type string;
        //          }
        //        }
        //        leaf interface-mode {
        //          description "Interface mode (access or trunk)";
        //          type enumeration {
        //            enum "access" {
        //              description "Interface mode is access";
        //            }
        //            enum "trunk" {
        //              description "Interface mode is trunk";
        //            }
        //          }
        //        }
        //        leaf vlan-auto-sense {
        //          description "Enable VLAN auto sense on this interface";
        //          type empty;
        //        }
        //        leaf bridge-domain-type {
        //          description "Bridge domain type (svlan or bvlan)";
        //          type enumeration {
        //            enum "svlan" {
        //              description "Bridge domain type svlan";
        //            }
        //            enum "bvlan" {
        //              description "Bridge domain type bvlan";
        //            }
        //          }
        //        }
        //        leaf inter-switch-link {
        //          description "PVLAN inter switch link";
        //          type empty;
        //        }
        //        choice vlan_list {
        //          case case_1 {
        //            leaf vlan-id {
        //              description "Access mode and trunk mode VLAN membership";
        //              type union {
        //                type string {
        //                  pattern "<.*>|$.*";
        //                }
        //                type uint32 {
        //                  range "1 .. 4094";
        //                }
        //              }
        //            }
        //          }
        //          case case_2 {
        //            leaf-list vlan-id-list {
        //              description "Trunk mode VLAN membership for this interface";
        //              type jt:vlan-range;
        //            }
        //          }
        //          case case_3 {
        //            leaf-list inner-vlan-id-list {
        //              description "Trunk mode VLAN membership for this interface based on inner VLAN tag";
        //              type jt:vlan-range;
        //            }
        //          }
        //        }
        //        container vlan-rewrite {
        //          description "Specify vlan translation";
        //          // uses apply-advanced;
        //          list translate {
        //            key name;
        //            ordered-by user;
        //            description "Translate incoming VLAN tag";
        //            leaf name {
        //              description "Specify the incoming VLAN tag";
        //              type union {
        //                type string {
        //                  pattern "<.*>|$.*";
        //                }
        //                type uint32 {
        //                  range "1 .. 4094";
        //                }
        //              }
        //            }
        //            leaf to-vlan-id {
        //              description "Specify the bridge-domain VLAN-ID";
        //              type union {
        //                type string {
        //                  pattern "<.*>|$.*";
        //                }
        //                type uint32 {
        //                  range "1 .. 4094";
        //                }
        //              }
        //            }
        //          }
        //        }
        //        choice isid_list {
        //          case case_1 {
        //            leaf isid-list {
        //              description "Specify the ISID list";
        //              type enumeration {
        //                enum "all-service-groups" {
        //                  description "Map all ISIDs specified under the service-groups";
        //                }
        //                enum "all" {
        //                  description "Map all ISIDs";
        //                }
        //              }
        //            }
        //          }
        //        }
        //        container storm-control {
        //          description "Storm control profile name to bind";
        //          // uses apply-advanced;
        //          leaf profile-name {
        //            description "Profile name";
        //            type string;
        //          }
        //        }
        //        container recovery-timeout {
        //          description "Recovery timeout for this interface";
        //          leaf time-in-seconds {
        //            units "seconds";
        //            type union {
        //              type string {
        //                pattern "<.*>|$.*";
        //              }
        //              type uint32 {
        //                range "10 .. 3600";
        //              }
        //            }
        //          }
        //        }
        //        container sampling {
        //          description "Interface sampling";
        //          // uses apply-advanced;
        //          leaf input {
        //            description "Sample all packets input on this interface";
        //            type empty;
        //          }
        //          leaf output {
        //            description "Sample all packets output on this interface";
        //            type empty;
        //          }
        //        }
        //      }
        //      container ethernet-switching {
        //        description "Ethernet switching parameters";
        //        presence "enable ethernet-switching";
        //        uses ethernet-switching-type;
        //      }
        //      container fibre-channel {
        //        description "Fibre channel switching parameters";
        //        presence "enable fibre-channel";
        //        uses fibre-channel-type;
        //      }
        //      container pppoe {
        //        description "PPP over Ethernet underlying interface-specific options";
        //        presence "enable pppoe";
        //        uses pppoe_underlying_options_type;
        //      }
        //      container any {
        //        presence "enable any";
        //        description "Parameters for 'any' family";
        //        // uses apply-advanced;
        //        container filter {
        //          description "Layer 2 packet filtering";
        //          // uses apply-advanced;
        //          leaf input {
        //            description "Name of filter applied to received packets";
        //            type string {
        //            }
        //          }
        //          leaf group {
        //            description "Group to which interface belongs";
        //            type union {
        //              type string {
        //                pattern "<.*>|$.*";
        //              }
        //              type uint32 {
        //                range "1 .. 255";
        //              }
        //            }
        //          }
        //        }
        //      }
        //    }
        //    leaf service-domain {
        //      description "Service domain to which interface belongs";
        //      type enumeration {
        //        enum "inside" {
        //          description "Inside network";
        //        }
        //        enum "outside" {
        //          description "Outside network";
        //        }
        //      }
        //    }
        //    leaf copy-tos-to-outer-ip-header {
        //      description "Copy IP payload header's ToS field to GRE delivery header";
        //      type empty;
        //    }
        //    leaf copy-tos-to-outer-ip-header-transit {
        //      description "Copy IP ToS field to GRE header for transit packets";
        //      type empty;
        //    }
        //    leaf force-control-packets-on-transit-path {
        //      description "Force control packets to follow transit path";
        //      type empty;
        //    }
        //    container load-balancing-options {
        //      description "AMS subunit load balancing options";
        //      // uses apply-advanced;
        //      leaf preferred-active {
        //        description "Preferred active Interface name";
        //        type union {
        //          type jt:interface-device;
        //          type string {
        //            pattern "<.*>|$.*";
        //          }
        //        }
        //      }
        //      leaf disable-hash {
        //        description "Hash based distribution is not needed for this subunit";
        //        type empty;
        //      }
        //      leaf modulo-key {
        //        description "Modulo based distribution";
        //        type enumeration {
        //          enum "source-ip" {
        //            description "Source Ip Address";
        //          }
        //          enum "destination-ip" {
        //            description "Destination Ip Address";
        //          }
        //        }
        //      }
        //      container hash-keys {
        //        // uses apply-advanced;
        //        leaf-list ingress-key {
        //          ordered-by user;
        //          description "Hash Key for the ingress direction";
        //          type enumeration {
        //            enum "source-ip" {
        //              description "Source Ip Address";
        //            }
        //            enum "destination-ip" {
        //              description "Destination Ip Address";
        //            }
        //            enum "protocol" {
        //              description "Protocol";
        //            }
        //            enum "iif" {
        //              description "Incoming Interface";
        //            }
        //          }
        //        }
        //        leaf-list egress-key {
        //          ordered-by user;
        //          description "Hash Key for the egress direction";
        //          status deprecated;
        //          type enumeration {
        //            enum "source-ip" {
        //              description "Source Ip Address";
        //              status deprecated;
        //            }
        //            enum "destination-ip" {
        //              description "Destination Ip Address";
        //              status deprecated;
        //            }
        //            enum "protocol" {
        //              description "Protocol";
        //              status deprecated;
        //            }
        //            enum "oif" {
        //              description "Outgoing Interface";
        //              status deprecated;
        //            }
        //          }
        //        }
        //        leaf ipv6-source-prefix-length {
        //          description "IPv6 source prefix length for hash computation";
        //          type enumeration {
        //            enum "56" {
        //              description "56 bit IPv6 address prefix";
        //            }
        //            enum "64" {
        //              description "64 bit IPv6 address prefix";
        //            }
        //            enum "96" {
        //              description "96 bit IPv6 address prefix";
        //            }
        //            enum "128" {
        //              description "Complete 128 bit IPv6 address";
        //            }
        //          }
        //        }
        //      }
        //    }
        //    container interface-state {
        //      description "IRB interface state computation";
        //      // uses apply-advanced;
        //      choice state {
        //        case case_1 {
        //          leaf local {
        //            description "IRB State computation based on local interface state";
        //            type empty;
        //          }
        //        }
        //        case case_2 {
        //          leaf remote {
        //            description "IRB State computation based on remote reachability";
        //            type empty;
        //          }
        //        }
        //        case case_3 {
        //          leaf local-remote {
        //            description "IRB State computation based on local or remote reachability";
        //            type empty;
        //          }
        //        }
        //        case case_4 {
        //          leaf local-interface {
        //            description "IRB State computation based on loopback AE port state";
        //            type union {
        //              type jt:interface-name;
        //              type string {
        //                pattern "<.*>|$.*";
        //              }
        //            }
        //          }
        //        }
        //      }
        //      leaf local-count {
        //        description "Minimum number of local layer2 link in up state to consider IRB up";
        //        type union {
        //          type uint16;
        //          type string {
        //            pattern "<.*>|$.*";
        //          }
        //        }
        //      }
        //      leaf vtep-count {
        //        description "Minimum number of VTEP link in up state to consider IRB up";
        //        type union {
        //          type uint16;
        //          type string {
        //            pattern "<.*>|$.*";
        //          }
        //        }
        //      }
        //      container hold-time {
        //        description "Delay before marking interface up or down for defect";
        //        // uses apply-advanced;
        //        leaf up {
        //          description "Delay in seconds before marking IRB interface up";
        //          units "seconds";
        //          type union {
        //            type uint32;
        //            type string {
        //              pattern "<.*>|$.*";
        //            }
        //          }
        //        }
        //        leaf down {
        //          description "Delay in seconds before marking IRB interface down";
        //          units "seconds";
        //          type union {
        //            type uint32;
        //            type string {
        //              pattern "<.*>|$.*";
        //            }
        //          }
        //        }
        //      }
        //    }
        //    leaf mac {
        //      description "Configure logical interface MAC address";
        //      type jt:mac-unicast;
        //    }
        //    leaf virtual-gateway-v4-mac {
        //      description "Configure virtual gateway IPV4 virtual MAC address";
        //      type jt:mac-unicast;
        //    }
        //    leaf virtual-gateway-v6-mac {
        //      description "Configure virtual gateway IPV6 virtual MAC address";
        //      type jt:mac-unicast;
        //    }
        //    leaf no-dhcp-flood {
        //      description "Disable dhcp flooding";
        //      type empty;
        //    }
        //    container forwarding-options {
        //      description "Aggregated Ethernet interface forwarding-options";
        //      // uses apply-advanced;
        //      container load-balance-stateful {
        //        description "Stateful load balancing";
        //        // uses apply-advanced;
        //        leaf per-flow {
        //          description "Enable feature";
        //          type empty;
        //        }
        //        leaf rebalance {
        //          description "Rebalancing interval";
        //          units "per minute";
        //          type union {
        //            type string {
        //              pattern "<.*>|$.*";
        //            }
        //            type uint32 {
        //              range "1 .. 1000";
        //            }
        //          }
        //        }
        //        leaf load-type {
        //          description "Load - defines the flows";
        //          type enumeration {
        //            enum "high" {
        //              description "If the no of flows on this aggregate is large(1000-10000 flows) ";
        //            }
        //            enum "medium" {
        //              description "If the no of flows on this aggregate is moderate(100-1000 flows)";
        //            }
        //            enum "low" {
        //              description "If the no of flows on this aggregate is less(1-100)";
        //            }
        //          }
        //        }
        //      }
        //    }
        //    leaf etree-ac-role {
        //      description "ETREE attachment circuit role";
        //      type enumeration {
        //        enum "root" {
        //          description "ETREE root interface";
        //        }
        //        enum "leaf" {
        //          description "ETREE leaf interface";
        //        }
        //      }
        //    }
        //    container load-balance {
        //      description "Load-balance weight per subscriber interface";
        //      // uses apply-advanced;
        //      leaf weight {
        //        description "Load-balance weight";
        //        type union {
        //          type string {
        //            pattern "<.*>|$.*";
        //          }
        //          type uint32 {
        //            range "1 .. 1000";
        //          }
        //        }
        //      }
        //    }
        //  }
        //  container no-partition {
        //    description "Use channelizable interface as clear channel";
        //    leaf interface-type {
        //      description "Interface type";
        //      type enumeration {
        //        enum "e1" {
        //          description "E1 interface";
        //        }
        //        enum "t1" {
        //          description "T1 interface";
        //        }
        //        enum "at" {
        //          description "ATM interface";
        //        }
        //        enum "t3" {
        //          description "T3 interface";
        //        }
        //        enum "e3" {
        //          description "E3 interface";
        //        }
        //        enum "ct3" {
        //          description "Channelized T3 interface";
        //        }
        //        enum "so" {
        //          description "SONET interface";
        //        }
        //        enum "cau4" {
        //          description "CAU4 interface";
        //        }
        //      }
        //    }
        //  }
        //  list partition {
        //    key name;
        //    ordered-by user;
        //    description "Channelized interface partition";
        //    leaf name {
        //      description "Sublevel interface partition index (for example, 1, 3-4)";
        //      type string;
        //    }
        //    leaf oc-slice {
        //      description "Range of SONET/SDH slices (for example, 1, 7-9)";
        //      type string;
        //    }
        //    leaf timeslots {
        //      description "Timeslots [(1..24) for T1, (1..31) for E1]; for example, 1-3,4,9,22-24 (no spaces)";
        //      type string;
        //    }
        //    leaf interface-type {
        //      description "Sublevel interface type";
        //      type enumeration {
        //        enum "ds" {
        //          description "DS0 interface";
        //        }
        //        enum "e1" {
        //          description "E1 interface";
        //        }
        //        enum "t1" {
        //          description "T1 interface";
        //        }
        //        enum "at" {
        //          description "ATM interface";
        //        }
        //        enum "ct1" {
        //          description "Channelized T1 interface";
        //        }
        //        enum "ce1" {
        //          description "Channelized E1 interface";
        //        }
        //        enum "t3" {
        //          description "T3 interface";
        //        }
        //        enum "ct3" {
        //          description "Channelized T3 interface";
        //        }
        //        enum "e3" {
        //          description "E3 interface";
        //        }
        //        enum "so" {
        //          description "SONET interface";
        //        }
        //        enum "coc1" {
        //          description "Channelized OC1 interface";
        //        }
        //        enum "cau4" {
        //          description "Channelized AU4 interface";
        //        }
        //        enum "dc" {
        //          description "D channel interface";
        //        }
        //        enum "bc" {
        //          description "B channel interface";
        //        }
        //      }
        //    }
        //  }
        //  container radius-options {
        //    description "Interface RADIUS Options";
        //    uses radius_options_vlan_type;
        //  }
        //  leaf rpf-stats {
        //    description "Enable Reverse path forwarding stats for this interface";
        //    type empty;
        //  }
       }
       list interface {
         key name;
         uses interfaces_type;
       }
     }
   }
  //  grouping advisory_options_type {
  //    // uses apply-advanced;
  //    leaf upstream-rate {
  //      description "Recommended upstream shaping rate";
  //      units "bits per second";
  //      type string;
  //    }
  //    leaf downstream-rate {
  //      description "Recommended downstream shaping rate";
  //      units "bits per second";
  //      type string;
  //    }
  //  }
  //  grouping aggregate-load-balance {
  //    description "Load balancing parameters";
  //    // uses apply-advanced;
  //    choice adaptive_option {
  //      case case_1 {
  //        leaf per-packet {
  //          description "Per packet";
  //          type empty;
  //        }
  //      }
  //      case case_2 {
  //        leaf no-adaptive {
  //          description "Disable adaptive";
  //          type empty;
  //        }
  //      }
  //      case case_3 {
  //        container adaptive {
  //          presence "enable adaptive";
  //          description "Enable adaptive load balancing by re-programming selector table";
  //          // uses apply-advanced;
  //          leaf tolerance {
  //            description "Target tolerance in percentage (default 20%)";
  //            units "percent";
  //            type union {
  //              type string {
  //                pattern "<.*>|$.*";
  //              }
  //              type uint32 {
  //                range "1 .. 100";
  //              }
  //            }
  //          }
  //          leaf pps {
  //            description "Adaptive load balance based on packet per second (default bps)";
  //            type empty;
  //          }
  //          leaf scan-interval {
  //            description "Scan interval for multiple of 30 seconds (default 30 seconds)";
  //            type union {
  //              type string {
  //                pattern "<.*>|$.*";
  //              }
  //              type uint32 {
  //                range "1 .. 5";
  //              }
  //            }
  //          }
  //        }
  //      }
  //    }
  //    leaf local-bias {
  //      description "Local bias in percentage";
  //      units "percent";
  //      type union {
  //        type string {
  //          pattern "<.*>|$.*";
  //        }
  //        type uint32 {
  //          range "0 .. 100";
  //        }
  //      }
  //    }
  //  }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
    //  list apply-macro {
    //    key name;
    //    ordered-by user;
    //    description "Macro and parameters for commit script expansion";
    //    uses apply-macro-type;
    //  }
   }
  //  grouping apply-macro-type {
  //    description "Macro data for commit-script expansion";
  //    leaf name {
  //      description "Name of the macro to be expanded";
  //      type string;
  //    }
  //    list data {
  //      key name;
  //      uses macro-data-type;
  //    }
  //  }
  //  grouping aps_type {
  //    // uses apply-advanced;
  //    choice aps_mode {
  //      case case_1 {
  //        leaf working-circuit {
  //          description "Working circuit group name";
  //          type string;
  //        }
  //      }
  //      case case_2 {
  //        leaf protect-circuit {
  //          description "Protect circuit group name";
  //          type string;
  //        }
  //      }
  //    }
  //    leaf annex-b {
  //      description "Annex-b mode";
  //      type empty;
  //    }
  //    leaf wait-to-restore-time {
  //      description "Circuit wait-to-restore time for annex-b";
  //      units "seconds";
  //      type union {
  //        type string {
  //          pattern "<.*>|$.*";
  //        }
  //        type uint32 {
  //          range "1 .. 4294967295";
  //        }
  //      }
  //    }
  //    leaf preserve-interface {
  //      description "Preserve interface state for fast failover";
  //      type empty;
  //    }
  //    leaf neighbor {
  //      description "Neighbor address";
  //      type jt:ipv4addr;
  //    }
  //    leaf paired-group {
  //      description "Name of paired APS group";
  //      type string;
  //    }
  //    container authentication-key {
  //      presence "enable authentication-key";
  //      description "Authentication parameters";
  //      leaf auth_key {
  //        description "Authentication key";
  //        type jt:unreadable;
  //      }
  //    }
  //    leaf switching-mode {
  //      description "APS switching mode";
  //      type enumeration {
  //        enum "bidirectional" {
  //          description "Bidirectional";
  //        }
  //        enum "unidirectional" {
  //          description "Unidirectional";
  //        }
  //      }
  //    }
  //    leaf advertise-interval {
  //      description "Advertise interval";
  //      units "milliseconds";
  //      type union {
  //        type string {
  //          pattern "<.*>|$.*";
  //        }
  //        type uint32 {
  //          range "1 .. 65534";
  //        }
  //      }
  //    }
  //    leaf hold-time {
  //      description "Hold time";
  //      units "milliseconds";
  //      type union {
  //        type string {
  //          pattern "<.*>|$.*";
  //        }
  //        type uint32 {
  //          range "1 .. 65534";
  //        }
  //      }
  //    }
  //    leaf revert-time {
  //      description "Circuit revert time";
  //      units "seconds";
  //      type union {
  //        type string {
  //          pattern "<.*>|$.*";
  //        }
  //        type uint32 {
  //          range "0 .. 65534";
  //        }
  //      }
  //    }
  //    choice break-before-make-choice {
  //      leaf break-before-make {
  //        description "Ensure only one interface is active at a time";
  //        type empty;
  //      }
  //      leaf no-break-before-make {
  //        description "Don't ensure only one interface is active at a time";
  //        type empty;
  //      }
  //    }
  //    choice manual_mode {
  //      case case_1 {
  //        leaf request {
  //          description "Request circuit state";
  //          type enumeration {
  //            enum "protect" {
  //              description "Request protect circuit";
  //            }
  //            enum "working" {
  //              description "Request working circuit";
  //            }
  //          }
  //        }
  //      }
  //      case case_2 {
  //        leaf force {
  //          description "Force circuit state";
  //          type enumeration {
  //            enum "protect" {
  //              description "Force protect circuit";
  //            }
  //            enum "working" {
  //              description "Force working circuit";
  //            }
  //          }
  //        }
  //      }
  //      case case_3 {
  //        leaf lockout {
  //          description "Lockout protection";
  //          type empty;
  //        }
  //      }
  //    }
  //    leaf fast-aps-switch {
  //      description "Fast aps switch";
  //      type empty;
  //    }
  //  }
  //  grouping auto_configure_vlan_type {
  //    // uses apply-advanced;
  //    container stacked-vlan-ranges {
  //      presence "enable stacked-vlan-ranges";
  //      description "Stacked Vlan Range configuration";
  //      // uses apply-advanced;
  //      list dynamic-profile {
  //        key name;
  //        ordered-by user;
  //        description "Attach dynamic-profile to ranges";
  //        max-elements 16;
  //        leaf name {
  //          description "Profile name";
  //          type string;
  //        }
  //        // uses apply-advanced;
  //        leaf-list accept {
  //          ordered-by user;
  //          type enumeration {
  //            enum "inet" {
  //              description "Family inet";
  //            }
  //            enum "inet6" {
  //              description "Family inet6";
  //            }
  //            enum "pppoe" {
  //              description "PPPoE PADI only";
  //            }
  //            enum "dhcp-v4" {
  //              description "DHCP v4 Discover only";
  //            }
  //            enum "dhcp-v6" {
  //              description "DHCP v6 Solicit only";
  //            }
  //            enum "any" {
  //              description "Any in-band packet type";
  //            }
  //          }
  //        }
  //        list ranges {
  //          key name;
  //          ordered-by user;
  //          description "Configure interface based on stacked-vlan range";
  //          leaf name {
  //            description "Stacked-vlan range: [any | <low-tag>-<high-tag>],[any | <low-tag>-<high-tag>]";
  //            type string {
  //            }
  //          }
  //          // uses apply-advanced;
  //        }
  //        container access-profile {
  //          description "Auto-configure VLAN access profile for these ranges";
  //          leaf ap-name {
  //            description "Access profile name";
  //            type string {
  //              length "1 .. 64";
  //            }
  //          }
  //        }
  //      }
  //      container override {
  //        presence "enable override";
  //        description "SVLAN profile override specification ";
  //        // uses apply-advanced;
  //        list outer-tag {
  //          key name;
  //          ordered-by user;
  //          description "Specify pair of SVLAN tags for profile override";
  //          max-elements 8;
  //          leaf name {
  //            description "Stacked-vlan outer tag range to be overridden";
  //            type union {
  //              type string {
  //                pattern "<.*>|$.*";
  //              }
  //              type uint32 {
  //                range "1 .. 4094";
  //              }
  //            }
  //          }
  //          // uses apply-advanced;
  //          leaf inner-tag {
  //            description "Stacked-vlan inner tag to be overridden";
  //            type union {
  //              type string {
  //                pattern "<.*>|$.*";
  //              }
  //              type uint32 {
  //                range "1 .. 4094";
  //              }
  //            }
  //          }
  //          leaf dynamic-profile {
  //            description "Dynamic profile to override with";
  //            type string;
  //          }
  //        }
  //      }
  //      container authentication {
  //        description "Auto-configure stacked VLAN authentication";
  //        uses auto_configure_authentication_type;
  //      }
  //      container access-profile {
  //        description "Auto-configure stacked VLAN access profile";
  //        leaf access-profile-name {
  //          description "Access profile name";
  //          type string {
  //            length "1 .. 64";
  //          }
  //        }
  //      }
  //    }
  //    container vlan-ranges {
  //      description "Vlan Range configuration";
  //      // uses apply-advanced;
  //      list dynamic-profile {
  //        key name;
  //        ordered-by user;
  //        description "Attach dynamic-profile to ranges";
  //        max-elements 16;
  //        leaf name {
  //          description "Profile name";
  //          type string;
  //        }
  //        // uses apply-advanced;
  //        choice accept_type {
  //          case case_1 {
  //            leaf-list accept {
  //              ordered-by user;
  //              type enumeration {
  //                enum "inet" {
  //                  description "Family inet";
  //                }
  //                enum "inet6" {
  //                  description "Family inet6";
  //                }
  //                enum "pppoe" {
  //                  description "PPPoE PADI only";
  //                }
  //                enum "dhcp-v4" {
  //                  description "DHCP v4 Discover only";
  //                }
  //                enum "dhcp-v6" {
  //                  description "DHCP v6 Solicit only";
  //                }
  //                enum "any" {
  //                  description "Any in-band packet type";
  //                }
  //              }
  //            }
  //          }
  //          case case_2 {
  //            leaf-list accept-out-of-band {
  //              ordered-by user;
  //              type enumeration {
  //                enum "ancp" {
  //                  description "ANCP";
  //                }
  //              }
  //            }
  //          }
  //        }
  //        list ranges {
  //          key name;
  //          ordered-by user;
  //          description "Configure interface based on vlan range";
  //          leaf name {
  //            description "Vlan range: [any | <low-tag>-<high-tag>]";
  //            type string {
  //            }
  //          }
  //          // uses apply-advanced;
  //        }
  //        container access-profile {
  //          description "Auto-configure VLAN access profile for these ranges";
  //          leaf ap-name {
  //            description "Access profile name";
  //            type string {
  //              length "1 .. 64";
  //            }
  //          }
  //        }
  //      }
  //      container override {
  //        presence "enable override";
  //        description "VLAN profile override specification";
  //        // uses apply-advanced;
  //        list tag {
  //          key name;
  //          ordered-by user;
  //          description "Specify VLAN tag for profile override";
  //          max-elements 8;
  //          leaf name {
  //            description "Vlan tag to be overridden";
  //            type union {
  //              type string {
  //                pattern "<.*>|$.*";
  //              }
  //              type uint32 {
  //                range "1 .. 4094";
  //              }
  //            }
  //          }
  //          // uses apply-advanced;
  //          leaf dynamic-profile {
  //            description "Dynamic profile to override with";
  //            type string;
  //          }
  //        }
  //      }
  //      container authentication {
  //        description "Auto-configure VLAN authentication";
  //        uses auto_configure_authentication_type;
  //      }
  //      container access-profile {
  //        description "Auto-configure VLAN access profile";
  //        leaf access-profile-name {
  //          description "Access profile name";
  //          type string {
  //            length "1 .. 64";
  //          }
  //        }
  //      }
  //    }
  //    container agent-circuit-identifier {
  //      description "ACI configuration";
  //      // uses apply-advanced;
  //      leaf dynamic-profile {
  //        description "Dynamic profile name";
  //        type string {
  //          length "1 .. 64";
  //        }
  //      }
  //    }
  //    container line-identity {
  //      description "Line-identity configuration";
  //      // uses apply-advanced;
  //      container includes {
  //        presence "enable includes";
  //        description "Agent options configuration";
  //        // uses apply-advanced;
  //        leaf circuit-id {
  //          description "Agent Circit id";
  //          type empty;
  //        }
  //        leaf remote-id {
  //          description "Agent Remote id";
  //          type empty;
  //        }
  //        container accept-no-ids {
  //          presence "enable accept-no-ids";
  //          description "Accept packet with no agent options";
  //          // uses apply-advanced;
  //        }
  //      }
  //      leaf dynamic-profile {
  //        description "Dynamic profile name";
  //        type string {
  //          length "1 .. 64";
  //        }
  //      }
  //    }
  //    leaf remove-when-no-subscribers {
  //      description "Requests auto-deletion of interface when not in use by subscribers";
  //      type empty;
  //    }
  //  }
  //  grouping auto_configure_authentication_type {
  //    description "Autoconf VLAN authentication";
  //    // uses apply-advanced;
  //    leaf-list packet-types {
  //      ordered-by user;
  //      type enumeration {
  //        enum "inet" {
  //          description "Family inet";
  //        }
  //        enum "inet6" {
  //          description "Family inet6";
  //        }
  //        enum "pppoe" {
  //          description "PPPoE PADI only";
  //        }
  //        enum "dhcp-v4" {
  //          description "DHCP v4 Discover only";
  //        }
  //        enum "dhcp-v6" {
  //          description "DHCP v6 Solicit only";
  //        }
  //        enum "any" {
  //          description "Any in-band packet type";
  //        }
  //      }
  //    }
  //    leaf password {
  //      description "Username password";
  //      type string {
  //        length "1 .. 64";
  //      }
  //    }
  //    container username-include {
  //      description "Username options";
  //      // uses apply-advanced;
  //      leaf delimiter {
  //        description "Delimiter/separator character";
  //        type string {
  //          length 1;
  //        }
  //      }
  //      leaf domain-name {
  //        description "Domain name";
  //        type string {
  //          length "1 .. 64";
  //        }
  //      }
  //      leaf user-prefix {
  //        description "User defined prefix";
  //        type string {
  //          length "1 .. 64";
  //        }
  //      }
  //      leaf mac-address {
  //        description "Include MAC address";
  //        type empty;
  //      }
  //      container option-82 {
  //        presence "enable option-82";
  //        description "Include option 82";
  //        leaf circuit-id {
  //          description "Include option 82 circuit-id (sub option 1)";
  //          type empty;
  //        }
  //        leaf remote-id {
  //          description "Include option 82 remote-id (sub option 2)";
  //          type empty;
  //        }
  //      }
  //      leaf option-18 {
  //        description "Include option 18 for dhcp-v6";
  //        type empty;
  //      }
  //      leaf option-37 {
  //        description "Include option 37 for dhcp-v6";
  //        type empty;
  //      }
  //      leaf circuit-type {
  //        description "Include circuit type";
  //        type empty;
  //      }
  //      leaf radius-realm {
  //        description "Include Radius realm name";
  //        type string {
  //          length "1 .. 64";
  //        }
  //      }
  //      leaf interface-name {
  //        description "Include interface name";
  //        type empty;
  //      }
  //      leaf vlan-tags {
  //        description "Include vlan tag(s)";
  //        type empty;
  //      }
  //    }
  //  }
  //  grouping cos_policer {
  //    description "Define a CoS based policer";
  //    leaf name {
  //      description "Policer name";
  //      type string {
  //      }
  //    }
  //    // uses apply-advanced;
  //    container premium {
  //      description "Policer to apply to premium traffic";
  //      presence "enable premium";
  //      uses ethernet_policer;
  //    }
  //    container aggregate {
  //      description "Policer to apply to aggregate traffic";
  //      presence "enable aggregate";
  //      uses ethernet_policer;
  //    }
  //  }
  //  grouping cos_policer_input_priority_map {
  //    description "Input policer priority map";
  //    // uses apply-advanced;
  //    container ieee-802.1p {
  //      description "Use IEEE 802.1p to determine policer priority map";
  //      // uses apply-advanced;
  //      leaf-list premium {
  //        ordered-by user;
  //        description "Input traffic's IEEE 802.1p value to which premium policer is applied";
  //        type union {
  //          type string {
  //            pattern "<.*>|$.*";
  //          }
  //          type uint32 {
  //            range "0 .. 7";
  //          }
  //        }
  //      }
  //    }
  //  }
  //  grouping cos_policer_output_priority_map {
  //    description "Output policer priority map";
  //    // uses apply-advanced;
  //    container classifier {
  //      description "Use classifier as policer priority map";
  //      // uses apply-advanced;
  //      container premium {
  //        description "Output traffic classifier to which premium policer is applied";
  //        // uses apply-advanced;
  //        list forwarding-class {
  //          key name;
  //          ordered-by user;
  //          description "Select a classification for this priority map";
  //          leaf name {
  //            description "Forwarding class name";
  //            type string {
  //            }
  //          }
  //          // uses apply-advanced;
  //          list loss-priority {
  //            key name;
  //            ordered-by user;
  //            description "Select a loss priority";
  //            leaf name {
  //              type enumeration {
  //                enum "low" {
  //                  description "Select low loss priority as premium policer";
  //                }
  //                enum "high" {
  //                  description "Select high loss priority as premium policer";
  //                }
  //              }
  //            }
  //          }
  //        }
  //      }
  //    }
  //  }
  //  grouping dcd_rx_bucket_config {
  //    // uses apply-advanced;
  //    leaf overflow {
  //      description "Overflow behavior";
  //      type enumeration {
  //        enum "tag" {
  //          description "Tag and count overflow packets";
  //        }
  //        enum "discard" {
  //          description "Discard overflow packets";
  //        }
  //      }
  //    }
  //    leaf rate {
  //      description "Bucket rate";
  //      type union {
  //        type string {
  //          pattern "<.*>|$.*";
  //        }
  //        type uint32 {
  //          range "0 .. 100";
  //        }
  //      }
  //    }
  //    leaf threshold {
  //      description "Bucket threshold";
  //      type union {
  //        type string {
  //          pattern "<.*>|$.*";
  //        }
  //        type uint32 {
  //          range "0 .. 65535";
  //        }
  //      }
  //    }
  //  }
  //  grouping dcd_shaping_config {
  //    description "Traffic-shaping profile";
  //    // uses apply-advanced;
  //    choice useless_shaping_choice {
  //      case case_1 {
  //        container cbr {
  //          presence "enable cbr";
  //          description "Constant bandwidth utilization";
  //          leaf cbr-value {
  //            description "Constant bandwidth utilization";
  //            type string;
  //          }
  //          leaf cdvt {
  //            description "Cell Delay Variation Tolerance";
  //            units "microseconds";
  //            type union {
  //              type string {
  //                pattern "<.*>|$.*";
  //              }
  //              type uint32 {
  //                range "1 .. 9999";
  //              }
  //            }
  //          }
  //        }
  //      }
  //      case case_2 {
  //        container vbr {
  //          description "Variable bandwidth utilization";
  //          leaf peak {
  //            description "Peak rate";
  //            type string;
  //          }
  //          leaf sustained {
  //            description "Sustained rate";
  //            type string;
  //          }
  //          leaf burst {
  //            description "Burst size";
  //            type string;
  //          }
  //          leaf cdvt {
  //            description "Cell Delay Variation Tolerance";
  //            units "microseconds";
  //            type union {
  //              type string {
  //                pattern "<.*>|$.*";
  //              }
  //              type uint32 {
  //                range "1 .. 9999";
  //              }
  //            }
  //          }
  //        }
  //      }
  //      case case_3 {
  //        container rtvbr {
  //          description "ATM2 real-time variable bandwidth utilization";
  //          leaf peak {
  //            description "Peak rate";
  //            type string;
  //          }
  //          leaf sustained {
  //            description "Sustained rate";
  //            type string;
  //          }
  //          leaf burst {
  //            description "Burst size";
  //            type string;
  //          }
  //          leaf cdvt {
  //            description "Cell Delay Variation Tolerance";
  //            units "microseconds";
  //            type union {
  //              type string {
  //                pattern "<.*>|$.*";
  //              }
  //              type uint32 {
  //                range "1 .. 9999";
  //              }
  //            }
  //          }
  //        }
  //      }
  //    }
  //    leaf queue-length {
  //      description "Queue length";
  //      type union {
  //        type string {
  //          pattern "<.*>|$.*";
  //        }
  //        type uint32 {
  //          range "1 .. 16383";
  //        }
  //      }
  //    }
  //  }
  //  grouping dcd_tx_bucket_config {
  //    // uses apply-advanced;
  //    leaf overflow {
  //      description "Overflow behavior";
  //      type enumeration {
  //        enum "discard" {
  //          description "Discard overflow packets";
  //        }
  //      }
  //    }
  //    leaf rate {
  //      description "Bucket rate";
  //      type union {
  //        type string {
  //          pattern "<.*>|$.*";
  //        }
  //        type uint32 {
  //          range "0 .. 100";
  //        }
  //      }
  //    }
  //    leaf threshold {
  //      description "Bucket threshold";
  //      type union {
  //        type string {
  //          pattern "<.*>|$.*";
  //        }
  //        type uint32 {
  //          range "0 .. 65535";
  //        }
  //      }
  //    }
  //  }
  //  grouping demux_options_table {
  //    leaf name {
  //      type enumeration {
  //        enum "inet" {
  //          description "Family inet";
  //        }
  //        enum "inet6" {
  //          description "Family inet6";
  //        }
  //      }
  //    }
  //  }
  //  grouping demux_options_type {
  //    // uses apply-advanced;
  //    leaf underlying-interface {
  //      description "Underlying interface name";
  //      type string;
  //    }
  //  }
  //  grouping dhcp-client-type {
  //    description "Dynamic Host Configuration Protocol client configuration";
  //    // uses apply-advanced;
  //    container client-identifier {
  //      description "DHCP server identifies a client by client-identifier value ";
  //      // uses apply-advanced;
  //      choice client-identifier-choice {
  //        case case_1 {
  //          leaf ascii {
  //            description "Client identifier as an ASCII string";
  //            type string;
  //          }
  //        }
  //        case case_2 {
  //          leaf hexadecimal {
  //            description "Client identifier as a hexadecimal string";
  //            type string {
  //            }
  //          }
  //        }
  //      }
  //      container user-id {
  //        description "Add user id to client-id option ";
  //        choice user-id-choice {
  //          case case_1 {
  //            leaf ascii {
  //              description "Client identifier as an ASCII string";
  //              type string;
  //            }
  //          }
  //          case case_2 {
  //            leaf hexadecimal {
  //              description "Client identifier as a hexadecimal string";
  //              type string {
  //              }
  //            }
  //          }
  //        }
  //      }
  //      container prefix {
  //        description "Add prefix to client-id option";
  //        // uses apply-advanced;
  //        leaf host-name {
  //          description "Add router host name to client-id option";
  //          type empty;
  //        }
  //        leaf logical-system-name {
  //          description "Add logical system name to client-id option";
  //          type empty;
  //        }
  //        leaf routing-instance-name {
  //          description "Add routing instance name to client-id option";
  //          type empty;
  //        }
  //      }
  //      leaf use-interface-description {
  //        description "Use the interface description";
  //        type enumeration {
  //          enum "logical" {
  //            description "Use the logical interface description";
  //          }
  //          enum "device" {
  //            description "Use the device interface description";
  //          }
  //        }
  //      }
  //      leaf hardware-type {
  //        description "Hardware type";
  //        default "0";
  //        type union {
  //          type string {
  //            pattern "<.*>|$.*";
  //          }
  //          type uint8 {
  //            range "0 .. 255";
  //          }
  //        }
  //      }
  //    }
  //    container no-dns-install {
  //      presence "enable no-dns-install";
  //      description "Do not install DNS information learned from DHCP server";
  //    }
  //    leaf lease-time {
  //      description "Lease time in seconds requested in DHCP client protocol packet";
  //      units "seconds";
  //      type string;
  //    }
  //    leaf retransmission-attempt {
  //      description "Number of attempts to retransmit the DHCP client protocol packet";
  //      default "4";
  //      type union {
  //        type string {
  //          pattern "<.*>|$.*";
  //        }
  //        type uint32 {
  //          range "0 .. 50000";
  //        }
  //      }
  //    }
  //    leaf retransmission-interval {
  //      description "Number of seconds between successive retransmission";
  //      default "4";
  //      units "seconds";
  //      type union {
  //        type string {
  //          pattern "<.*>|$.*";
  //        }
  //        type uint32 {
  //          range "4 .. 64";
  //        }
  //      }
  //    }
  //    leaf metric {
  //      description "Client initiated default-route metric";
  //      default "0";
  //      type union {
  //        type string {
  //          pattern "<.*>|$.*";
  //        }
  //        type uint32 {
  //          range "0 .. 255";
  //        }
  //      }
  //    }
  //    leaf server-address {
  //      description "DHCP Server-address";
  //      type jt:ipv4addr;
  //    }
  //    leaf update-server {
  //      description "Propagate TCP/IP settings to DHCP server";
  //      type empty;
  //    }
  //    leaf vendor-id {
  //      description "Vendor class id for the DHCP Client";
  //      type string {
  //        length "1 .. 60";
  //      }
  //    }
  //    leaf force-discover {
  //      description "Send DHCPDISCOVER after DHCPREQUEST retransmission failure";
  //      type empty;
  //    }
  //    container options {
  //      description "DHCP options";
  //      // uses apply-advanced;
  //      list number {
  //        key name;
  //        description "DHCP option code";
  //        leaf name {
  //          description "DHCP option identifier code";
  //          type union {
  //            type string {
  //              pattern "<.*>|$.*";
  //            }
  //            type uint32 {
  //              range "1 .. 254";
  //            }
  //          }
  //        }
  //        choice option-type-choice {
  //          case case_1 {
  //            leaf hex-string {
  //              description "Hexadecimal string";
  //              type string {
  //                length "1 .. 510";
  //              }
  //            }
  //          }
  //        }
  //      }
  //      leaf no-hostname {
  //        description "Do not carry hostname (RFC option code is 12) in packet";
  //        type empty;
  //      }
  //    }
  //    list requested-options {
  //      key name;
  //      description "DHCP options";
  //      leaf name {
  //        description "DHCP option identifier code";
  //        type union {
  //          type string {
  //            pattern "<.*>|$.*";
  //          }
  //          type uint32 {
  //            range "1 .. 254";
  //          }
  //        }
  //      }
  //    }
  //  }
  //  grouping dynamic_ifbw_parms_type {
  //    // uses apply-advanced;
  //    leaf capacity {
  //      description "Weight of current (vs. maximum) data rate";
  //      status deprecated;
  //      units "percent";
  //      type union {
  //        type string {
  //          pattern "<.*>|$.*";
  //        }
  //        type uint32 {
  //          range "0 .. 100";
  //        }
  //      }
  //    }
  //    leaf margin {
  //      description "Maximum reduction in bandwidth due to low link quality";
  //      status deprecated;
  //      units "percent";
  //      type union {
  //        type string {
  //          pattern "<.*>|$.*";
  //        }
  //        type uint32 {
  //          range "0 .. 100";
  //        }
  //      }
  //    }
  //    leaf delay {
  //      description "Bandwidth reduction when delay is announced as 1 second";
  //      status deprecated;
  //      units "bits per second";
  //      type string;
  //    }
  //    leaf bandwidth {
  //      description "Weight of current (vs. maximum) data rate";
  //      type union {
  //        type string {
  //          pattern "<.*>|$.*";
  //        }
  //        type uint32 {
  //          range "0 .. 100";
  //        }
  //      }
  //    }
  //    leaf resource {
  //      description "Resource weight";
  //      type union {
  //        type string {
  //          pattern "<.*>|$.*";
  //        }
  //        type uint32 {
  //          range "0 .. 100";
  //        }
  //      }
  //    }
  //    leaf latency {
  //      description "Latency weight";
  //      type union {
  //        type string {
  //          pattern "<.*>|$.*";
  //        }
  //        type uint32 {
  //          range "0 .. 100";
  //        }
  //      }
  //    }
  //    leaf quality {
  //      description "Relative Link Quality weight";
  //      type union {
  //        type string {
  //          pattern "<.*>|$.*";
  //        }
  //        type uint32 {
  //          range "0 .. 100";
  //        }
  //      }
  //    }
  //    leaf data-rate {
  //      description "Data rate weight";
  //      type union {
  //        type string {
  //          pattern "<.*>|$.*";
  //        }
  //        type uint32 {
  //          range "0 .. 100";
  //        }
  //      }
  //    }
  //    leaf threshold {
  //      description "Percentage bandwidth change required for routing updates";
  //      units "percent";
  //      type union {
  //        type string {
  //          pattern "<.*>|$.*";
  //        }
  //        type uint32 {
  //          range "0 .. 100";
  //        }
  //      }
  //    }
  //    container credit {
  //      presence "enable credit";
  //      description "Credit-based scheduling parameters";
  //      // uses apply-advanced;
  //      leaf interval {
  //        description "Grant rate interval in 100mS steps";
  //        type union {
  //          type string {
  //            pattern "<.*>|$.*";
  //          }
  //          type uint16 {
  //            range "1 .. 60";
  //          }
  //        }
  //      }
  //    }
  //  }
  //  grouping dynamic_ipv4_type {
  //    description "Packet triggered subscribers";
  //    // uses apply-advanced;
  //    container address-ranges {
  //      description "Packet triggered subscribers configuration";
  //      // uses apply-advanced;
  //      list dynamic-profile {
  //        key name;
  //        ordered-by user;
  //        description "Attach dynamic-profile to packet triggered subscriber ranges";
  //        max-elements 16;
  //        leaf name {
  //          description "Profile name";
  //          type string;
  //        }
  //        // uses apply-advanced;
  //        list network {
  //          key name;
  //          ordered-by user;
  //          description "IPv4 Network address";
  //          max-elements 16;
  //          leaf name {
  //            description "Specify the network address";
  //            type jt:ipv4prefix;
  //          }
  //          // uses apply-advanced;
  //          list range {
  //            key name;
  //            ordered-by user;
  //            description "Configure demux interface based on source IP address range";
  //            max-elements 16;
  //            leaf name {
  //              description "Name of range";
  //              type string;
  //            }
  //            // uses apply-advanced;
  //            leaf low {
  //              description "Lower limit of address range";
  //              type jt:ipv4prefix;
  //            }
  //            leaf high {
  //              description "Upper limit of address range";
  //              type jt:ipv4prefix;
  //            }
  //          }
  //        }
  //      }
  //      container authentication {
  //        description "Auto-configure packet triggered subscriber authentication";
  //        uses dynamic_ip_authentication_type;
  //      }
  //      leaf session-timeout {
  //        description "Self destruct or auto clear timeout in seconds";
  //        type union {
  //          type string {
  //            pattern "<.*>|$.*";
  //          }
  //          type uint32 {
  //            range "600 .. 6000";
  //          }
  //        }
  //      }
  //    }
  //  }
  //  grouping dynamic_ip_authentication_type {
  //    description "Autoconf packet trigger subscriber authentication";
  //    // uses apply-advanced;
  //    leaf password {
  //      description "Username password";
  //      type string {
  //        length "1 .. 64";
  //      }
  //    }
  //    container username-include {
  //      description "Username options";
  //      // uses apply-advanced;
  //      leaf delimiter {
  //        description "Delimiter/separator character";
  //        type string {
  //          length 1;
  //        }
  //      }
  //      leaf domain-name {
  //        description "Domain name";
  //        type string {
  //          length "1 .. 64";
  //        }
  //      }
  //      leaf user-prefix {
  //        description "User defined prefix";
  //        type string {
  //          length "1 .. 64";
  //        }
  //      }
  //      leaf auth-server-realm {
  //        description "Authentication server realm name";
  //        type string {
  //          length "1 .. 64";
  //        }
  //      }
  //      leaf interface-name {
  //        description "Interface name";
  //        type empty;
  //      }
  //      leaf source-address {
  //        description "Source address";
  //        type empty;
  //      }
  //    }
  //  }
  //  grouping dynamic_ipv6_type {
  //    description "Packet triggered subscribers";
  //    // uses apply-advanced;
  //    container prefix-ranges {
  //      description "Packet triggered subscribers configuration";
  //      // uses apply-advanced;
  //      list dynamic-profile {
  //        key name;
  //        ordered-by user;
  //        description "Attach dynamic-profile to packet triggered subscriber ranges";
  //        max-elements 16;
  //        leaf name {
  //          description "Profile name";
  //          type string;
  //        }
  //        // uses apply-advanced;
  //        list prefix {
  //          key name;
  //          ordered-by user;
  //          description "IPv6 Network prefix ";
  //          max-elements 16;
  //          leaf name {
  //            description "Specify the network prefix";
  //            type jt:ipv6prefix;
  //          }
  //          // uses apply-advanced;
  //          list range {
  //            key name;
  //            ordered-by user;
  //            description "Configure demux interface based on source IP address range";
  //            max-elements 16;
  //            leaf name {
  //              description "Name of range";
  //              type string;
  //            }
  //            // uses apply-advanced;
  //            leaf low {
  //              description "Lower limit of prefix range";
  //              type jt:ipv6prefix;
  //            }
  //            leaf high {
  //              description "Upper limit of prefix range";
  //              type jt:ipv6prefix;
  //            }
  //          }
  //        }
  //      }
  //      container authentication {
  //        description "Auto-configure packet triggered subscriber authentication";
  //        uses dynamic_ip_authentication_type;
  //      }
  //      leaf session-timeout {
  //        description "Self destruct or auto clear timeout in seconds";
  //        type union {
  //          type string {
  //            pattern "<.*>|$.*";
  //          }
  //          type uint32 {
  //            range "600 .. 6000";
  //          }
  //        }
  //      }
  //    }
  //  }
  //  grouping epd_threshold_config {
  //    // uses apply-advanced;
  //    leaf epd-threshold-plp0 {
  //      description "Early packet discard threshold value";
  //      units "cells";
  //      type string;
  //    }
  //    leaf plp1 {
  //      description "Early packet drop threshold value for PLP 1";
  //      units "cells";
  //      type string;
  //    }
  //  }
  //  grouping ethernet-switching-type {
  //    description "Ethernet switching family";
  //    // uses apply-advanced;
  //    leaf port-mode {
  //      description "Type of port mode";
  //      type enumeration {
  //        enum "access" {
  //          description "Interface mode is access";
  //        }
  //        enum "tagged-access" {
  //          description "Interface mode is tagged-access";
  //        }
  //        enum "trunk" {
  //          description "Interface mode is trunk";
  //        }
  //      }
  //    }
  //    leaf interface-mode {
  //      description "Type of interface mode";
  //      default "access";
  //      type enumeration {
  //        enum "access" {
  //          description "Interface mode is access";
  //        }
  //        enum "trunk" {
  //          description "Interface mode is trunk";
  //        }
  //      }
  //    }
  //    leaf inter-switch-link {
  //      description "PVLAN inter switch link";
  //      type empty;
  //    }
  //    leaf reflective-relay {
  //      description "Reflective-relay mode for this interface";
  //      type empty;
  //    }
  //    choice vlan_choice_list {
  //      case case_1 {
  //        container vlan {
  //          description "Virtual LAN parameters";
  //          // uses apply-advanced;
  //          leaf-list members {
  //            ordered-by user;
  //            description "Membership for this interface (name or id)";
  //            type string;
  //          }
  //        }
  //      }
  //      case case_2 {
  //        container inner-vlan {
  //          description "Trunk mode vlan membership for this interface";
  //          // uses apply-advanced;
  //          leaf-list members {
  //            ordered-by user;
  //            description "Membership for this interface (name or id)";
  //            type string;
  //          }
  //        }
  //      }
  //      case case_3 {
  //        leaf-list inner-vlan-id-list {
  //          description "Trunk mode VLAN membership for this interface based on inner VLAN tag";
  //          type jt:vlan-range;
  //        }
  //      }
  //    }
  //    leaf vlan-auto-sense {
  //      description "Enable VLAN auto sense on this interface";
  //      type empty;
  //    }
  //    leaf bridge-domain-type {
  //      description "Bridge domain type";
  //      type enumeration {
  //        enum "svlan" {
  //          description "Bridge domain type SVLAN";
  //        }
  //        enum "bvlan" {
  //          description "Bridge domain type BVLAN";
  //        }
  //      }
  //    }
  //    container vlan-rewrite {
  //      description "Specify VLAN translation";
  //      // uses apply-advanced;
  //      list translate {
  //        key name;
  //        ordered-by user;
  //        description "Translate incoming VLAN tag";
  //        leaf name {
  //          description "Specify the incoming VLAN tag";
  //          type union {
  //            type string {
  //              pattern "<.*>|$.*";
  //            }
  //            type uint32 {
  //              range "1 .. 4094";
  //            }
  //          }
  //        }
  //        leaf to-vlan-id {
  //          description "Specify the bridge-domain VLAN-ID";
  //          type union {
  //            type string {
  //              pattern "<.*>|$.*";
  //            }
  //            type uint32 {
  //              range "1 .. 4094";
  //            }
  //          }
  //        }
  //      }
  //    }
  //    leaf native-vlan-id {
  //      description "Untagged packets on a trunk/tagged-access interface belong to this vlan";
  //      type string {
  //      }
  //    }
  //    choice isid_list {
  //      case case_1 {
  //        leaf isid-list {
  //          description "Specify the ISID list";
  //          type enumeration {
  //            enum "all-service-groups" {
  //              description "Map all ISIDs specified under the service-groups";
  //            }
  //            enum "all" {
  //              description "Map all ISIDs";
  //            }
  //          }
  //        }
  //      }
  //    }
  //    leaf core-facing {
  //      description "Interface is core facing";
  //      type empty;
  //    }
  //    container filter {
  //      description "Packet filtering";
  //      // uses apply-advanced;
  //      leaf input {
  //        description "Name of filter applied to received packets";
  //        type string;
  //      }
  //      leaf input-precedence {
  //        description "Precedence of the filter";
  //        type union {
  //          type string {
  //            pattern "<.*>|$.*";
  //          }
  //          type uint32 {
  //            range "0 .. 255";
  //          }
  //        }
  //      }
  //      leaf-list input-list {
  //        ordered-by user;
  //        description "List of filter modules applied to received packets ";
  //        type string;
  //      }
  //      leaf output {
  //        description "Name of filter applied to transmitted packets";
  //        type string;
  //      }
  //      leaf output-precedence {
  //        description "Precedence of the filter";
  //        type union {
  //          type string {
  //            pattern "<.*>|$.*";
  //          }
  //          type uint32 {
  //            range "0 .. 255";
  //          }
  //        }
  //      }
  //      leaf-list output-list {
  //        ordered-by user;
  //        description "List of filter modules applied to transmitted packets ";
  //        type string;
  //      }
  //      leaf-list input-chain {
  //        ordered-by user;
  //        description "List of filter modules applied to received packets ";
  //        type string;
  //      }
  //      leaf-list output-chain {
  //        ordered-by user;
  //        description "List of filter modules applied to transmitted packets ";
  //        type string;
  //      }
  //      container adf {
  //        description "Ascend Data Filter definition";
  //        // uses apply-advanced;
  //        list rule {
  //          key name;
  //          ordered-by user;
  //          description "Set of ADF rules";
  //          leaf name {
  //            description "Value for a single rule";
  //            type string;
  //          }
  //          // uses apply-advanced;
  //        }
  //        leaf counter {
  //          description "Add a counter to each rule";
  //          type empty;
  //        }
  //        leaf input-precedence {
  //          description "Precedence of the input rules";
  //          type union {
  //            type string {
  //              pattern "<.*>|$.*";
  //            }
  //            type uint32 {
  //              range "0 .. 255";
  //            }
  //          }
  //        }
  //        leaf not-mandatory {
  //          description "No errors will be reported if no rules are present";
  //          type empty;
  //        }
  //        leaf output-precedence {
  //          description "Precedence of the output rules";
  //          type union {
  //            type string {
  //              pattern "<.*>|$.*";
  //            }
  //            type uint32 {
  //              range "0 .. 255";
  //            }
  //          }
  //        }
  //      }
  //      leaf group {
  //        description "Group to which interface belongs";
  //        type union {
  //          type string {
  //            pattern "<.*>|$.*";
  //          }
  //          type uint32 {
  //            range "1 .. 255";
  //          }
  //        }
  //      }
  //    }
  //    container policer {
  //      description "Interface policing";
  //      // uses apply-advanced;
  //      leaf input {
  //        description "Name of policer applied to received packets";
  //        type string;
  //      }
  //      leaf output {
  //        description "Name of policer applied to transmitted packets";
  //        type string;
  //      }
  //    }
  //    container storm-control {
  //      description "Storm control profile name to bind";
  //      // uses apply-advanced;
  //      leaf profile-name {
  //        description "Profile name";
  //        type string;
  //      }
  //    }
  //    container recovery-timeout {
  //      description "Recovery timeout for this interface";
  //      leaf time-in-seconds {
  //        units "seconds";
  //        type union {
  //          type string {
  //            pattern "<.*>|$.*";
  //          }
  //          type uint32 {
  //            range "10 .. 3600";
  //          }
  //        }
  //      }
  //    }
  //  }
  //  grouping ethernet_policer {
  //    description "Define a policer";
  //    // uses apply-advanced;
  //    choice bandwidth {
  //      case case_1 {
  //        leaf bandwidth-limit {
  //          description "Bandwidth limit";
  //          units "bits per second";
  //          type string;
  //        }
  //      }
  //    }
  //    leaf burst-size-limit {
  //      description "Burst size limit";
  //      units "bytes";
  //      type string;
  //    }
  //  }
  //  grouping ett-attributes {
  //    description "Transport ethernet configuration attributes";
  //    // uses apply-advanced;
  //    leaf rate {
  //      description "Ethernet client signal rate";
  //      type enumeration {
  //        enum "100ge" {
  //          description "100 gigabit ethernet";
  //        }
  //      }
  //    }
  //  }
  //  grouping fibre-channel-type {
  //    description "Fibre Channel switching family";
  //    // uses apply-advanced;
  //    leaf port-mode {
  //      description "Port mode";
  //      type enumeration {
  //        enum "f-port" {
  //          description "Fabric port";
  //        }
  //        enum "e-port" {
  //          description "Inter-switch port";
  //        }
  //        enum "np-port" {
  //          description "Proxy node port";
  //        }
  //        enum "auto" {
  //          description "Interface mode (F/E) is determined at runtime";
  //        }
  //      }
  //    }
  //    leaf no-npiv {
  //      description "Disable NPIV";
  //      type empty;
  //    }
  //    container fc-fabric {
  //      description "Virtual fabric parameters";
  //      // uses apply-advanced;
  //      leaf-list members {
  //        ordered-by user;
  //        description "Virtual Fabric Membership for this interface (name or id)";
  //        type string;
  //      }
  //    }
  //    leaf native-fabric {
  //      description "FC frames with no virtual fabric header on a interface belong to this fabric";
  //      type string {
  //      }
  //    }
  //  }
   grouping interfaces_type {
     description "Physical interface";
     leaf name {
       type string;
     }
     // uses apply-advanced;
     leaf description {
       description "Text description of interface";
       type string;
     }
     leaf external-model-name {
       description "Name for interface as configured using 3rd-party model";
       type string;
     }
    //  container management-ethernet-redundancy {
    //    presence "enable management-ethernet-redundancy";
    //    description "Management Interface Redundancy";
    //    // uses apply-advanced;
    //    choice enable_choice {
    //      case case_1 {
    //        leaf redundancy-enable {
    //          description "Enable Managment Ethernet Redundancy";
    //          type empty;
    //        }
    //      }
    //      case case_2 {
    //        leaf redundancy-disable {
    //          description "Disable  Managment Ethernet Redundancy";
    //          type empty;
    //        }
    //      }
    //    }
    //    leaf connectivity-test-interval {
    //      description "Connectivity test interval";
    //      default "5";
    //      units "seconds";
    //      type union {
    //        type string {
    //          pattern "<.*>|$.*";
    //        }
    //        type uint32 {
    //          range "1 .. 10";
    //        }
    //      }
    //    }
    //    leaf connectivity-test-response-interval {
    //      description "Connectivity test response wait time";
    //      default "5";
    //      units "seconds";
    //      type union {
    //        type string {
    //          pattern "<.*>|$.*";
    //        }
    //        type uint32 {
    //          range "1 .. 10";
    //        }
    //      }
    //    }
    //    leaf remote-ipv4-address {
    //      description "Destination IPV4 address to reach remote ";
    //      default "nil";
    //      type jt:ipv4addr;
    //    }
    //    leaf remote-ipv6-address {
    //      description "Destination IPV6 address to reach remote";
    //      default "nil";
    //      type jt:ipv6addr;
    //    }
    //    leaf number-of-connectivity-retries {
    //      description "Number of Connectivity retries ";
    //      default "2";
    //      type union {
    //        type string {
    //          pattern "<.*>|$.*";
    //        }
    //        type uint32 {
    //          range "1 .. 8";
    //        }
    //      }
    //    }
    //  }
     choice enable-disable {
       case case_1 {
         leaf disable {
           description "Disable this interface";
           type empty;
         }
       }
     }
     leaf promiscuous-mode {
       description "Enable promiscuous mode for L3 interface";
       type empty;
     }
     leaf multicast-statistics {
       description "Enable multicast statistics";
       type empty;
     }
     leaf oam-on-svlan {
       description "Propagate SVLAN OAM state to CVLANs";
       type empty;
     }
    //  container fabric-options {
    //    description "Fabric interface specific options";
    //    // uses apply-advanced;
    //    list member-interfaces {
    //      key name;
    //      description "Member interface for the fabric interface";
    //      leaf name {
    //        description "Interface name of member";
    //        type union {
    //          type jt:interface-device;
    //          type string {
    //            pattern "<.*>|$.*";
    //          }
    //        }
    //      }
    //      // uses apply-advanced;
    //    }
    //    container remote-chassis {
    //      presence "enable remote-chassis";
    //      description "Remote chassis reachability";
    //      // uses apply-advanced;
    //      leaf destination {
    //        description "Destination IP address to reach remote chassis";
    //        type jt:ipv4addr;
    //      }
    //    }
    //  }
    //  container traceoptions {
    //    presence "enable traceoptions";
    //    description "Interface trace options";
    //    // uses apply-advanced;
    //    list flag {
    //      key name;
    //      ordered-by user;
    //      description "Tracing parameters";
    //      leaf name {
    //        type enumeration {
    //          enum "ipc" {
    //            description "Trace interface IPC messages";
    //          }
    //          enum "event" {
    //            description "Trace interface events";
    //          }
    //          enum "media" {
    //            description "Trace interface media changes";
    //          }
    //          enum "all" {
    //            description "Enable all interface trace flags";
    //          }
    //        }
    //      }
    //    }
    //  }
    //  leaf passive-monitor-mode {
    //    description "Use interface to tap packets from another router";
    //    type empty;
    //  }
    //  choice keepalive_choices {
    //    case case_1 {
    //      container keepalives {
    //        description "Send or demand keepalive messages";
    //        presence "enable keepalives";
    //        uses keepalives_type;
    //      }
    //    }
    //    case case_2 {
    //      leaf no-keepalives {
    //        description "Do not send keepalive messages";
    //        type empty;
    //      }
    //    }
    //  }
    //  choice traps-choice {
    //    leaf traps {
    //      description "Enable SNMP notifications on state changes";
    //      type empty;
    //    }
    //    leaf no-traps {
    //      description "Don't enable SNMP notifications on state changes";
    //      type empty;
    //    }
    //  }
    //  choice interface-mib-choice {
    //    leaf interface-mib {
    //      description "Enable interface-related MIBs";
    //      type empty;
    //    }
    //    leaf no-interface-mib {
    //      description "Don't enable interface-related MIBs";
    //      type empty;
    //    }
    //  }
    //  leaf accounting-profile {
    //    description "Accounting profile name";
    //    type string;
    //  }
    //  container anchor-point {
    //    description "Anchor point";
    //    // uses apply-advanced;
    //    leaf interface-name {
    //      description "Interface name";
    //      type union {
    //        type jt:interface-device;
    //        type string {
    //          pattern "<.*>|$.*";
    //        }
    //      }
    //    }
    //  }
    //  container targeted-options {
    //    description "Targeting specific options for PS/RLT active-active mode";
    //    // uses apply-advanced;
    //    leaf type {
    //      description "Targeting type of PS";
    //      type enumeration {
    //        enum "manual" {
    //          description "Targeting type is Manual";
    //        }
    //      }
    //    }
    //    choice redundancy_choice {
    //      case case_1 {
    //        leaf logical-interface-fpc-redundancy {
    //          description "Enable FPC redundancy for logical interfaces";
    //          type empty;
    //        }
    //      }
    //      case case_2 {
    //        leaf logical-interface-chassis-redundancy {
    //          description "Enable CHASSIS redundancy for logical interfaces";
    //          type empty;
    //        }
    //      }
    //    }
    //    container rebalance-periodic {
    //      presence "enable rebalance-periodic";
    //      // uses apply-advanced;
    //      leaf start-time {
    //        description "Start time of the rebalance operation ( Wall clock time )";
    //        type jt:time-of-day;
    //      }
    //      leaf interval {
    //        description "Interval of the rebalance operation in hrs";
    //        type union {
    //          type string {
    //            pattern "<.*>|$.*";
    //          }
    //          type uint32 {
    //            range "1 .. 24";
    //          }
    //        }
    //      }
    //    }
    //    leaf rebalance-subscriber-granularity {
    //      description "Max subscriber aggregate weight";
    //      type union {
    //        type string {
    //          pattern "<.*>|$.*";
    //        }
    //        type uint32 {
    //          range "1 .. 65535";
    //        }
    //      }
    //    }
    //  }
    //  choice bypass-queueing-chip-choice {
    //    leaf bypass-queueing-chip {
    //      description "Enable to bypass queueing chip";
    //      type empty;
    //    }
    //    leaf no-bypass-queueing-chip {
    //      description "Don't enable to bypass queueing chip";
    //      type empty;
    //    }
    //  }
    //  choice scheduler_type {
    //    case case_1 {
    //      choice per-unit-scheduler-choice {
    //        leaf per-unit-scheduler {
    //          description "Enable subunit queuing on Frame Relay or VLAN IQ interface";
    //          type empty;
    //        }
    //        leaf no-per-unit-scheduler {
    //          description "Don't enable subunit queuing on Frame Relay or VLAN IQ interface";
    //          type empty;
    //        }
    //      }
    //    }
    //    case case_2 {
    //      leaf shared-scheduler {
    //        description "Enabled shared queuing on an IQ2 interface";
    //        type empty;
    //      }
    //    }
    //    case case_3 {
    //      container hierarchical-scheduler {
    //        presence "enable hierarchical-scheduler";
    //        description "Enable hierarchical scheduling";
    //        leaf maximum-hierarchy-levels {
    //          description "Maximum hierarchy levels";
    //          type union {
    //            type string {
    //              pattern "<.*>|$.*";
    //            }
    //            type uint32;
    //          }
    //        }
    //        leaf maximum-l2-nodes {
    //          description "Maximum l2 nodes, allowed numbers are power of 2 between 1 and 16k (needs FPC reboot)";
    //          default "1";
    //          type union {
    //            type string {
    //              pattern "<.*>|$.*";
    //            }
    //            type uint32 {
    //              range "1 .. 16384";
    //            }
    //          }
    //        }
    //        leaf maximum-l3-nodes {
    //          description "Maximum l3 nodes, allowed numbers are power of 2 between 2 and 32k (needs FPC reboot)";
    //          default "16384";
    //          type union {
    //            type string {
    //              pattern "<.*>|$.*";
    //            }
    //            type uint32 {
    //              range "2 .. 32768";
    //            }
    //          }
    //        }
    //        leaf implicit-hierarchy {
    //          description "Implicit hierarchy (follows interface hierarchy)";
    //          type empty;
    //        }
    //      }
    //    }
    //  }
    //  leaf l2tp-maximum-session {
    //    description "Maximum L2TP session";
    //    type union {
    //      type string {
    //        pattern "<.*>|$.*";
    //      }
    //      type uint32 {
    //        range "0 .. 64000";
    //      }
    //    }
    //  }
    //  leaf schedulers {
    //    description "Number of schedulers to allocate for interface";
    //    type union {
    //      type uint32;
    //      type string {
    //        pattern "<.*>|$.*";
    //      }
    //    }
    //  }
    //  leaf interface-transmit-statistics {
    //    description "Interface statistics based on the transmitted packets";
    //    type empty;
    //  }
    //  leaf cascade-port {
    //    description "Cascade port";
    //    type empty;
    //  }
    //  leaf dce {
    //    description "Respond to Frame Relay status enquiry messages";
    //    type empty;
    //  }
     choice vlan_tag_mode {
       case case_1 {
         leaf vlan-tagging {
           description "802.1q VLAN tagging support";
           type empty;
         }
       }
       case case_2 {
         leaf stacked-vlan-tagging {
           description "Stacked 802.1q VLAN tagging support";
           type empty;
         }
       }
       case case_3 {
         leaf flexible-vlan-tagging {
           description "Support for no tagging, or single and double 802.1q VLAN tagging";
           type empty;
         }
       }
       case case_4 {
         leaf vlan-vci-tagging {
           description "CCC for VLAN Q-in-Q and ATM VPI/VCI interworking";
           type empty;
         }
       }
     }
     leaf native-vlan-id {
       description "Virtual LAN identifier for untagged frames";
       type union {
         type string {
           pattern "<.*>|$.*";
         }
         type uint32 {
           range "0 .. 4094";
         }
       }
     }
     leaf no-native-vlan-insert {
       description "Disable native-vlan-id insertion to untagged frames";
       type empty;
     }
     leaf vlan-offload {
       description "Offload VLAN filtering to NIC HW";
       type empty;
     }
     leaf input-native-vlan-push {
       description "Control native-vlan-id insertion to untagged frames when input-vlan-map push is configured";
       type enumeration {
         enum "disable" {
           description "Disable input-native-vlan-push";
         }
         enum "enable" {
           description "Enable input-native-vlan-push";
         }
       }
     }
     leaf no-pseudowire-down-on-core-isolation {
       description "Do not bring the pseudowire down in the event of EVPN Core isolation";
       type empty;
     }
     leaf number-of-sub-ports {
       description "Number of channels to create for a port";
       type union {
         type string {
           pattern "<.*>|$.*";
         }
         type uint32 {
           range "1 .. 8";
         }
       }
     }
     leaf unused {
       description "Disable physical port";
       type empty;
     }
     leaf speed {
       description "Link speed";
       type enumeration {
         enum "auto" {
           description "Enable auto negotiation of interface speed";
         }
         enum "auto-10m-100m" {
           description "Enable auto negotiation of limiting interface speed to 10m/100m";
         }
         enum "10m" {
         }
         enum "100m" {
         }
         enum "1g" {
         }
         enum "2.5g" {
         }
         enum "5g" {
         }
         enum "10g" {
         }
         enum "25g" {
         }
         enum "40g" {
         }
         enum "50g" {
         }
         enum "100g" {
         }
         enum "200g" {
         }
         enum "400g" {
         }
         enum "800g" {
         }
         enum "oc3" {
         }
         enum "oc12" {
         }
         enum "oc48" {
         }
       }
     }
    //  container forwarding-class-accounting {
    //    presence "enable forwarding-class-accounting";
    //    description "Configure Forwarding-class-accounting parameters";
    //    // uses apply-advanced;
    //    leaf direction {
    //      description "Direction of the traffic to be accounted for IFD";
    //      type enumeration {
    //        enum "ingress" {
    //          description "Enable forwarding-class-accounting for ingress traffic";
    //        }
    //        enum "egress" {
    //          description "Enable forwarding-class-accounting for egress traffic";
    //        }
    //        enum "both" {
    //          description "Enable forwarding-class-accounting for both directions";
    //        }
    //      }
    //    }
    //    container enhanced {
    //      presence "enable enhanced";
    //      // uses apply-advanced;
    //      leaf traffic-type {
    //        description "Traffic-type to be accounted for forwarding-class-accounting";
    //        type enumeration {
    //          enum "unicast-statistics" {
    //            description "Count only unicast traffic for forwarding-class-accounting";
    //          }
    //          enum "multicast-statistics" {
    //            description "Count only multicast traffic for forwarding-class-accounting";
    //          }
    //        }
    //      }
    //      leaf family {
    //        description "Protocol traffic to be accounted for forwarding-class-accounting";
    //        type enumeration {
    //          enum "inet" {
    //            description "Enable forwarding-class-accounting for IPv4 family only";
    //          }
    //          enum "inet6" {
    //            description "Enable forwarding-class-accounting for IPv6 family only";
    //          }
    //          enum "both" {
    //            description "Enable forwarding-class-accounting for both IPv4 and IPv6 family only";
    //          }
    //        }
    //      }
    //      leaf direction {
    //        description "Direction of the traffic to be accounted for forwarding-class-accounting";
    //        type enumeration {
    //          enum "ingress" {
    //            description "Enable forwarding-class-accounting for ingress traffic";
    //          }
    //          enum "egress" {
    //            description "Enable forwarding-class-accounting for egress traffic";
    //          }
    //          enum "both" {
    //            description "Enable forwarding-class-accounting for both ingress and egress traffic";
    //          }
    //        }
    //      }
    //      leaf overhead-bytes {
    //        description "Per octet overhead bytes to be accounted for forwarding-class-accounting";
    //        default "0";
    //        type union {
    //          type string {
    //            pattern "<.*>|$.*";
    //          }
    //          type uint32 {
    //            range "0 .. 255";
    //          }
    //        }
    //      }
    //    }
    //  }
    //  container auto-configure {
    //    description "Auto configuration";
    //    uses auto_configure_vlan_type;
    //  }
     leaf mtu {
       description "Maximum transmit packet size";
       type union {
         type string {
           pattern "<.*>|$.*";
         }
         type uint32;
       }
     }
     container hold-time {
       description "Hold time for link up and link down";
       leaf up {
         description "Link up hold time";
         units "milliseconds";
         type union {
           type uint32;
           type string {
             pattern "<.*>|$.*";
           }
         }
       }
       leaf down {
         description "Link down hold time";
         units "milliseconds";
         type union {
           type uint32;
           type string {
             pattern "<.*>|$.*";
           }
         }
       }
     }
    //  container damping {
    //    description "Interface damping parameters";
    //    // uses apply-advanced;
    //    leaf half-life {
    //      description "Damping half life time";
    //      default "5";
    //      units "seconds";
    //      type union {
    //        type string {
    //          pattern "<.*>|$.*";
    //        }
    //        type uint32 {
    //          range "1 .. 30";
    //        }
    //      }
    //    }
    //    leaf max-suppress {
    //      description "Maximum suppress time";
    //      default "20";
    //      units "seconds";
    //      type union {
    //        type string {
    //          pattern "<.*>|$.*";
    //        }
    //        type uint32 {
    //          range "1 .. 20000";
    //        }
    //      }
    //    }
    //    leaf reuse {
    //      description "Reuse threshold";
    //      default "1000";
    //      type union {
    //        type string {
    //          pattern "<.*>|$.*";
    //        }
    //        type uint32 {
    //          range "1 .. 20000";
    //        }
    //      }
    //    }
    //    leaf suppress {
    //      description "Suppress threshold";
    //      default "2000";
    //      type union {
    //        type string {
    //          pattern "<.*>|$.*";
    //        }
    //        type uint32 {
    //          range "1 .. 20000";
    //        }
    //      }
    //    }
    //    leaf enable {
    //      description "Enable interface damping";
    //      type empty;
    //    }
    //  }
    //  container link-degrade-monitor {
    //    presence "enable link-degrade-monitor";
    //    description "Enable link degrade monitoring";
    //    // uses apply-advanced;
    //    choice enable_choice {
    //      case case_1 {
    //        leaf link-degrade-monitor-enable {
    //          description "Enable Link Degrade Monitoring";
    //          type empty;
    //        }
    //      }
    //      case case_2 {
    //        leaf no-link-degrade-monitor-enable {
    //          description "Disable Link Degrade Monitoring";
    //          type empty;
    //        }
    //      }
    //    }
    //    container actions {
    //      description "Action upon link degrade event";
    //      // uses apply-advanced;
    //      choice action_choice {
    //        case case_1 {
    //          leaf media-based {
    //            description "Media based";
    //            type empty;
    //          }
    //        }
    //      }
    //    }
    //    container recovery {
    //      description "Link degrade recovery mechanism";
    //      // uses apply-advanced;
    //      leaf timer {
    //        description "Auto recovery timer in seconds";
    //        default "1800";
    //        type union {
    //          type uint32;
    //          type string {
    //            pattern "<.*>|$.*";
    //          }
    //        }
    //      }
    //      choice receovery_choice {
    //        case case_1 {
    //          leaf auto {
    //            description "Automatic recovery";
    //            type empty;
    //          }
    //        }
    //        case case_2 {
    //          leaf manual {
    //            description "Manual recovery";
    //            type empty;
    //          }
    //        }
    //      }
    //    }
    //    container thresholds {
    //      description "Link degrade threshold parameters";
    //      // uses apply-advanced;
    //      leaf set {
    //        description "BER at which link considered degraded(1..16)";
    //        default "1e-7";
    //        type string {
    //        }
    //      }
    //      leaf clear {
    //        description "BER at which link considered improved(1..16)";
    //        default "1e-12";
    //        type string {
    //        }
    //      }
    //      leaf warning-set {
    //        description "BER at which link degrade warning raised(1..16)";
    //        default "1e-9";
    //        type string {
    //        }
    //      }
    //      leaf warning-clear {
    //        description "BER at which link degrade warning cleared(1..16)";
    //        default "1e-11";
    //        type string {
    //        }
    //      }
    //      leaf interval {
    //        description "Consecutive link degrade events";
    //        default "10";
    //        type union {
    //          type string {
    //            pattern "<.*>|$.*";
    //          }
    //          type uint32 {
    //            range "1 .. 256";
    //          }
    //        }
    //      }
    //    }
    //  }
    //  container satop-options {
    //    description "Structure-Agnostic TDM over Packet protocol options";
    //    // uses apply-advanced;
    //    leaf idle-pattern {
    //      description "An 8-bit hexadecimal pattern to replace TDM data in a lost packet";
    //      type union {
    //        type string {
    //          pattern "<.*>|$.*";
    //        }
    //        type uint32 {
    //          range "0 .. 255";
    //        }
    //      }
    //    }
    //    leaf payload-size {
    //      description "Number of payload bytes per packet";
    //      type union {
    //        type string {
    //          pattern "<.*>|$.*";
    //        }
    //        type uint32 {
    //          range "64 .. 1024";
    //        }
    //      }
    //    }
    //    container excessive-packet-loss-rate {
    //      description "Packet loss options";
    //      // uses apply-advanced;
    //      leaf threshold {
    //        description "Percentile designating the threshold of excessive packet loss rate";
    //        type union {
    //          type string {
    //            pattern "<.*>|$.*";
    //          }
    //          type uint8 {
    //            range "1 .. 100";
    //          }
    //        }
    //      }
    //      leaf sample-period {
    //        description "Number of milliseconds over which excessive packet loss rate is calculated";
    //        type union {
    //          type string {
    //            pattern "<.*>|$.*";
    //          }
    //          type uint32 {
    //            range "1000 .. 65535";
    //          }
    //        }
    //      }
    //    }
    //    choice jitter-buffer-size {
    //      case case_1 {
    //        leaf jitter-buffer-packets {
    //          description "Number of packets in jitter buffer before packet data is played out in the line";
    //          type union {
    //            type string {
    //              pattern "<.*>|$.*";
    //            }
    //            type uint32 {
    //              range "1 .. 64";
    //            }
    //          }
    //        }
    //      }
    //      case case_2 {
    //        leaf jitter-buffer-latency {
    //          description "Number of milliseconds delay in jitter buffer before packet data is played out in the line";
    //          units "milliseconds";
    //          type union {
    //            type string {
    //              pattern "<.*>|$.*";
    //            }
    //            type uint32 {
    //              range "1 .. 1000";
    //            }
    //          }
    //        }
    //      }
    //      case case_3 {
    //        leaf jitter-buffer-auto-adjust {
    //          description "Automatically adjust jitter buffer";
    //          type empty;
    //        }
    //      }
    //    }
    //    leaf bit-rate {
    //      description "In multiples of DS0";
    //      type union {
    //        type string {
    //          pattern "<.*>|$.*";
    //        }
    //        type uint32 {
    //          range "1 .. 10240";
    //        }
    //      }
    //    }
    //  }
    //  container cesopsn-options {
    //    description "Structure-Aware TDM over Packet protocol options";
    //    // uses apply-advanced;
    //    leaf idle-pattern {
    //      description "An 8-bit hexadecimal pattern to replace TDM data in a lost packet";
    //      type union {
    //        type string {
    //          pattern "<.*>|$.*";
    //        }
    //        type uint32 {
    //          range "0 .. 255";
    //        }
    //      }
    //    }
    //    leaf packetization-latency {
    //      description "Number of microseconds to create packets";
    //      units "microseconds";
    //      type union {
    //        type string {
    //          pattern "<.*>|$.*";
    //        }
    //        type uint32 {
    //          range "1000 .. 8000";
    //        }
    //      }
    //    }
    //    leaf payload-size {
    //      description "Number of payload bytes per packet";
    //      type union {
    //        type string {
    //          pattern "<.*>|$.*";
    //        }
    //        type uint32 {
    //          range "64 .. 1024";
    //        }
    //      }
    //    }
    //    container excessive-packet-loss-rate {
    //      description "Packet loss options";
    //      // uses apply-advanced;
    //      leaf threshold {
    //        description "Percentile designating the threshold of excessive packet loss rate";
    //        type union {
    //          type string {
    //            pattern "<.*>|$.*";
    //          }
    //          type uint8 {
    //            range "1 .. 100";
    //          }
    //        }
    //      }
    //      leaf sample-period {
    //        description "Number of milliseconds over which excessive packet loss rate is calculated";
    //        type union {
    //          type string {
    //            pattern "<.*>|$.*";
    //          }
    //          type uint32 {
    //            range "1000 .. 65535";
    //          }
    //        }
    //      }
    //    }
    //    choice jitter-buffer-size {
    //      case case_1 {
    //        leaf jitter-buffer-packets {
    //          description "Number of packets in jitter buffer before packet data is played out in the line";
    //          type union {
    //            type string {
    //              pattern "<.*>|$.*";
    //            }
    //            type uint32 {
    //              range "1 .. 64";
    //            }
    //          }
    //        }
    //      }
    //      case case_2 {
    //        leaf jitter-buffer-latency {
    //          description "Number of milliseconds delay in jitter buffer before packet data is played out in the line";
    //          units "milliseconds";
    //          type union {
    //            type string {
    //              pattern "<.*>|$.*";
    //            }
    //            type uint32 {
    //              range "1 .. 1000";
    //            }
    //          }
    //        }
    //      }
    //      case case_3 {
    //        leaf jitter-buffer-auto-adjust {
    //          description "Automatically adjust jitter buffer";
    //          type empty;
    //        }
    //      }
    //    }
    //    leaf bit-rate {
    //      description "In multiples of DS0";
    //      type union {
    //        type string {
    //          pattern "<.*>|$.*";
    //        }
    //        type uint32 {
    //          range "1 .. 10240";
    //        }
    //      }
    //    }
    //  }
    //  container ima-group-options {
    //    description "IMA group options";
    //    // uses apply-advanced;
    //    leaf frame-length {
    //      description "Frame length (cells)";
    //      type enumeration {
    //        enum "32" {
    //        }
    //        enum "64" {
    //        }
    //        enum "128" {
    //        }
    //        enum "256" {
    //        }
    //      }
    //    }
    //    leaf symmetry {
    //      description "Symmetry of IMA group";
    //      default "symmetrical-config-and-operation";
    //      type enumeration {
    //        enum "symmetrical-config-and-operation" {
    //        }
    //        enum "symmetrical-config-asymmetrical-operation" {
    //        }
    //      }
    //    }
    //    leaf transmit-clock {
    //      description "Transmit clock";
    //      type enumeration {
    //        enum "common" {
    //          description "Common transmit clock";
    //        }
    //        enum "independent" {
    //          description "Independent transmit clock";
    //        }
    //      }
    //    }
    //    leaf version {
    //      description "IMA specification version";
    //      type enumeration {
    //        enum "1.0" {
    //          description "Version 1.0";
    //        }
    //        enum "1.1" {
    //          description "Version 1.1";
    //        }
    //      }
    //    }
    //    container minimum-links {
    //      description "IMA group minimum active links";
    //      choice minimum_links_type {
    //        case case_1 {
    //          leaf symmetrical {
    //            description "Minimum active receive and transmit links";
    //            type union {
    //              type string {
    //                pattern "<.*>|$.*";
    //              }
    //              type uint32 {
    //                range "1 .. 32";
    //              }
    //            }
    //          }
    //        }
    //      }
    //    }
    //    container frame-synchronization {
    //      description "IMA group frame synchronization state parameters";
    //      // uses apply-advanced;
    //      leaf alpha {
    //        description "Consecutive invalid ICP cells";
    //        type union {
    //          type string {
    //            pattern "<.*>|$.*";
    //          }
    //          type uint32 {
    //            range "1 .. 2";
    //          }
    //        }
    //      }
    //      leaf beta {
    //        description "Consecutive errored ICP cells";
    //        type union {
    //          type string {
    //            pattern "<.*>|$.*";
    //          }
    //          type uint32 {
    //            range "1 .. 5";
    //          }
    //        }
    //      }
    //      leaf gamma {
    //        description "Consecutive valid ICP cells";
    //        type union {
    //          type string {
    //            pattern "<.*>|$.*";
    //          }
    //          type uint32 {
    //            range "1 .. 5";
    //          }
    //        }
    //      }
    //    }
    //    container test-procedure {
    //      description "IMA group test pattern procedure";
    //      // uses apply-advanced;
    //      leaf period {
    //        description "Length of IMA pattern test";
    //        units "seconds";
    //        type union {
    //          type string {
    //            pattern "<.*>|$.*";
    //          }
    //          type uint32 {
    //            range "1 .. 4294967294";
    //          }
    //        }
    //      }
    //      leaf interface {
    //        description "Interface name of the IMA link to test";
    //        type union {
    //          type jt:interface-device;
    //          type string {
    //            pattern "<.*>|$.*";
    //          }
    //        }
    //      }
    //      leaf pattern {
    //        description "IMA test pattern";
    //        type union {
    //          type string {
    //            pattern "<.*>|$.*";
    //          }
    //          type uint32 {
    //            range "1 .. 254";
    //          }
    //        }
    //      }
    //    }
    //    leaf differential-delay {
    //      description "Maximum differential delay among links in the IMA group";
    //      units "milliseconds";
    //      type union {
    //        type string {
    //          pattern "<.*>|$.*";
    //        }
    //        type uint32 {
    //          range "1 .. 56";
    //        }
    //      }
    //    }
    //  }
    //  container ima-link-options {
    //    description "IMA link options";
    //    // uses apply-advanced;
    //    leaf group-id {
    //      description "IMA group ID this IMA link belongs to";
    //      type union {
    //        type string {
    //          pattern "<.*>|$.*";
    //        }
    //        type uint32;
    //      }
    //    }
    //  }
    //  list multi-chassis-protection {
    //    key name;
    //    description "Inter-Chassis protection configuration";
    //    uses multi-chassis-protection-group;
    //  }
    //  container clocking {
    //    description "Interface clock source";
    //    choice clocking_choices {
    //      case case_1 {
    //        leaf internal {
    //          description "Clocking provided by local system";
    //          type empty;
    //        }
    //      }
    //      case case_2 {
    //        container external {
    //          presence "enable external";
    //          description "Clocking provided by DCE (loop timing)";
    //        }
    //      }
    //    }
    //  }
     leaf link-mode {
       description "Link operational mode";
       type enumeration {
         enum "automatic" {
           description "Automatically negotiate duplex";
         }
         enum "half-duplex" {
           description "Half-duplex operation";
         }
         enum "full-duplex" {
           description "Full-duplex operation";
         }
       }
     }
     leaf media-type {
       description "Interface media type (copper or fiber)";
       type enumeration {
         enum "copper" {
           description "Copper as media";
         }
         enum "fiber" {
           description "Fiber as media";
         }
       }
     }
     leaf encapsulation {
       description "Physical link-layer encapsulation";
       type enumeration {
         enum "ethernet" {
           description "Ethernet physical media";
         }
         enum "fddi" {
           description "FDDI physical media";
         }
         enum "token-ring" {
           description "Token Ring physical media";
         }
         enum "ppp" {
           description "Serial PPP device";
         }
         enum "ppp-ccc" {
           description "Serial PPP device for a cross-connect";
         }
         enum "ppp-tcc" {
           description "Serial PPP device for a translational cross-connect";
         }
         enum "ether-vpls-ppp" {
           description "Ethernet VPLS over PPP (bridging) device";
         }
         enum "frame-relay" {
           description "Frame Relay encapsulation";
         }
         enum "frame-relay-ccc" {
           description "Frame Relay for cross-connect";
         }
         enum "frame-relay-tcc" {
           description "Frame Relay for translational cross-connect";
         }
         enum "extended-frame-relay-ccc" {
           description "Any Frame Relay DLCI for cross-connect";
         }
         enum "extended-frame-relay-tcc" {
           description "Any Frame Relay DLCI for translational cross-connect";
         }
         enum "flexible-frame-relay" {
           description "Multiple Frame Relay encapsulations";
         }
         enum "frame-relay-port-ccc" {
           description "Frame Relay port encapsulation for a cross-connect";
         }
         enum "frame-relay-ether-type" {
           description "Cisco-compatible Frame Relay encapsulation";
         }
         enum "frame-relay-ether-type-tcc" {
           description "Cisco-compatible Frame Relay encapsulation for translational cross-connect";
         }
         enum "extended-frame-relay-ether-type-tcc" {
           description "Cisco-compatible Frame Relay encapsulation any DLCI for translational cross-connect";
         }
         enum "cisco-hdlc" {
           description "Cisco-compatible HDLC framing";
         }
         enum "cisco-hdlc-ccc" {
           description "Cisco-compatible HDLC framing for a cross-connect";
         }
         enum "cisco-hdlc-tcc" {
           description "Cisco-compatible HDLC framing for a translational cross-connect";
         }
         enum "vlan-ccc" {
           description "802.1q tagging for a cross-connect";
         }
         enum "extended-vlan-ccc" {
           description "Nonstandard TPID tagging for a cross-connect";
         }
         enum "ethernet-ccc" {
           description "Ethernet cross-connect";
         }
         enum "flexible-ethernet-services" {
           description "Allows per-unit Ethernet encapsulation configuration";
         }
         enum "smds-dxi" {
           description "SMDS DXI framing";
         }
         enum "atm-pvc" {
           description "ATM permanent virtual circuits";
         }
         enum "atm-ccc-cell-relay" {
           description "ATM cell relay encapsulation for cross-connect";
         }
         enum "ethernet-over-atm" {
           description "Ethernet over ATM encapsulation";
         }
         enum "ethernet-tcc" {
           description "Ethernet translational cross-connect";
         }
         enum "extended-vlan-tcc" {
           description "802.1q tagging for a translational cross-connect";
         }
         enum "multilink-frame-relay-uni-nni" {
           description "Multilink Frame Relay UNI NNI (FRF.16) encapsulation";
         }
         enum "satop" {
           description "Structure-Agnostic TDM over Packet encapsulation";
         }
         enum "cesopsn" {
           description "Structure-Agnostic TDM over Packet encapsulation";
         }
         enum "ima" {
           description "Inverse Multiplexing for ATM";
         }
         enum "ethernet-vpls" {
           description "Ethernet virtual private LAN service";
         }
         enum "ethernet-bridge" {
           description "Ethernet layer-2 bridging";
         }
         enum "vlan-vpls" {
           description "VLAN virtual private LAN service";
         }
         enum "vlan-vci-ccc" {
           description "CCC for VLAN Q-in-Q and ATM VPI/VCI interworking";
         }
         enum "extended-vlan-vpls" {
           description "Extended VLAN virtual private LAN service";
         }
         enum "extended-vlan-bridge" {
           description "VLAN layer-2 bridging";
         }
         enum "multilink-ppp" {
           description "Multilink PPP";
         }
         enum "generic-services" {
           description "Generic services";
         }
       }
     }
    //  leaf network-isolation-profile {
    //    description "Attach a network isolation profile on this interface";
    //    type string;
    //  }
    //  container esi {
    //    description "ESI configuration of multi-homed interface";
    //    // uses apply-advanced;
    //    container auto-derive {
    //      description "Auto-derive ESI value for the interface";
    //      // uses apply-advanced;
    //      choice esitype {
    //        case case_1 {
    //          leaf lacp-pe-system-id-and-admin-key {
    //            description "Auto-derive ESI from lacp pe system-id and admin key";
    //            type empty;
    //          }
    //        }
    //        case case_2 {
    //          leaf type-1-lacp {
    //            description "Auto-generate Type1 ESI LACP";
    //            type empty;
    //          }
    //        }
    //        case case_3 {
    //          container type-3-system-mac {
    //            description "Auto-generate Type3 ESI System-mac";
    //            // uses apply-advanced;
    //            leaf mac {
    //              description "System mac";
    //              type jt:mac-unicast;
    //            }
    //            leaf local-discriminator {
    //              description "Local-discriminator";
    //              type union {
    //                type string {
    //                  pattern "<.*>|$.*";
    //                }
    //                type int32 {
    //                  range "0 .. 16777215";
    //                }
    //              }
    //            }
    //          }
    //        }
    //      }
    //    }
    //    leaf identifier {
    //      description "ESI value for the interface";
    //      type jt:esi;
    //    }
    //    choice mode {
    //      case case_1 {
    //        leaf single-active {
    //          description "Single-active mode";
    //          type empty;
    //        }
    //      }
    //      case case_2 {
    //        leaf all-active {
    //          description "All-active mode";
    //          type empty;
    //        }
    //      }
    //    }
    //    container df-election-granularity {
    //      presence "enable df-election-granularity";
    //      description "DF Election Granularity Selection ";
    //      // uses apply-advanced;
    //      choice mode {
    //        case case_1 {
    //          container per-esi {
    //            presence "enable per-esi";
    //            description "DF Election Granularity Per Esi";
    //            // uses apply-advanced;
    //            leaf lacp-oos-on-ndf {
    //              description "Lacp Oos";
    //              type empty;
    //            }
    //          }
    //        }
    //        case case_2 {
    //          leaf per-esi-vlan {
    //            description "Per Esi Vlan";
    //            type empty;
    //          }
    //        }
    //      }
    //    }
    //    container df-election-type {
    //      presence "enable df-election-type";
    //      description "DF Election Type";
    //      // uses apply-advanced;
    //      choice pref_choice {
    //        case case_1 {
    //          container preference {
    //            presence "enable preference";
    //            description "Preference based DF election";
    //            // uses apply-advanced;
    //            leaf value {
    //              description "Preference value for EVPN Multihoming DF election";
    //              default "32767";
    //              type union {
    //                type string {
    //                  pattern "<.*>|$.*";
    //                }
    //                type uint32 {
    //                  range "0 .. 65535";
    //                }
    //              }
    //            }
    //          }
    //        }
    //      }
    //      choice mod_choice {
    //        case case_1 {
    //          container mod {
    //            presence "enable mod";
    //            description "MOD based DF election";
    //          }
    //        }
    //      }
    //    }
    //    leaf source-bmac {
    //      description "Unicast Source B-MAC address per ESI for PBB-EVPN";
    //      type jt:mac-unicast;
    //    }
    //  }
    //  container framing {
    //    description "Frame type";
    //    // uses apply-advanced;
    //    choice frame {
    //      case case_1 {
    //        leaf lan-phy {
    //          description "802.3ae 10-Gbps LAN-mode interface";
    //          type empty;
    //        }
    //      }
    //      case case_2 {
    //        leaf wan-phy {
    //          description "802.3ae 10-Gbps WAN-mode interface";
    //          type empty;
    //        }
    //      }
    //      case case_3 {
    //        leaf sonet {
    //          description "SONET framing";
    //          type empty;
    //        }
    //      }
    //      case case_4 {
    //        leaf sdh {
    //          description "SDH framing";
    //          type empty;
    //        }
    //      }
    //    }
    //    leaf precise-bandwidth {
    //      description "Use precise bandwidth for 10G wan-phy interface";
    //      type empty;
    //    }
    //  }
    //  leaf unidirectional {
    //    description "Unidirectional Mode";
    //    type empty;
    //  }
    //  container lmi {
    //    description "Local Management Interface settings";
    //    // uses apply-advanced;
    //    leaf n391dte {
    //      description "DTE full status polling interval";
    //      type union {
    //        type string {
    //          pattern "<.*>|$.*";
    //        }
    //        type uint16 {
    //          range "1 .. 255";
    //        }
    //      }
    //    }
    //    leaf n392dce {
    //      description "DCE error threshold";
    //      type union {
    //        type string {
    //          pattern "<.*>|$.*";
    //        }
    //        type uint16 {
    //          range "1 .. 10";
    //        }
    //      }
    //    }
    //    leaf n392dte {
    //      description "DTE error threshold";
    //      type union {
    //        type string {
    //          pattern "<.*>|$.*";
    //        }
    //        type uint16 {
    //          range "1 .. 10";
    //        }
    //      }
    //    }
    //    leaf n393dce {
    //      description "DCE monitored event count";
    //      type union {
    //        type string {
    //          pattern "<.*>|$.*";
    //        }
    //        type uint16 {
    //          range "1 .. 10";
    //        }
    //      }
    //    }
    //    leaf n393dte {
    //      description "DTE monitored event count";
    //      type union {
    //        type string {
    //          pattern "<.*>|$.*";
    //        }
    //        type uint16 {
    //          range "1 .. 10";
    //        }
    //      }
    //    }
    //    leaf t391dte {
    //      description "DTE polling timer";
    //      units "seconds";
    //      type union {
    //        type string {
    //          pattern "<.*>|$.*";
    //        }
    //        type uint16 {
    //          range "5 .. 30";
    //        }
    //      }
    //    }
    //    leaf t392dce {
    //      description "DCE polling verification timer";
    //      units "seconds";
    //      type union {
    //        type string {
    //          pattern "<.*>|$.*";
    //        }
    //        type uint16 {
    //          range "5 .. 30";
    //        }
    //      }
    //    }
    //    leaf lmi-type {
    //      description "Specify the Frame Relay LMI type";
    //      type enumeration {
    //        enum "ansi" {
    //          description "Use ANSI Annex D LMI";
    //        }
    //        enum "itu" {
    //          description "Use ITU Q933a Annex A LMI";
    //        }
    //        enum "c-lmi" {
    //          description "Use Consortium LMI";
    //        }
    //      }
    //    }
    //  }
    //  container mlfr-uni-nni-bundle-options {
    //    description "Multilink Frame Relay UNI NNI (FRF.16) management settings";
    //    // uses apply-advanced;
    //    container cisco-interoperability {
    //      description "FRF.16 Cisco interoperability settings";
    //      // uses apply-advanced;
    //      leaf send-lip-remove-link-for-link-reject {
    //        description "Send Link Integrity Protocol remove link on receiving add-link rejection";
    //        type empty;
    //      }
    //    }
    //    leaf mrru {
    //      description "Maximum received reconstructed unit";
    //      units "bytes";
    //      type union {
    //        type string {
    //          pattern "<.*>|$.*";
    //        }
    //        type uint16 {
    //          range "1500 .. 4500";
    //        }
    //      }
    //    }
    //    leaf yellow-differential-delay {
    //      description "Yellow differential delay among bundle links to give warning";
    //      units "milliseconds";
    //      type union {
    //        type string {
    //          pattern "<.*>|$.*";
    //        }
    //        type uint16 {
    //          range "3 .. 2000";
    //        }
    //      }
    //    }
    //    leaf red-differential-delay {
    //      description "Red differential delay among bundle links to take action";
    //      units "milliseconds";
    //      type union {
    //        type string {
    //          pattern "<.*>|$.*";
    //        }
    //        type uint16 {
    //          range "5 .. 2000";
    //        }
    //      }
    //    }
    //    leaf action-red-differential-delay {
    //      description "Type of actions when differential delay exceeds red limit";
    //      type enumeration {
    //        enum "remove-link" {
    //          description "Remove bundle link from service when exceeding red limit";
    //        }
    //        enum "disable-tx" {
    //          description "Disable transfer of bundle link when exceeding red limit";
    //        }
    //      }
    //    }
    //    leaf fragment-threshold {
    //      description "Fragmentation threshold";
    //      units "bytes";
    //      type union {
    //        type string {
    //          pattern "<.*>|$.*";
    //        }
    //        type uint32 {
    //          range "64 .. 16320";
    //        }
    //      }
    //    }
    //    leaf drop-timeout {
    //      description "Drop timeout";
    //      units "milliseconds";
    //      type union {
    //        type string {
    //          pattern "<.*>|$.*";
    //        }
    //        type uint16 {
    //          range "0 .. 2000";
    //        }
    //      }
    //    }
    //    leaf link-layer-overhead {
    //      description "Link layer bit stuffing overhead (0.0 .. 50.0 percent)";
    //      type jt:unsigned-float;
    //    }
    //    leaf lmi-type {
    //      description "Specify the multilink Frame Relay UNI NNI LMI type";
    //      type enumeration {
    //        enum "ansi" {
    //          description "Use ANSI Annex D LMI";
    //        }
    //        enum "itu" {
    //          description "Use ITU Q933a Annex A LMI";
    //        }
    //        enum "c-lmi" {
    //          description "Use Consortium LMI";
    //        }
    //      }
    //    }
    //    leaf minimum-links {
    //      description "Minimum number of links to sustain the bundle";
    //      type union {
    //        type string {
    //          pattern "<.*>|$.*";
    //        }
    //        type uint16 {
    //          range "1 .. 8";
    //        }
    //      }
    //    }
    //    leaf hello-timer {
    //      description "LIP hello timer";
    //      type union {
    //        type string {
    //          pattern "<.*>|$.*";
    //        }
    //        type uint16 {
    //          range "5 .. 180";
    //        }
    //      }
    //    }
    //    leaf acknowledge-timer {
    //      description "LIP ack timer";
    //      type union {
    //        type string {
    //          pattern "<.*>|$.*";
    //        }
    //        type uint16 {
    //          range "1 .. 10";
    //        }
    //      }
    //    }
    //    leaf acknowledge-retries {
    //      description "LIP ack retry times";
    //      type union {
    //        type string {
    //          pattern "<.*>|$.*";
    //        }
    //        type uint16 {
    //          range "1 .. 5";
    //        }
    //      }
    //    }
    //    leaf n391 {
    //      description "Multilink Frame Relay UNI NNI full status polling counter";
    //      type union {
    //        type string {
    //          pattern "<.*>|$.*";
    //        }
    //        type uint16 {
    //          range "1 .. 255";
    //        }
    //      }
    //    }
    //    leaf n392 {
    //      description "Multilink Frame Relay UNI NNI LMI error threshold";
    //      type union {
    //        type string {
    //          pattern "<.*>|$.*";
    //        }
    //        type uint16 {
    //          range "1 .. 10";
    //        }
    //      }
    //    }
    //    leaf n393 {
    //      description "Multilink Frame Relay UNI NNI LMI monitored event count";
    //      type union {
    //        type string {
    //          pattern "<.*>|$.*";
    //        }
    //        type uint16 {
    //          range "1 .. 10";
    //        }
    //      }
    //    }
    //    leaf t391 {
    //      description "Multilink Frame Relay UNI NNI link integrity verify polling timer";
    //      type union {
    //        type string {
    //          pattern "<.*>|$.*";
    //        }
    //        type uint16 {
    //          range "5 .. 30";
    //        }
    //      }
    //    }
    //    leaf t392 {
    //      description "Multilink Frame Relay UNI NNI polling verification timer";
    //      type union {
    //        type string {
    //          pattern "<.*>|$.*";
    //        }
    //        type uint16 {
    //          range "5 .. 30";
    //        }
    //      }
    //    }
    //  }
     leaf mac {
       description "Hardware MAC address";
       type jt:mac-unicast;
     }
     leaf no-forwarding-viable {
       description "Disable forwarding";
       type empty;
     }
     container p4rt {
       description "P4-runtime interfaces";
       // uses apply-advanced;
       leaf id {
         description "Port number";
         type union {
           type string {
             pattern "<.*>|$.*";
           }
           type uint64 {
             range "1 .. 4294967296";
           }
         }
       }
       leaf node-id {
         description "Device Id";
         type union {
           type string {
             pattern "<.*>|$.*";
           }
           type uint64 {
             range "1 .. 18446744073709551615";
           }
         }
       }
     }
    //  container receive-bucket {
    //    description "Set receive bucket parameters";
    //    uses dcd_rx_bucket_config;
    //  }
    //  container transmit-bucket {
    //    description "Set transmit bucket parameters";
    //    uses dcd_tx_bucket_config;
    //  }
    //  leaf shared-interface {
    //    description "Enable shared interface on the interface";
    //    type empty;
    //  }
    //  container sonet-options {
    //    description "SONET interface-specific options";
    //    uses sonet_options_type;
    //  }
    //  container logical-tunnel-options {
    //    description "Logical Tunnel interface-specific options";
    //    // uses apply-advanced;
    //    container link-protection {
    //      presence "enable link-protection";
    //      description "Enable link protection mode";
    //      // uses apply-advanced;
    //      leaf revertive {
    //        description "Revert back (Default mode) from active backup link to primary, if primary is UP";
    //        type empty;
    //      }
    //      leaf non-revertive {
    //        description "Do not revert back from active backup link to primary, if primary is UP";
    //        type empty;
    //      }
    //    }
    //    leaf per-unit-mac-disable {
    //      description "Disable the creation of per unit mac address on LT IFLs for VPLS/CCC encaps";
    //      type empty;
    //    }
    //    container load-balance {
    //      uses aggregate-load-balance;
    //    }
    //    leaf distribution-list {
    //      description "Distribution list to which interface belongs";
    //      type string {
    //        length "1 .. 20";
    //      }
    //    }
    //  }
    //  container aggregated-sonet-options {
    //    description "Aggregated SONET interface-specific options";
    //    // uses apply-advanced;
    //    leaf minimum-links {
    //      description "Minimum number of aggregated links";
    //      type union {
    //        type string {
    //          pattern "<.*>|$.*";
    //        }
    //        type uint16;
    //      }
    //    }
    //    leaf link-speed {
    //      description "Aggregated links speed";
    //      type enumeration {
    //        enum "oc3" {
    //          description "Links are OC-3c or STM-1c";
    //        }
    //        enum "oc12" {
    //          description "Links are OC-12c or STM-4c";
    //        }
    //        enum "oc48" {
    //          description "Links are OC-48c or STM-16c";
    //        }
    //        enum "oc192" {
    //          description "Links are OC-192c or STM-64c";
    //        }
    //        enum "oc768" {
    //          description "Links are OC-768c or STM-256c";
    //        }
    //        enum "mixed" {
    //          description "Links are various speeds";
    //        }
    //      }
    //    }
    //    leaf minimum-bandwidth {
    //      description "Minimum bandwidth necessary to sustain bundle";
    //      units "bps";
    //      type union {
    //        type string {
    //          pattern "<.*>|$.*";
    //        }
    //        type uint64 {
    //          range "0 .. 159232000000";
    //        }
    //      }
    //    }
    //  }
    //  container atm-options {
    //    description "ATM interface-specific options";
    //    // uses apply-advanced;
    //    leaf pic-type {
    //      description "Type of ATM PIC (ATM I, ATM II or ATM CE)";
    //      type enumeration {
    //        enum "atm-ce" {
    //          description "CE PIC";
    //        }
    //        enum "atm2" {
    //          description "ATM II IQ PIC";
    //        }
    //        enum "atm1" {
    //          description "ATM I PIC";
    //        }
    //      }
    //    }
    //    leaf cell-bundle-size {
    //      description "L2 circuit cell bundle size";
    //      units "cells";
    //      type union {
    //        type string {
    //          pattern "<.*>|$.*";
    //        }
    //        type uint32 {
    //          range "1 .. 176";
    //        }
    //      }
    //    }
    //    leaf cell-bundle-timeout {
    //      description "L2 circuit cell bundle timeout";
    //      units "microseconds";
    //      type union {
    //        type string {
    //          pattern "<.*>|$.*";
    //        }
    //        type uint32 {
    //          range "1 .. 512";
    //        }
    //      }
    //    }
    //    leaf plp-to-clp {
    //      description "Enable ATM2 PLP to CLP copy";
    //      type empty;
    //    }
    //    leaf use-null-cw {
    //      description "Always insert/strip null control words with cell-relay";
    //      type empty;
    //    }
    //    container promiscuous-mode {
    //      presence "enable promiscuous-mode";
    //      description "Set ATM interface to promiscuous mode";
    //      // uses apply-advanced;
    //      list vpi {
    //        key name;
    //        ordered-by user;
    //        description "Open this VPI in promiscuous mode";
    //        leaf name {
    //          description "Virtual path index";
    //          type union {
    //            type string {
    //              pattern "<.*>|$.*";
    //            }
    //            type uint32 {
    //              range "0 .. 255";
    //            }
    //          }
    //        }
    //      }
    //    }
    //    list vpi {
    //      key name;
    //      ordered-by user;
    //      description "Define a virtual path";
    //      leaf name {
    //        description "Virtual path index";
    //        type union {
    //          type string {
    //            pattern "<.*>|$.*";
    //          }
    //          type uint32 {
    //            range "0 .. 255";
    //          }
    //        }
    //      }
    //      // uses apply-advanced;
    //      leaf maximum-vcs {
    //        description "Maximum number of virtual circuits on this VP";
    //        type union {
    //          type uint32;
    //          type string {
    //            pattern "<.*>|$.*";
    //          }
    //        }
    //      }
    //      container shaping {
    //        description "Virtual path traffic-shaping options";
    //        uses dcd_shaping_config;
    //      }
    //      container oam-period {
    //        description "F4 OAM cell period";
    //        choice oam_period_choices {
    //          case case_1 {
    //            leaf oam-period {
    //              description "F4 OAM cell period";
    //              units "seconds";
    //              type union {
    //                type string {
    //                  pattern "<.*>|$.*";
    //                }
    //                type uint32 {
    //                  range "1 .. 900";
    //                }
    //              }
    //            }
    //          }
    //          case case_2 {
    //            container disable {
    //              presence "enable disable";
    //              description "Disable F4 OAM loopback";
    //            }
    //          }
    //        }
    //      }
    //      container oam-liveness {
    //        description "F4 OAM virtual path liveness parameters";
    //        // uses apply-advanced;
    //        leaf up-count {
    //          description "Number of F4 OAM cells to consider VP up";
    //          type union {
    //            type string {
    //              pattern "<.*>|$.*";
    //            }
    //            type uint32 {
    //              range "1 .. 255";
    //            }
    //          }
    //        }
    //        leaf down-count {
    //          description "Number of F4 OAM cells to consider VP down";
    //          type union {
    //            type string {
    //              pattern "<.*>|$.*";
    //            }
    //            type uint32 {
    //              range "1 .. 255";
    //            }
    //          }
    //        }
    //      }
    //    }
    //    container ilmi {
    //      presence "enable ilmi";
    //      description "Enable Interim Local Management Interface";
    //      // uses apply-advanced;
    //    }
    //    list linear-red-profiles {
    //      key name;
    //      ordered-by user;
    //      description "ATM2 CoS virtual circuit drop profiles";
    //      leaf name {
    //        description "Linear RED profile name";
    //        type string {
    //        }
    //      }
    //      leaf queue-depth {
    //        description "Maximum queue depth";
    //        units "cells";
    //        type string;
    //      }
    //      leaf high-plp-threshold {
    //        description "Fill level percentage when linear RED is applied for high PLP";
    //        type union {
    //          type string {
    //            pattern "<.*>|$.*";
    //          }
    //          type uint32 {
    //            range "0 .. 100";
    //          }
    //        }
    //      }
    //      leaf low-plp-threshold {
    //        description "Fill level percentage when linear RED is applied for low PLP";
    //        type union {
    //          type string {
    //            pattern "<.*>|$.*";
    //          }
    //          type uint32 {
    //            range "0 .. 100";
    //          }
    //        }
    //      }
    //      leaf high-plp-max-threshold {
    //        description "Fill level percentage with 100 percent packet drop for high PLP";
    //        type union {
    //          type string {
    //            pattern "<.*>|$.*";
    //          }
    //          type uint32 {
    //            range "0 .. 100";
    //          }
    //        }
    //      }
    //      leaf low-plp-max-threshold {
    //        description "Fill level percentage with 100 percent packet drop for low PLP";
    //        type union {
    //          type string {
    //            pattern "<.*>|$.*";
    //          }
    //          type uint32 {
    //            range "0 .. 100";
    //          }
    //        }
    //      }
    //    }
    //    list scheduler-maps {
    //      key name;
    //      ordered-by user;
    //      description "ATM2 CoS parameters assigned to forwarding classes";
    //      leaf name {
    //        description "ATM2 CoS scheduler map name";
    //        type string {
    //        }
    //      }
    //      // uses apply-advanced;
    //      leaf vc-cos-mode {
    //        description "ATM2 virtual circuit CoS mode";
    //        type enumeration {
    //          enum "strict" {
    //            description "Always schedule high priority queue first";
    //          }
    //          enum "alternate" {
    //            description "Every other packet from high priority queue (default)";
    //          }
    //        }
    //      }
    //      list forwarding-class {
    //        key name;
    //        ordered-by user;
    //        description "Scheduling parameters associated with forwarding class";
    //        leaf name {
    //          description "Forwarding class name";
    //          type string {
    //          }
    //        }
    //        // uses apply-advanced;
    //        leaf priority {
    //          description "Queuing priority assigned to forwarding class";
    //          type enumeration {
    //            enum "low" {
    //              description "Low priority queuing";
    //            }
    //            enum "high" {
    //              description "High priority queuing";
    //            }
    //          }
    //        }
    //        container transmit-weight {
    //          description "Transmit weight";
    //          choice weight-method {
    //            case case_1 {
    //              leaf percent {
    //                description "Transmit weight as percentage";
    //                type union {
    //                  type string {
    //                    pattern "<.*>|$.*";
    //                  }
    //                  type uint32 {
    //                    range "5 .. 100";
    //                  }
    //                }
    //              }
    //            }
    //            case case_2 {
    //              leaf cells {
    //                description "Transmit weight by cells count";
    //                type string;
    //              }
    //            }
    //          }
    //        }
    //        choice drop-profile-method {
    //          case case_1 {
    //            container epd-threshold {
    //              description "Early packet discard threshold for ATM2";
    //              uses epd_threshold_config;
    //            }
    //          }
    //          case case_2 {
    //            leaf linear-red-profile {
    //              description "Linear RED profile profile name";
    //              type string;
    //            }
    //          }
    //        }
    //      }
    //    }
    //    container mpls {
    //      description "MPLS options";
    //      uses mpls_ifd_options;
    //    }
    //    choice payload-scrambler-choice {
    //      leaf payload-scrambler {
    //        description "Enable payload scrambling";
    //        type empty;
    //      }
    //      leaf no-payload-scrambler {
    //        description "Don't enable payload scrambling";
    //        type empty;
    //      }
    //    }
    //  }
    //  container multiservice-options {
    //    description "Multiservice interface-specific options";
    //    // uses apply-advanced;
    //    choice syslog-choice {
    //      leaf syslog {
    //        description "Enable system logging on this interface";
    //        type empty;
    //      }
    //      leaf no-syslog {
    //        description "Don't enable system logging on this interface";
    //        type empty;
    //      }
    //    }
    //    choice core-dump-choice {
    //      leaf core-dump {
    //        description "Enable core dumping on this interface";
    //        type empty;
    //      }
    //      leaf no-core-dump {
    //        description "Don't enable core dumping on this interface";
    //        type empty;
    //      }
    //    }
    //    choice dump-on-flow-control-choice {
    //      leaf dump-on-flow-control {
    //        description "Enable dumping for this interface on prolonged flow-control";
    //        status deprecated;
    //        type empty;
    //      }
    //      leaf no-dump-on-flow-control {
    //        description "Don't enable dumping for this interface on prolonged flow-control";
    //        status deprecated;
    //        type empty;
    //      }
    //    }
    //    choice reset-on-flow-control-choice {
    //      leaf reset-on-flow-control {
    //        description "Enable resetting this interface on prolonged flow-control";
    //        status deprecated;
    //        type empty;
    //      }
    //      leaf no-reset-on-flow-control {
    //        description "Don't enable resetting this interface on prolonged flow-control";
    //        status deprecated;
    //        type empty;
    //      }
    //    }
    //    container flow-control-options {
    //      description "Flow control configuration";
    //      // uses apply-advanced;
    //      leaf dump-on-flow-control {
    //        description "Cause core dump during prolonged flow-control";
    //        type empty;
    //      }
    //      leaf reset-on-flow-control {
    //        description "Reset interface during prolonged flow-control";
    //        type empty;
    //      }
    //      leaf down-on-flow-control {
    //        description "Bring interface down during prolonged flow-control";
    //        type empty;
    //      }
    //      leaf up-on-flow-control {
    //        description "Keep interface up during prolonged flow-control";
    //        type empty;
    //      }
    //    }
    //  }
    //  container ggsn-options {
    //    description "GGSN interface-specific options";
    //    // uses apply-advanced;
    //    choice syslog-choice {
    //      leaf syslog {
    //        description "Enable system logging on this interface";
    //        type empty;
    //      }
    //      leaf no-syslog {
    //        description "Don't enable system logging on this interface";
    //        type empty;
    //      }
    //    }
    //    choice core-dump-choice {
    //      leaf core-dump {
    //        description "Enable core dumping on this interface";
    //        type empty;
    //      }
    //      leaf no-core-dump {
    //        description "Don't enable core dumping on this interface";
    //        type empty;
    //      }
    //    }
    //  }
    //  container ppp-options {
    //    description "Point-to-Point Protocol (PPP) interface-specific options";
    //    uses ppp_options_type;
    //  }
    //  container redundancy-options {
    //    description "Redundancy options";
    //    // uses apply-advanced;
    //    leaf primary {
    //      description "Specify the primary interface";
    //      type union {
    //        type jt:interface-device;
    //        type string {
    //          pattern "<.*>|$.*";
    //        }
    //      }
    //    }
    //    leaf secondary {
    //      description "Specify the secondary interface";
    //      type union {
    //        type jt:interface-device;
    //        type string {
    //          pattern "<.*>|$.*";
    //        }
    //      }
    //    }
    //    container redundancy-peer {
    //      description "Specify information for peer";
    //      // uses apply-advanced;
    //      leaf ipaddress {
    //        description "Specify the IP address";
    //        type jt:ipv4addr;
    //      }
    //    }
    //    container redundancy-local {
    //      description "Specify information for the local peer";
    //      // uses apply-advanced;
    //      leaf data-address {
    //        description "Specify the HA local data IP address";
    //        type jt:ipv4addr;
    //      }
    //    }
    //    leaf routing-instance {
    //      description "Specify routing-instance for the HA traffic";
    //      type string;
    //    }
    //    leaf replication-threshold {
    //      description "Duration for which flow should remain active for replication";
    //      default "180";
    //      units "seconds";
    //      type union {
    //        type string {
    //          pattern "<.*>|$.*";
    //        }
    //        type uint32 {
    //          range "60 .. 3600";
    //        }
    //      }
    //    }
    //    container replication-options {
    //      description "Specify state replication attributes";
    //      // uses apply-advanced;
    //      leaf mtu {
    //        description "Specify the maximal packet size for replicated data";
    //        default "1500";
    //        type union {
    //          type string {
    //            pattern "<.*>|$.*";
    //          }
    //          type uint32 {
    //            range "1500 .. 8000";
    //          }
    //        }
    //      }
    //    }
    //    container replicate-services {
    //      description "Replicate services state from active to backup";
    //      // uses apply-advanced;
    //      leaf pgcp {
    //        description "Replicate the PGCP service state";
    //        type empty;
    //      }
    //    }
    //  }
    //  container load-balancing-options {
    //    description "Load-balancing on services pics";
    //    // uses apply-advanced;
    //    list member-interface {
    //      key name;
    //      max-elements 36;
    //      leaf name {
    //        description "Interface name";
    //        type union {
    //          type jt:interface-device;
    //          type string {
    //            pattern "<.*>|$.*";
    //          }
    //        }
    //      }
    //      // uses apply-advanced;
    //      container redundancy-group {
    //        description "Group id to represent a pair of active-backup mams";
    //        leaf description {
    //          description "Text description mapping the redundancy group id";
    //          type string;
    //        }
    //        leaf group-id {
    //          description "Value for Redundancy-group";
    //          type union {
    //            type string {
    //              pattern "<.*>|$.*";
    //            }
    //            type uint32 {
    //              range "1 .. 18";
    //            }
    //          }
    //        }
    //      }
    //    }
    //    container member-failure-options {
    //      description "Load balancing member failure handling options";
    //      // uses apply-advanced;
    //      choice member-failure {
    //        case case_1 {
    //          container redistribute-all-traffic {
    //            presence "enable redistribute-all-traffic";
    //            description "On a member failure, redistribute traffic to ams";
    //            // uses apply-advanced;
    //            leaf enable-rejoin {
    //              description "Failed member can rejoin after recovery";
    //              type empty;
    //            }
    //          }
    //        }
    //        case case_2 {
    //          container drop-member-traffic {
    //            presence "enable drop-member-traffic";
    //            description "On a member failure, drop its traffic";
    //            // uses apply-advanced;
    //            leaf rejoin-timeout {
    //              description "Wait time(in seconds) for failed member to rejoin";
    //              default "120";
    //              type union {
    //                type string {
    //                  pattern "<.*>|$.*";
    //                }
    //                type uint32 {
    //                  range "0 .. 1000";
    //                }
    //              }
    //            }
    //            leaf enable-rejoin {
    //              description "Failed member can join after recovery";
    //              type empty;
    //            }
    //          }
    //        }
    //      }
    //    }
    //    leaf no-bundle-flap {
    //      description "No bundle flap on member addition - recommended only with IPSec services";
    //      type empty;
    //    }
    //    container high-availability-options {
    //      description "High Availability options for Load-balancing";
    //      // uses apply-advanced;
    //      choice ha-type {
    //        case case_1 {
    //          container many-to-one {
    //            description "N:1 High Availability model";
    //            // uses apply-advanced;
    //            leaf preferred-backup {
    //              description "Preferred backup Interface name";
    //              type union {
    //                type jt:interface-device;
    //                type string {
    //                  pattern "<.*>|$.*";
    //                }
    //              }
    //            }
    //          }
    //        }
    //        case case_2 {
    //          container one-to-one {
    //            description "1:1 High Availability model";
    //            // uses apply-advanced;
    //            list redundancy-group {
    //              key name;
    //              ordered-by user;
    //              description "Group number for linking HA member for intra-chassis";
    //              leaf name {
    //                description "Value for HA Redundancy-group";
    //                type union {
    //                  type string {
    //                    pattern "<.*>|$.*";
    //                  }
    //                  type uint32 {
    //                    range "1 .. 18";
    //                  }
    //                }
    //              }
    //              leaf preferred-backup {
    //                description "Preferred backup Interface name for Redundancy group";
    //                type union {
    //                  type jt:interface-device;
    //                  type string {
    //                    pattern "<.*>|$.*";
    //                  }
    //                }
    //              }
    //            }
    //            leaf preferred-backup {
    //              description "Preferred backup Interface name";
    //              type union {
    //                type jt:interface-device;
    //                type string {
    //                  pattern "<.*>|$.*";
    //                }
    //              }
    //            }
    //          }
    //        }
    //      }
    //    }
    //  }
    //  container aggregated-inline-services-options {
    //    description "Aggregated Inline Service interface specific options";
    //    // uses apply-advanced;
    //    leaf primary-interface {
    //      description "Specify the primary interface";
    //      type union {
    //        type jt:interface-device;
    //        type string {
    //          pattern "<.*>|$.*";
    //        }
    //      }
    //    }
    //    leaf secondary-interface {
    //      description "Specify the secondary interface";
    //      type union {
    //        type jt:interface-device;
    //        type string {
    //          pattern "<.*>|$.*";
    //        }
    //      }
    //    }
    //  }
    //  container anchoring-options {
    //    description "Groups anchoring PFEs or FPCs together.";
    //    // uses apply-advanced;
    //    leaf apfe-group-set {
    //      description "Ties up different anchoring groups to share similar fate";
    //      type string {
    //        length "1 .. 32";
    //      }
    //    }
    //    list primary-list {
    //      key name;
    //      description "Primary anchoring PFE name.";
    //      leaf name {
    //        description "Anchoring PFE name.";
    //        type string {
    //        }
    //      }
    //      // uses apply-advanced;
    //    }
    //    container secondary {
    //      presence "enable secondary";
    //      description "Secondary anchoring PFE name.";
    //      // uses apply-advanced;
    //      leaf anchoring-device-name {
    //        description "Anchoring PFE name.";
    //        type string {
    //        }
    //      }
    //    }
    //    choice mode {
    //      case case_1 {
    //        leaf warm-standby {
    //          description "Delayed failover to secondary when primary fails";
    //          type empty;
    //        }
    //      }
    //    }
    //  }
    //  container lsq-failure-options {
    //    description "Link services queuing failure options";
    //    // uses apply-advanced;
    //    list trigger-link-failure {
    //      key name;
    //      ordered-by user;
    //      description "Link on which to trigger failure";
    //      leaf name {
    //        description "Interface name";
    //        type union {
    //          type jt:interface-device;
    //          type string {
    //            pattern "<.*>|$.*";
    //          }
    //        }
    //      }
    //      // uses apply-advanced;
    //    }
    //    choice no-termination-request-choice {
    //      leaf no-termination-request {
    //        description "Do not send PPP termination requests";
    //        type empty;
    //      }
    //      leaf no-no-termination-request {
    //        description "Don't do not send PPP termination requests";
    //        type empty;
    //      }
    //    }
    //  }
    //  container redundancy-group {
    //    description "Redundancy group configuration";
    //    // uses apply-advanced;
    //    list member-interface {
    //      key name;
    //      description "Member interface for the redundancy group";
    //      leaf name {
    //        description "Interface name of member";
    //        type union {
    //          type jt:interface-device;
    //          type string {
    //            pattern "<.*>|$.*";
    //          }
    //        }
    //      }
    //      // uses apply-advanced;
    //      choice redundancy {
    //        case case_1 {
    //          leaf active {
    //            description "Active interface";
    //            type empty;
    //          }
    //        }
    //        case case_2 {
    //          leaf backup {
    //            description "Backup interface";
    //            type empty;
    //          }
    //        }
    //      }
    //    }
    //    leaf maximum-links {
    //      type union {
    //        type string {
    //          pattern "<.*>|$.*";
    //        }
    //        type uint32 {
    //          range "2 .. 32";
    //        }
    //      }
    //    }
    //  }
    //  container services-options {
    //    description "Services interface-specific options";
    //    // uses apply-advanced;
    //    container syslog {
    //      description "Define system log parameters";
    //      uses log-object;
    //    }
    //    container jflow-log {
    //      description "Define Jflow-log parameters.";
    //      // uses apply-advanced;
    //      leaf message-rate-limit {
    //        description "Maximum jflow-log NAT error events allowed per second from this interface";
    //        units "messages per second";
    //        type union {
    //          type string {
    //            pattern "<.*>|$.*";
    //          }
    //          type uint32 {
    //            range "1 .. 2147483647";
    //          }
    //        }
    //      }
    //    }
    //    container deterministic-nat-configuration-log-interval {
    //      presence "enable deterministic-nat-configuration-log-interval";
    //      description "Define Deterministic NAT parameters";
    //      // uses apply-advanced;
    //      leaf interval {
    //        description "Interval in which deterministic NAT logs are generated";
    //        units "seconds";
    //        type union {
    //          type string {
    //            pattern "<.*>|$.*";
    //          }
    //          type uint32 {
    //            range "1800 .. 86400";
    //          }
    //        }
    //      }
    //    }
    //    leaf open-timeout {
    //      description "Timeout period for TCP session establishment";
    //      units "seconds";
    //      type union {
    //        type string {
    //          pattern "<.*>|$.*";
    //        }
    //        type uint32 {
    //          range "4 .. 300";
    //        }
    //      }
    //    }
    //    leaf close-timeout {
    //      description "Timeout period for TCP session tear-down";
    //      units "seconds";
    //      type union {
    //        type string {
    //          pattern "<.*>|$.*";
    //        }
    //        type uint32 {
    //          range "2 .. 300";
    //        }
    //      }
    //    }
    //    leaf inactivity-timeout {
    //      description "Inactivity timeout period for established sessions (4..86400)";
    //      units "seconds";
    //      type union {
    //        type uint32;
    //        type string {
    //          pattern "<.*>|$.*";
    //        }
    //      }
    //    }
    //    leaf inactivity-tcp-timeout {
    //      description "Inactivity timeout period for TCP established sessions";
    //      units "seconds";
    //      type union {
    //        type string {
    //          pattern "<.*>|$.*";
    //        }
    //        type uint32 {
    //          range "4 .. 86400";
    //        }
    //      }
    //    }
    //    leaf inactivity-asymm-tcp-timeout {
    //      description "Inactivity timeout period for asymmetric TCP established sessions";
    //      units "seconds";
    //      type union {
    //        type string {
    //          pattern "<.*>|$.*";
    //        }
    //        type uint32 {
    //          range "4 .. 86400";
    //        }
    //      }
    //    }
    //    leaf inactivity-non-tcp-timeout {
    //      description "Inactivity timeout period for non-TCP established sessions";
    //      units "seconds";
    //      type union {
    //        type string {
    //          pattern "<.*>|$.*";
    //        }
    //        type uint32 {
    //          range "4 .. 86400";
    //        }
    //      }
    //    }
    //    leaf session-timeout {
    //      description "Session timeout period for established sessions";
    //      units "seconds";
    //      type union {
    //        type string {
    //          pattern "<.*>|$.*";
    //        }
    //        type uint32 {
    //          range "4 .. 86400";
    //        }
    //      }
    //    }
    //    leaf disable-global-timeout-override {
    //      description "Disallow overriding  global inactivity or session timeout";
    //      type empty;
    //    }
    //    leaf tcp-tickles {
    //      description "Number of TCP keep-alive packets to be sent for bi-directional TCP flows";
    //      default "4";
    //      type union {
    //        type string {
    //          pattern "<.*>|$.*";
    //        }
    //        type uint8 {
    //          range "0 .. 30";
    //        }
    //      }
    //    }
    //    container trio-flow-offload {
    //      presence "enable trio-flow-offload";
    //      description "Allow PIC to offload flows to Trio-based PFE";
    //      // uses apply-advanced;
    //      leaf minimum-bytes {
    //        description "Attempt flow offload after minimum bytes are seen on the flow";
    //        type union {
    //          type uint32;
    //          type string {
    //            pattern "<.*>|$.*";
    //          }
    //        }
    //      }
    //    }
    //    leaf fragment-limit {
    //      description "Maximum number of fragments allowed for a packet";
    //      default "64";
    //      type union {
    //        type string {
    //          pattern "<.*>|$.*";
    //        }
    //        type uint8 {
    //          range "1 .. 250";
    //        }
    //      }
    //    }
    //    leaf reassembly-timeout {
    //      description "Re-assembly timeout (seconds) for fragments of a packet";
    //      default "4";
    //      units "seconds";
    //      type union {
    //        type string {
    //          pattern "<.*>|$.*";
    //        }
    //        type uint8 {
    //          range "1 .. 60";
    //        }
    //      }
    //    }
    //    leaf cgn-pic {
    //      description "PIC will be used for Carrier Grade NAT configuration only";
    //      type empty;
    //    }
    //    leaf pba-interim-logging-interval {
    //      description "Interim logging interval in seconds";
    //      default "0";
    //      units "seconds";
    //      type union {
    //        type string {
    //          pattern "<.*>|$.*";
    //        }
    //        type uint32 {
    //          range "0 .. 86400";
    //        }
    //      }
    //    }
    //    container session-limit {
    //      presence "enable session-limit";
    //      description "Session limit";
    //      // uses apply-advanced;
    //      leaf maximum {
    //        description "Maximum number of sessions allowed simultaneously";
    //        type string;
    //      }
    //      leaf rate {
    //        description "Maximum number of new sessions allowed per second";
    //        type string;
    //      }
    //      leaf cpu-load-threshold {
    //        description "CPU limit in percentage for auto-tuning of session rate";
    //        units "percent";
    //        type union {
    //          type string {
    //            pattern "<.*>|$.*";
    //          }
    //          type uint8 {
    //            range "1 .. 100";
    //          }
    //        }
    //      }
    //    }
    //    leaf enable-subscriber-analysis {
    //      description "Enable subscriber analysis on the interface";
    //      type empty;
    //    }
    //    leaf disable-subscriber-analysis {
    //      description "Disable subscriber analysis on the interface";
    //      type empty;
    //    }
    //    leaf disable-usp-tracing {
    //      description "Disable usp tracing on this pic";
    //      type empty;
    //    }
    //    leaf disable-drop-flows {
    //      description "Disable drop flows on this pic";
    //      type empty;
    //    }
    //    container ignore-errors {
    //      presence "enable ignore-errors";
    //      description "Ignore anomalies or errors";
    //      leaf tcp {
    //        description "TCP protocol errors";
    //        type empty;
    //      }
    //      leaf alg {
    //        description "ALG anomalies or errors";
    //        type empty;
    //      }
    //    }
    //    container capture {
    //      description "Packet capture for SFW and NAT on the Services PIC";
    //      // uses apply-advanced;
    //      leaf capture-size {
    //        description "The number of packets to store";
    //        type union {
    //          type string {
    //            pattern "<.*>|$.*";
    //          }
    //          type uint32 {
    //            range "1 .. 344000";
    //          }
    //        }
    //      }
    //      leaf pkt-size {
    //        description "Number of bytes to be saved from each packet";
    //        type union {
    //          type string {
    //            pattern "<.*>|$.*";
    //          }
    //          type uint16 {
    //            range "64 .. 15000";
    //          }
    //        }
    //      }
    //      leaf logs-per-packet {
    //        description "The number of trace messages stored for each packet";
    //        type union {
    //          type string {
    //            pattern "<.*>|$.*";
    //          }
    //          type uint16 {
    //            range "0 .. 500";
    //          }
    //        }
    //      }
    //      leaf max-log-line-size {
    //        description "The maximum length of a stored trace message";
    //        type union {
    //          type uint8;
    //          type string {
    //            pattern "<.*>|$.*";
    //          }
    //        }
    //      }
    //      container filter {
    //        presence "enable filter";
    //        description "Filtering options for the packet capture";
    //        // uses apply-advanced;
    //        container source-ip {
    //          description "Filter based on source-ip (and wildcard)";
    //          leaf ip {
    //            description "Source IP";
    //            type jt:ipaddr;
    //          }
    //          leaf wildcard {
    //            description "Source IP wildcard";
    //            type jt:ipaddr;
    //          }
    //        }
    //        container dest-ip {
    //          description "Filter based on dest-ip (and wildcard)";
    //          leaf ip {
    //            description "Dest IP";
    //            type jt:ipaddr;
    //          }
    //          leaf wildcard {
    //            description "Dest IP wildcard";
    //            type jt:ipaddr;
    //          }
    //        }
    //        container sw-sip {
    //          description "Filter based on source softwire ip (and wildcard)";
    //          leaf ip {
    //            description "Source softwire IP";
    //            type jt:ipv6addr;
    //          }
    //          leaf wildcard {
    //            description "Source IP wildcard";
    //            type jt:ipv6addr;
    //          }
    //        }
    //        container sw-dip {
    //          description "Filter based on destination softwire ip (and wildcard)";
    //          leaf ip {
    //            description "Destination softwire IP";
    //            type jt:ipaddr;
    //          }
    //          leaf wildcard {
    //            description "Destination IP wildcard";
    //            type jt:ipaddr;
    //          }
    //        }
    //        container sport-range {
    //          description "Filter based on source port";
    //          leaf low {
    //            description "Source port range start";
    //            type union {
    //              type uint16;
    //              type string {
    //                pattern "<.*>|$.*";
    //              }
    //            }
    //          }
    //          leaf high {
    //            description "Source port range end";
    //            type union {
    //              type uint16;
    //              type string {
    //                pattern "<.*>|$.*";
    //              }
    //            }
    //          }
    //        }
    //        container dport-range {
    //          description "Filter based on destination port";
    //          leaf low {
    //            description "Destination port range start";
    //            type union {
    //              type uint16;
    //              type string {
    //                pattern "<.*>|$.*";
    //              }
    //            }
    //          }
    //          leaf high {
    //            description "Destination port range end";
    //            type union {
    //              type uint16;
    //              type string {
    //                pattern "<.*>|$.*";
    //              }
    //            }
    //          }
    //        }
    //        leaf proto {
    //          description "Filter based on L4 protocol";
    //          type enumeration {
    //            enum "icmp" {
    //            }
    //            enum "tcp" {
    //            }
    //            enum "udp" {
    //            }
    //          }
    //        }
    //      }
    //    }
    //    container flow {
    //      description "Define flow parameters";
    //      // uses apply-advanced;
    //      container traceoptions {
    //        description "Trace options for flow services";
    //      }
    //    }
    //    leaf fpc-pic-information {
    //      description "Include FPC and PIC slot number in the syslogs";
    //      type empty;
    //    }
    //    leaf utc-timestamp {
    //      description "Use UTC time for security log timestamps";
    //      type empty;
    //    }
    //    leaf syslog-local-system-timestamp {
    //      description "Use local system time for services syslog timestamp";
    //      type empty;
    //    }
    //  }
    //  container t3-options {
    //    description "T3 interface-specific options";
    //    // uses apply-advanced;
    //    leaf loopback {
    //      description "Loopback mode";
    //      type enumeration {
    //        enum "local" {
    //          description "Local loopback";
    //        }
    //        enum "remote" {
    //          description "Remote loopback";
    //        }
    //        enum "payload" {
    //          description "Payload loopback";
    //        }
    //      }
    //    }
    //    choice long-buildout-choice {
    //      leaf long-buildout {
    //        description "Set hardware to drive line longer than 255 feet";
    //        type empty;
    //      }
    //      leaf no-long-buildout {
    //        description "Don't set hardware to drive line longer than 255 feet";
    //        type empty;
    //      }
    //    }
    //    choice loop-timing-choice {
    //      leaf loop-timing {
    //        description "Set loop timing for T3";
    //        type empty;
    //      }
    //      leaf no-loop-timing {
    //        description "Don't set loop timing for T3";
    //        type empty;
    //      }
    //    }
    //    container compatibility-mode {
    //      description "Set CSU compatibility mode";
    //      choice vendor {
    //        case case_1 {
    //          container larscom {
    //            presence "enable larscom";
    //            description "Compatible with Larscom CSU";
    //            leaf subrate {
    //              description "Set subrate value";
    //              type union {
    //                type string {
    //                  pattern "<.*>|$.*";
    //                }
    //                type uint32 {
    //                  range "1 .. 14";
    //                }
    //              }
    //            }
    //          }
    //        }
    //        case case_2 {
    //          container verilink {
    //            presence "enable verilink";
    //            description "Compatible with Verilink CSU (not on 2/4-port T3 PIC)";
    //            leaf subrate {
    //              description "Set subrate value";
    //              type union {
    //                type string {
    //                  pattern "<.*>|$.*";
    //                }
    //                type uint32 {
    //                  range "1 .. 28";
    //                }
    //              }
    //            }
    //          }
    //        }
    //        case case_3 {
    //          container adtran {
    //            presence "enable adtran";
    //            description "Compatible with Adtran CSU (not on 2/4-port T3 PIC)";
    //            leaf subrate {
    //              description "Set subrate value";
    //              type union {
    //                type string {
    //                  pattern "<.*>|$.*";
    //                }
    //                type uint32 {
    //                  range "1 .. 588";
    //                }
    //              }
    //            }
    //          }
    //        }
    //        case case_4 {
    //          container kentrox {
    //            presence "enable kentrox";
    //            description "Compatible with Kentrox CSU";
    //            leaf subrate {
    //              description "Set subrate value (not on 2/4-port T3 PIC)";
    //              type union {
    //                type string {
    //                  pattern "<.*>|$.*";
    //                }
    //                type uint32 {
    //                  range "1 .. 69";
    //                }
    //              }
    //            }
    //          }
    //        }
    //        case case_5 {
    //          container digital-link {
    //            presence "enable digital-link";
    //            description "Compatible with Digital Link CSU";
    //            leaf subrate {
    //              description "Set subrate value";
    //              type enumeration {
    //                enum "301Kb" {
    //                  description "301 Kbps";
    //                }
    //                enum "601Kb" {
    //                  description "601 Kbps";
    //                }
    //                enum "902Kb" {
    //                  description "902 Kbps";
    //                }
    //                enum "1.2Mb" {
    //                  description "1.2 Mbps";
    //                }
    //                enum "1.5Mb" {
    //                  description "1.5 Mbps";
    //                }
    //                enum "1.8Mb" {
    //                  description "1.8 Mbps";
    //                }
    //                enum "2.1Mb" {
    //                  description "2.1 Mbps";
    //                }
    //                enum "2.4Mb" {
    //                  description "2.4 Mbps";
    //                }
    //                enum "2.7Mb" {
    //                  description "2.7 Mbps";
    //                }
    //                enum "3.0Mb" {
    //                  description "3.0 Mbps";
    //                }
    //                enum "3.3Mb" {
    //                  description "3.3 Mbps";
    //                }
    //                enum "3.6Mb" {
    //                  description "3.6 Mbps";
    //                }
    //                enum "3.9Mb" {
    //                  description "3.9 Mbps";
    //                }
    //                enum "4.2Mb" {
    //                  description "4.2 Mbps";
    //                }
    //                enum "4.5Mb" {
    //                  description "4.5 Mbps";
    //                }
    //                enum "4.8Mb" {
    //                  description "4.8 Mbps";
    //                }
    //                enum "5.1Mb" {
    //                  description "5.1 Mbps";
    //                }
    //                enum "5.4Mb" {
    //                  description "5.4 Mbps";
    //                }
    //                enum "5.7Mb" {
    //                  description "5.7 Mbps";
    //                }
    //                enum "6.0Mb" {
    //                  description "6.0 Mbps";
    //                }
    //                enum "6.3Mb" {
    //                  description "6.3 Mbps";
    //                }
    //                enum "6.6Mb" {
    //                  description "6.6 Mbps";
    //                }
    //                enum "6.9Mb" {
    //                  description "6.9 Mbps";
    //                }
    //                enum "7.2Mb" {
    //                  description "7.2 Mbps";
    //                }
    //                enum "7.5Mb" {
    //                  description "7.5 Mbps";
    //                }
    //                enum "7.8Mb" {
    //                  description "7.8 Mbps";
    //                }
    //                enum "8.1Mb" {
    //                  description "8.1 Mbps";
    //                }
    //                enum "8.4Mb" {
    //                  description "8.4 Mbps";
    //                }
    //                enum "8.7Mb" {
    //                  description "8.7 Mbps";
    //                }
    //                enum "9.0Mb" {
    //                  description "9.0 Mbps";
    //                }
    //                enum "9.3Mb" {
    //                  description "9.3 Mbps";
    //                }
    //                enum "9.6Mb" {
    //                  description "9.6 Mbps";
    //                }
    //                enum "9.9Mb" {
    //                  description "9.9 Mbps";
    //                }
    //                enum "10.2Mb" {
    //                  description "10.2 Mbps";
    //                }
    //                enum "10.5Mb" {
    //                  description "10.5 Mbps";
    //                }
    //                enum "10.8Mb" {
    //                  description "10.8 Mbps";
    //                }
    //                enum "11.1Mb" {
    //                  description "11.1 Mbps";
    //                }
    //                enum "11.4Mb" {
    //                  description "11.4 Mbps";
    //                }
    //                enum "11.7Mb" {
    //                  description "11.7 Mbps";
    //                }
    //                enum "12.0Mb" {
    //                  description "12.0 Mbps";
    //                }
    //                enum "12.3Mb" {
    //                  description "12.3 Mbps";
    //                }
    //                enum "12.6Mb" {
    //                  description "12.6 Mbps";
    //                }
    //                enum "12.9Mb" {
    //                  description "12.9 Mbps";
    //                }
    //                enum "13.2Mb" {
    //                  description "13.2 Mbps";
    //                }
    //                enum "13.5Mb" {
    //                  description "13.5 Mbps";
    //                }
    //                enum "13.8Mb" {
    //                  description "13.8 Mbps";
    //                }
    //                enum "14.1Mb" {
    //                  description "14.1 Mbps";
    //                }
    //                enum "14.4Mb" {
    //                  description "14.4 Mbps";
    //                }
    //                enum "14.7Mb" {
    //                  description "14.7 Mbps";
    //                }
    //                enum "15.0Mb" {
    //                  description "15.0 Mbps";
    //                }
    //                enum "15.3Mb" {
    //                  description "15.3 Mbps";
    //                }
    //                enum "15.6Mb" {
    //                  description "15.6 Mbps";
    //                }
    //                enum "15.9Mb" {
    //                  description "15.9 Mbps";
    //                }
    //                enum "16.2Mb" {
    //                  description "16.2 Mbps";
    //                }
    //                enum "16.5Mb" {
    //                  description "16.5 Mbps";
    //                }
    //                enum "16.8Mb" {
    //                  description "16.8 Mbps";
    //                }
    //                enum "17.1Mb" {
    //                  description "17.1 Mbps";
    //                }
    //                enum "17.4Mb" {
    //                  description "17.4 Mbps";
    //                }
    //                enum "17.7Mb" {
    //                  description "17.7 Mbps";
    //                }
    //                enum "18.0Mb" {
    //                  description "18.0 Mbps";
    //                }
    //                enum "18.3Mb" {
    //                  description "18.3 Mbps";
    //                }
    //                enum "18.6Mb" {
    //                  description "18.6 Mbps";
    //                }
    //                enum "18.9Mb" {
    //                  description "18.9 Mbps";
    //                }
    //                enum "19.2Mb" {
    //                  description "19.2 Mbps";
    //                }
    //                enum "19.5Mb" {
    //                  description "19.5 Mbps";
    //                }
    //                enum "19.8Mb" {
    //                  description "19.8 Mbps";
    //                }
    //                enum "20.1Mb" {
    //                  description "20.1 Mbps";
    //                }
    //                enum "20.5Mb" {
    //                  description "20.5 Mbps";
    //                }
    //                enum "20.8Mb" {
    //                  description "20.8 Mbps";
    //                }
    //                enum "21.1Mb" {
    //                  description "21.1 Mbps";
    //                }
    //                enum "21.4Mb" {
    //                  description "21.4 Mbps";
    //                }
    //                enum "21.7Mb" {
    //                  description "21.7 Mbps";
    //                }
    //                enum "22.0Mb" {
    //                  description "22.0 Mbps";
    //                }
    //                enum "22.3Mb" {
    //                  description "22.3 Mbps";
    //                }
    //                enum "22.6Mb" {
    //                  description "22.6 Mbps";
    //                }
    //                enum "22.9Mb" {
    //                  description "22.9 Mbps";
    //                }
    //                enum "23.2Mb" {
    //                  description "23.2 Mbps";
    //                }
    //                enum "23.5Mb" {
    //                  description "23.5 Mbps";
    //                }
    //                enum "23.8Mb" {
    //                  description "23.8 Mbps";
    //                }
    //                enum "24.1Mb" {
    //                  description "24.1 Mbps";
    //                }
    //                enum "24.4Mb" {
    //                  description "24.4 Mbps";
    //                }
    //                enum "24.7Mb" {
    //                  description "24.7 Mbps";
    //                }
    //                enum "25.0Mb" {
    //                  description "25.0 Mbps";
    //                }
    //                enum "25.3Mb" {
    //                  description "25.3 Mbps";
    //                }
    //                enum "25.6Mb" {
    //                  description "25.6 Mbps";
    //                }
    //                enum "25.9Mb" {
    //                  description "25.9 Mbps";
    //                }
    //                enum "26.2Mb" {
    //                  description "26.2 Mbps";
    //                }
    //                enum "26.5Mb" {
    //                  description "26.5 Mbps";
    //                }
    //                enum "26.8Mb" {
    //                  description "26.8 Mbps";
    //                }
    //                enum "27.1Mb" {
    //                  description "27.1 Mbps";
    //                }
    //                enum "27.4Mb" {
    //                  description "27.4 Mbps";
    //                }
    //                enum "27.7Mb" {
    //                  description "27.7 Mbps";
    //                }
    //                enum "28.0Mb" {
    //                  description "28.0 Mbps";
    //                }
    //                enum "28.3Mb" {
    //                  description "28.3 Mbps";
    //                }
    //                enum "28.6Mb" {
    //                  description "28.6 Mbps";
    //                }
    //                enum "28.9Mb" {
    //                  description "28.9 Mbps";
    //                }
    //                enum "29.2Mb" {
    //                  description "29.2 Mbps";
    //                }
    //                enum "29.5Mb" {
    //                  description "29.5 Mbps";
    //                }
    //                enum "29.8Mb" {
    //                  description "29.8 Mbps";
    //                }
    //                enum "30.1Mb" {
    //                  description "30.1 Mbps";
    //                }
    //                enum "30.4Mb" {
    //                  description "30.4 Mbps";
    //                }
    //                enum "30.7Mb" {
    //                  description "30.7 Mbps";
    //                }
    //                enum "31.0Mb" {
    //                  description "31.0 Mbps";
    //                }
    //                enum "31.3Mb" {
    //                  description "31.3 Mbps";
    //                }
    //                enum "31.6Mb" {
    //                  description "31.6 Mbps";
    //                }
    //                enum "31.9Mb" {
    //                  description "31.9 Mbps";
    //                }
    //                enum "32.2Mb" {
    //                  description "32.2 Mbps";
    //                }
    //                enum "32.5Mb" {
    //                  description "32.5 Mbps";
    //                }
    //                enum "32.8Mb" {
    //                  description "32.8 Mbps";
    //                }
    //                enum "33.1Mb" {
    //                  description "33.1 Mbps";
    //                }
    //                enum "33.4Mb" {
    //                  description "33.4 Mbps";
    //                }
    //                enum "33.7Mb" {
    //                  description "33.7 Mbps";
    //                }
    //                enum "34.0Mb" {
    //                  description "34.0 Mbps";
    //                }
    //                enum "34.3Mb" {
    //                  description "34.3 Mbps";
    //                }
    //                enum "34.6Mb" {
    //                  description "34.6 Mbps";
    //                }
    //                enum "34.9Mb" {
    //                  description "34.9 Mbps";
    //                }
    //                enum "35.2Mb" {
    //                  description "35.2 Mbps";
    //                }
    //                enum "35.5Mb" {
    //                  description "35.5 Mbps";
    //                }
    //                enum "35.8Mb" {
    //                  description "35.8 Mbps";
    //                }
    //                enum "36.1Mb" {
    //                  description "36.1 Mbps";
    //                }
    //                enum "36.4Mb" {
    //                  description "36.4 Mbps";
    //                }
    //                enum "36.7Mb" {
    //                  description "36.7 Mbps";
    //                }
    //                enum "37.0Mb" {
    //                  description "37.0 Mbps";
    //                }
    //                enum "37.3Mb" {
    //                  description "37.3 Mbps";
    //                }
    //                enum "37.6Mb" {
    //                  description "37.6 Mbps";
    //                }
    //                enum "37.9Mb" {
    //                  description "37.9 Mbps";
    //                }
    //                enum "38.2Mb" {
    //                  description "38.2 Mbps";
    //                }
    //                enum "38.5Mb" {
    //                  description "38.5 Mbps";
    //                }
    //                enum "38.8Mb" {
    //                  description "38.8 Mbps";
    //                }
    //                enum "39.1Mb" {
    //                  description "39.1 Mbps";
    //                }
    //                enum "39.4Mb" {
    //                  description "39.4 Mbps";
    //                }
    //                enum "39.7Mb" {
    //                  description "39.7 Mbps";
    //                }
    //                enum "40.0Mb" {
    //                  description "40.0 Mbps";
    //                }
    //                enum "40.3Mb" {
    //                  description "40.3 Mbps";
    //                }
    //                enum "40.6Mb" {
    //                  description "40.6 Mbps";
    //                }
    //                enum "40.9Mb" {
    //                  description "40.9 Mbps";
    //                }
    //                enum "41.2Mb" {
    //                  description "41.2 Mbps";
    //                }
    //                enum "41.5Mb" {
    //                  description "41.5 Mbps";
    //                }
    //                enum "41.8Mb" {
    //                  description "41.8 Mbps";
    //                }
    //                enum "42.1Mb" {
    //                  description "42.1 Mbps";
    //                }
    //                enum "42.4Mb" {
    //                  description "42.4 Mbps";
    //                }
    //                enum "42.7Mb" {
    //                  description "42.7 Mbps";
    //                }
    //                enum "43.0Mb" {
    //                  description "43.0 Mbps";
    //                }
    //                enum "43.3Mb" {
    //                  description "43.3 Mbps";
    //                }
    //                enum "43.6Mb" {
    //                  description "43.6 Mbps";
    //                }
    //                enum "43.9Mb" {
    //                  description "43.9 Mbps";
    //                }
    //                enum "44.2Mb" {
    //                  description "44.2 Mbps";
    //                }
    //              }
    //            }
    //          }
    //        }
    //      }
    //    }
    //    choice payload-scrambler-choice {
    //      leaf payload-scrambler {
    //        description "Enable payload scrambling";
    //        type empty;
    //      }
    //      leaf no-payload-scrambler {
    //        description "Don't enable payload scrambling";
    //        type empty;
    //      }
    //    }
    //    choice cbit-parity-choice {
    //      leaf cbit-parity {
    //        description "Enable C-bit parity mode";
    //        type empty;
    //      }
    //      leaf no-cbit-parity {
    //        description "Don't enable C-bit parity mode";
    //        type empty;
    //      }
    //    }
    //    leaf fcs {
    //      description "Frame checksum";
    //      type enumeration {
    //        enum "32" {
    //          description "32-bit mode";
    //        }
    //        enum "16" {
    //          description "16-bit mode";
    //        }
    //      }
    //    }
    //    leaf idle-cycle-flag {
    //      description "Value to transmit in idle cycles";
    //      type enumeration {
    //        enum "flags" {
    //          description "Transmit 0x7E in idle cycles";
    //        }
    //        enum "ones" {
    //          description "Transmit 0xFF (all ones) in idle cycles";
    //        }
    //      }
    //    }
    //    leaf start-end-flag {
    //      description "Set start/end flags on transmission";
    //      type enumeration {
    //        enum "shared" {
    //          description "Share start/end flags on transmit";
    //        }
    //        enum "filler" {
    //          description "Send two idle cycles between start/end flags";
    //        }
    //      }
    //    }
    //    choice feac-loop-respond-choice {
    //      leaf feac-loop-respond {
    //        description "Respond to FEAC loop requests";
    //        type empty;
    //      }
    //      leaf no-feac-loop-respond {
    //        description "Don't respond to FEAC loop requests";
    //        type empty;
    //      }
    //    }
    //    leaf bert-algorithm {
    //      description "Set BERT algorithm";
    //      type enumeration {
    //        enum "pseudo-2e3" {
    //          description "Pattern is 2^3 - 1";
    //        }
    //        enum "pseudo-2e4" {
    //          description "Pattern is 2^4 - 1";
    //        }
    //        enum "pseudo-2e5" {
    //          description "Pattern is 2^5 - 1";
    //        }
    //        enum "pseudo-2e6" {
    //          description "Pattern is 2^6 - 1";
    //        }
    //        enum "pseudo-2e7" {
    //          description "Pattern is 2^7 - 1";
    //        }
    //        enum "pseudo-2e9-o153" {
    //          description "Pattern is 2^9 - 1 (per O.153 standard)";
    //        }
    //        enum "pseudo-2e10" {
    //          description "Pattern is 2^10 - 1";
    //        }
    //        enum "pseudo-2e11-o152" {
    //          description "Pattern is 2^11 -1 (per O.152 standard)";
    //        }
    //        enum "pseudo-2e15-o151" {
    //          description "Pattern is 2^15 - 1 (per O.151 standard)";
    //        }
    //        enum "pseudo-2e17" {
    //          description "Pattern is 2^17 - 1";
    //        }
    //        enum "pseudo-2e18" {
    //          description "Pattern is 2^18 - 1";
    //        }
    //        enum "pseudo-2e20-o153" {
    //          description "Pattern is 2^20 - 1 (per O.153 standard)";
    //        }
    //        enum "pseudo-2e20-o151" {
    //          description "Pattern is 2^20 - 1 (per O.151 standard)";
    //        }
    //        enum "pseudo-2e21" {
    //          description "Pattern is 2^21 - 1";
    //        }
    //        enum "pseudo-2e22" {
    //          description "Pattern is 2^22 - 1";
    //        }
    //        enum "pseudo-2e23-o151" {
    //          description "Pattern is 2^23 (per O.151 standard)";
    //        }
    //        enum "pseudo-2e25" {
    //          description "Pattern is 2^25 - 1";
    //        }
    //        enum "pseudo-2e28" {
    //          description "Pattern is 2^28 - 1";
    //        }
    //        enum "pseudo-2e29" {
    //          description "Pattern is 2^29 - 1";
    //        }
    //        enum "pseudo-2e31" {
    //          description "Pattern is 2^31 - 1";
    //        }
    //        enum "pseudo-2e32" {
    //          description "Pattern is 2^32 - 1";
    //        }
    //        enum "all-ones-repeating" {
    //          description "Repeating one bits";
    //        }
    //        enum "all-zeros-repeating" {
    //          description "Repeating zero bits";
    //        }
    //        enum "alternating-ones-zeros" {
    //          description "Alternating ones and zeros";
    //        }
    //        enum "alternating-double-ones-zeros" {
    //          description "Alternating pairs of ones and zeros";
    //        }
    //        enum "repeating-3-in-24" {
    //          description "3 bits in 24 are set";
    //        }
    //        enum "repeating-1-in-8" {
    //          description "1 bit in 8 is set";
    //        }
    //        enum "repeating-1-in-4" {
    //          description "1 bit in 4 is set";
    //        }
    //      }
    //    }
    //    leaf bert-error-rate {
    //      description "Bit error rate (10^-n for n > 0, and zero for n = 0)";
    //      type union {
    //        type string {
    //          pattern "<.*>|$.*";
    //        }
    //        type uint32 {
    //          range "0 .. 7";
    //        }
    //      }
    //    }
    //    leaf bert-period {
    //      description "Length of BERT test";
    //      units "seconds";
    //      type union {
    //        type string {
    //          pattern "<.*>|$.*";
    //        }
    //        type uint32 {
    //          range "1 .. 240";
    //        }
    //      }
    //    }
    //    leaf buildout {
    //      description "Line buildout";
    //      units "feet";
    //      type union {
    //        type string {
    //          pattern "<.*>|$.*";
    //        }
    //        type uint32 {
    //          range "0 .. 450";
    //        }
    //      }
    //    }
    //    leaf atm-encapsulation {
    //      description "DS-3 interface encapsulation";
    //      type enumeration {
    //        enum "plcp" {
    //          description "PLCP encapsulation";
    //        }
    //        enum "direct" {
    //          description "ATM direct mapping";
    //        }
    //      }
    //    }
    //  }
    //  container e3-options {
    //    description "E3 interface-specific options";
    //    // uses apply-advanced;
    //    leaf loopback {
    //      description "Loopback mode";
    //      type enumeration {
    //        enum "local" {
    //          description "Local loopback";
    //        }
    //        enum "remote" {
    //          description "Remote loopback";
    //        }
    //      }
    //    }
    //    choice unframed-choice {
    //      leaf unframed {
    //        description "Enable unframed mode";
    //        type empty;
    //      }
    //      leaf no-unframed {
    //        description "Don't enable unframed mode";
    //        type empty;
    //      }
    //    }
    //    container compatibility-mode {
    //      description "Set CSU compatibility mode";
    //      choice vendor {
    //        case case_1 {
    //          leaf larscom {
    //            description "Compatible with Larscom CSU (only non IQ E3 interfaces)";
    //            type empty;
    //          }
    //        }
    //        case case_2 {
    //          container digital-link {
    //            presence "enable digital-link";
    //            description "Compatible with Digital Link CSU";
    //            leaf subrate {
    //              description "Set subrate value";
    //              type enumeration {
    //                enum "358Kb" {
    //                  description "358 Kbps";
    //                }
    //                enum "716Kb" {
    //                  description "716 Kbps";
    //                }
    //                enum "1.1Mb" {
    //                  description "1.1 Mbps";
    //                }
    //                enum "1.4Mb" {
    //                  description "1.4 Mbps";
    //                }
    //                enum "1.8Mb" {
    //                  description "1.8 Mbps";
    //                }
    //                enum "2.1Mb" {
    //                  description "2.1 Mbps";
    //                }
    //                enum "2.5Mb" {
    //                  description "2.5 Mbps";
    //                }
    //                enum "2.9Mb" {
    //                  description "2.9 Mbps";
    //                }
    //                enum "3.2Mb" {
    //                  description "3.2 Mbps";
    //                }
    //                enum "3.6Mb" {
    //                  description "3.6 Mbps";
    //                }
    //                enum "3.9Mb" {
    //                  description "3.9 Mbps";
    //                }
    //                enum "4.3Mb" {
    //                  description "4.3 Mbps";
    //                }
    //                enum "4.7Mb" {
    //                  description "4.7 Mbps";
    //                }
    //                enum "5.0Mb" {
    //                  description "5.0 Mbps";
    //                }
    //                enum "5.4Mb" {
    //                  description "5.4 Mbps";
    //                }
    //                enum "5.7Mb" {
    //                  description "5.7 Mbps";
    //                }
    //                enum "6.1Mb" {
    //                  description "6.1 Mbps";
    //                }
    //                enum "6.4Mb" {
    //                  description "6.4 Mbps";
    //                }
    //                enum "6.8Mb" {
    //                  description "6.8 Mbps";
    //                }
    //                enum "7.2Mb" {
    //                  description "7.2 Mbps";
    //                }
    //                enum "7.5Mb" {
    //                  description "7.5 Mbps";
    //                }
    //                enum "7.9Mb" {
    //                  description "7.9 Mbps";
    //                }
    //                enum "8.2Mb" {
    //                  description "8.2 Mbps";
    //                }
    //                enum "8.6Mb" {
    //                  description "8.6 Mbps";
    //                }
    //                enum "9.0Mb" {
    //                  description "9.0 Mbps";
    //                }
    //                enum "9.3Mb" {
    //                  description "9.3 Mbps";
    //                }
    //                enum "9.7Mb" {
    //                  description "9.7 Mbps";
    //                }
    //                enum "10.0Mb" {
    //                  description "10.0 Mbps";
    //                }
    //                enum "10.4Mb" {
    //                  description "10.4 Mbps";
    //                }
    //                enum "10.7Mb" {
    //                  description "10.7 Mbps";
    //                }
    //                enum "11.1Mb" {
    //                  description "11.1 Mbps";
    //                }
    //                enum "11.5Mb" {
    //                  description "11.5 Mbps";
    //                }
    //                enum "11.8Mb" {
    //                  description "11.8 Mbps";
    //                }
    //                enum "12.2Mb" {
    //                  description "12.2 Mbps";
    //                }
    //                enum "12.5Mb" {
    //                  description "12.5 Mbps";
    //                }
    //                enum "12.9Mb" {
    //                  description "12.9 Mbps";
    //                }
    //                enum "13.2Mb" {
    //                  description "13.2 Mbps";
    //                }
    //                enum "13.6Mb" {
    //                  description "13.6 Mbps";
    //                }
    //                enum "14.0Mb" {
    //                  description "14.0 Mbps";
    //                }
    //                enum "14.3Mb" {
    //                  description "14.3 Mbps";
    //                }
    //                enum "14.7Mb" {
    //                  description "14.7 Mbps";
    //                }
    //                enum "15.0Mb" {
    //                  description "15.0 Mbps";
    //                }
    //                enum "15.4Mb" {
    //                  description "15.4 Mbps";
    //                }
    //                enum "15.8Mb" {
    //                  description "15.8 Mbps";
    //                }
    //                enum "16.1Mb" {
    //                  description "16.1 Mbps";
    //                }
    //                enum "16.5Mb" {
    //                  description "16.5 Mbps";
    //                }
    //                enum "16.8Mb" {
    //                  description "16.8 Mbps";
    //                }
    //                enum "17.2Mb" {
    //                  description "17.2 Mbps";
    //                }
    //                enum "17.5Mb" {
    //                  description "17.5 Mbps";
    //                }
    //                enum "17.9Mb" {
    //                  description "17.9 Mbps";
    //                }
    //                enum "18.3Mb" {
    //                  description "18.3 Mbps";
    //                }
    //                enum "18.6Mb" {
    //                  description "18.6 Mbps";
    //                }
    //                enum "19.0Mb" {
    //                  description "19.0 Mbps";
    //                }
    //                enum "19.3Mb" {
    //                  description "19.3 Mbps";
    //                }
    //                enum "19.7Mb" {
    //                  description "19.7 Mbps";
    //                }
    //                enum "20.0Mb" {
    //                  description "20.0 Mbps";
    //                }
    //                enum "20.4Mb" {
    //                  description "20.4 Mbps";
    //                }
    //                enum "20.8Mb" {
    //                  description "20.8 Mbps";
    //                }
    //                enum "21.1Mb" {
    //                  description "21.1 Mbps";
    //                }
    //                enum "21.5Mb" {
    //                  description "21.5 Mbps";
    //                }
    //                enum "21.8Mb" {
    //                  description "21.8 Mbps";
    //                }
    //                enum "22.2Mb" {
    //                  description "22.2 Mbps";
    //                }
    //                enum "22.6Mb" {
    //                  description "22.6 Mbps";
    //                }
    //                enum "22.9Mb" {
    //                  description "22.9 Mbps";
    //                }
    //                enum "23.3Mb" {
    //                  description "23.3 Mbps";
    //                }
    //                enum "23.6Mb" {
    //                  description "23.6 Mbps";
    //                }
    //                enum "24.0Mb" {
    //                  description "24.0 Mbps";
    //                }
    //                enum "24.3Mb" {
    //                  description "24.3 Mbps";
    //                }
    //                enum "24.7Mb" {
    //                  description "24.7 Mbps";
    //                }
    //                enum "25.1Mb" {
    //                  description "25.1 Mbps";
    //                }
    //                enum "25.4Mb" {
    //                  description "25.4 Mbps";
    //                }
    //                enum "25.8Mb" {
    //                  description "25.8 Mbps";
    //                }
    //                enum "26.1Mb" {
    //                  description "26.1 Mbps";
    //                }
    //                enum "26.5Mb" {
    //                  description "26.5 Mbps";
    //                }
    //                enum "26.9Mb" {
    //                  description "26.9 Mbps";
    //                }
    //                enum "27.2Mb" {
    //                  description "27.2 Mbps";
    //                }
    //                enum "27.6Mb" {
    //                  description "27.6 Mbps";
    //                }
    //                enum "27.9Mb" {
    //                  description "27.9 Mbps";
    //                }
    //                enum "28.3Mb" {
    //                  description "28.3 Mbps";
    //                }
    //                enum "28.6Mb" {
    //                  description "28.6 Mbps";
    //                }
    //                enum "29.0Mb" {
    //                  description "29.0 Mbps";
    //                }
    //                enum "29.4Mb" {
    //                  description "29.4 Mbps";
    //                }
    //                enum "29.7Mb" {
    //                  description "29.7 Mbps";
    //                }
    //                enum "30.1Mb" {
    //                  description "30.1 Mbps";
    //                }
    //                enum "30.4Mb" {
    //                  description "30.4 Mbps";
    //                }
    //                enum "30.8Mb" {
    //                  description "30.8 Mbps";
    //                }
    //                enum "31.1Mb" {
    //                  description "31.1 Mbps";
    //                }
    //                enum "31.5Mb" {
    //                  description "31.5 Mbps";
    //                }
    //                enum "31.9Mb" {
    //                  description "31.9 Mbps";
    //                }
    //                enum "32.2Mb" {
    //                  description "32.2 Mbps";
    //                }
    //                enum "32.6Mb" {
    //                  description "32.6 Mbps";
    //                }
    //                enum "32.9Mb" {
    //                  description "32.9 Mbps";
    //                }
    //                enum "33.3Mb" {
    //                  description "33.3 Mbps";
    //                }
    //                enum "33.7Mb" {
    //                  description "33.7 Mbps";
    //                }
    //                enum "34.0Mb" {
    //                  description "34.0 Mbps";
    //                }
    //              }
    //            }
    //          }
    //        }
    //        case case_3 {
    //          container kentrox {
    //            presence "enable kentrox";
    //            description "Compatible with Kentrox CSU";
    //            leaf subrate {
    //              description "Set subrate value (only for E3 IQ interfaces)";
    //              type union {
    //                type string {
    //                  pattern "<.*>|$.*";
    //                }
    //                type uint32 {
    //                  range "1 .. 48";
    //                }
    //              }
    //            }
    //          }
    //        }
    //      }
    //    }
    //    choice payload-scrambler-choice {
    //      leaf payload-scrambler {
    //        description "Enable payload scrambling";
    //        type empty;
    //      }
    //      leaf no-payload-scrambler {
    //        description "Don't enable payload scrambling";
    //        type empty;
    //      }
    //    }
    //    leaf fcs {
    //      description "Frame checksum";
    //      type enumeration {
    //        enum "32" {
    //          description "32-bit mode";
    //        }
    //        enum "16" {
    //          description "16-bit mode";
    //        }
    //      }
    //    }
    //    leaf idle-cycle-flag {
    //      description "Value to transmit in idle cycles";
    //      type enumeration {
    //        enum "flags" {
    //          description "Transmit 0x7E in idle cycles";
    //        }
    //        enum "ones" {
    //          description "Transmit 0xFF (all ones) in idle cycles";
    //        }
    //      }
    //    }
    //    leaf invert-data {
    //      description "Invert data";
    //      type empty;
    //    }
    //    leaf start-end-flag {
    //      description "Set start/end flags on transmission";
    //      type enumeration {
    //        enum "shared" {
    //          description "Share start/end flags on transmit";
    //        }
    //        enum "filler" {
    //          description "Send two idle cycles between start/end flags";
    //        }
    //      }
    //    }
    //    leaf bert-algorithm {
    //      description "Set BERT algorithm";
    //      type enumeration {
    //        enum "pseudo-2e3" {
    //          description "Pattern is 2^3 - 1";
    //        }
    //        enum "pseudo-2e4" {
    //          description "Pattern is 2^4 - 1";
    //        }
    //        enum "pseudo-2e5" {
    //          description "Pattern is 2^5 - 1";
    //        }
    //        enum "pseudo-2e6" {
    //          description "Pattern is 2^6 - 1";
    //        }
    //        enum "pseudo-2e7" {
    //          description "Pattern is 2^7 - 1";
    //        }
    //        enum "pseudo-2e9-o153" {
    //          description "Pattern is 2^9 - 1 (per O.153 standard)";
    //        }
    //        enum "pseudo-2e10" {
    //          description "Pattern is 2^10 - 1";
    //        }
    //        enum "pseudo-2e11-o152" {
    //          description "Pattern is 2^11 -1 (per O.152 standard)";
    //        }
    //        enum "pseudo-2e15-o151" {
    //          description "Pattern is 2^15 - 1 (per O.151 standard)";
    //        }
    //        enum "pseudo-2e17" {
    //          description "Pattern is 2^17 - 1";
    //        }
    //        enum "pseudo-2e18" {
    //          description "Pattern is 2^18 - 1";
    //        }
    //        enum "pseudo-2e20-o153" {
    //          description "Pattern is 2^20 - 1 (per O.153 standard)";
    //        }
    //        enum "pseudo-2e20-o151" {
    //          description "Pattern is 2^20 - 1 (per O.151 standard)";
    //        }
    //        enum "pseudo-2e21" {
    //          description "Pattern is 2^21 - 1";
    //        }
    //        enum "pseudo-2e22" {
    //          description "Pattern is 2^22 - 1";
    //        }
    //        enum "pseudo-2e23-o151" {
    //          description "Pattern is 2^23 (per O.151 standard)";
    //        }
    //        enum "pseudo-2e25" {
    //          description "Pattern is 2^25 - 1";
    //        }
    //        enum "pseudo-2e28" {
    //          description "Pattern is 2^28 - 1";
    //        }
    //        enum "pseudo-2e29" {
    //          description "Pattern is 2^29 - 1";
    //        }
    //        enum "pseudo-2e31" {
    //          description "Pattern is 2^31 - 1";
    //        }
    //        enum "pseudo-2e32" {
    //          description "Pattern is 2^32 - 1";
    //        }
    //        enum "all-ones-repeating" {
    //          description "Repeating one bits";
    //        }
    //        enum "all-zeros-repeating" {
    //          description "Repeating zero bits";
    //        }
    //        enum "alternating-ones-zeros" {
    //          description "Alternating ones and zeros";
    //        }
    //        enum "alternating-double-ones-zeros" {
    //          description "Alternating pairs of ones and zeros";
    //        }
    //        enum "repeating-3-in-24" {
    //          description "3 bits in 24 are set";
    //        }
    //        enum "repeating-1-in-8" {
    //          description "1 bit in 8 is set";
    //        }
    //        enum "repeating-1-in-4" {
    //          description "1 bit in 4 is set";
    //        }
    //      }
    //    }
    //    leaf bert-error-rate {
    //      description "Bit error rate (10^-n for n > 0, and zero for n = 0)";
    //      type union {
    //        type string {
    //          pattern "<.*>|$.*";
    //        }
    //        type uint32 {
    //          range "0 .. 7";
    //        }
    //      }
    //    }
    //    leaf bert-period {
    //      description "Length of BERT test";
    //      units "seconds";
    //      type union {
    //        type string {
    //          pattern "<.*>|$.*";
    //        }
    //        type uint32 {
    //          range "1 .. 240";
    //        }
    //      }
    //    }
    //    leaf buildout {
    //      description "Line buildout";
    //      units "feet";
    //      type union {
    //        type string {
    //          pattern "<.*>|$.*";
    //        }
    //        type uint32 {
    //          range "0 .. 450";
    //        }
    //      }
    //    }
    //    leaf atm-encapsulation {
    //      description "E3 interface encapsulation";
    //      type enumeration {
    //        enum "plcp" {
    //          description "PLCP encapsulation";
    //        }
    //        enum "direct" {
    //          description "ATM direct mapping";
    //        }
    //      }
    //    }
    //    leaf framing {
    //      description "E3 line format";
    //      type enumeration {
    //        enum "g.751" {
    //          description "G.751 format";
    //        }
    //        enum "g.832" {
    //          description "G.832 format";
    //        }
    //      }
    //    }
    //  }
    //  container e1-options {
    //    description "E1 interface-specific options";
    //    // uses apply-advanced;
    //    leaf timeslots {
    //      description "Timeslots (1..32); for example, 1-4,6,9-11,32 (no space)";
    //      type string;
    //    }
    //    leaf loopback {
    //      description "Loopback mode";
    //      type enumeration {
    //        enum "local" {
    //          description "Local loopback";
    //        }
    //        enum "remote" {
    //          description "Remote loopback";
    //        }
    //      }
    //    }
    //    leaf framing {
    //      description "Framing mode";
    //      type enumeration {
    //        enum "g704" {
    //          description "G704 mode with CRC4";
    //        }
    //        enum "unframed" {
    //          description "Unframed mode";
    //        }
    //        enum "g704-no-crc4" {
    //          description "G704 mode without CRC4";
    //        }
    //      }
    //    }
    //    leaf fcs {
    //      description "Frame checksum";
    //      type enumeration {
    //        enum "32" {
    //          description "32-bit mode";
    //        }
    //        enum "16" {
    //          description "16-bit mode";
    //        }
    //      }
    //    }
    //    leaf invert-data {
    //      description "Invert data";
    //      type empty;
    //    }
    //    leaf idle-cycle-flag {
    //      description "Value to transmit in idle cycles";
    //      type enumeration {
    //        enum "flags" {
    //          description "Transmit 0x7E in idle cycles";
    //        }
    //        enum "ones" {
    //          description "Transmit 0xFF (all ones) in idle cycles";
    //        }
    //      }
    //    }
    //    leaf start-end-flag {
    //      description "Set start/end flags on transmission";
    //      type enumeration {
    //        enum "shared" {
    //          description "Share start/end flags on transmit";
    //        }
    //        enum "filler" {
    //          description "Send two idle cycles between start/end flags";
    //        }
    //      }
    //    }
    //    leaf bert-algorithm {
    //      description "Set BERT algorithm";
    //      type enumeration {
    //        enum "pseudo-2e3" {
    //          description "Pattern is 2^3 - 1";
    //        }
    //        enum "pseudo-2e4" {
    //          description "Pattern is 2^4 - 1";
    //        }
    //        enum "pseudo-2e5" {
    //          description "Pattern is 2^5 - 1";
    //        }
    //        enum "pseudo-2e6" {
    //          description "Pattern is 2^6 - 1";
    //        }
    //        enum "pseudo-2e7" {
    //          description "Pattern is 2^7 - 1";
    //        }
    //        enum "pseudo-2e9-o153" {
    //          description "Pattern is 2^9 - 1 (per O.153 standard)";
    //        }
    //        enum "pseudo-2e10" {
    //          description "Pattern is 2^10 - 1";
    //        }
    //        enum "pseudo-2e11-o152" {
    //          description "Pattern is 2^11 -1 (per O.152 standard)";
    //        }
    //        enum "pseudo-2e15-o151" {
    //          description "Pattern is 2^15 - 1 (per O.151 standard)";
    //        }
    //        enum "pseudo-2e17" {
    //          description "Pattern is 2^17 - 1";
    //        }
    //        enum "pseudo-2e18" {
    //          description "Pattern is 2^18 - 1";
    //        }
    //        enum "pseudo-2e20-o153" {
    //          description "Pattern is 2^20 - 1 (per O.153 standard)";
    //        }
    //        enum "pseudo-2e20-o151" {
    //          description "Pattern is 2^20 - 1 (per O.151 standard)";
    //        }
    //        enum "pseudo-2e21" {
    //          description "Pattern is 2^21 - 1";
    //        }
    //        enum "pseudo-2e22" {
    //          description "Pattern is 2^22 - 1";
    //        }
    //        enum "pseudo-2e23-o151" {
    //          description "Pattern is 2^23 (per O.151 standard)";
    //        }
    //        enum "pseudo-2e25" {
    //          description "Pattern is 2^25 - 1";
    //        }
    //        enum "pseudo-2e28" {
    //          description "Pattern is 2^28 - 1";
    //        }
    //        enum "pseudo-2e29" {
    //          description "Pattern is 2^29 - 1";
    //        }
    //        enum "pseudo-2e31" {
    //          description "Pattern is 2^31 - 1";
    //        }
    //        enum "pseudo-2e32" {
    //          description "Pattern is 2^32 - 1";
    //        }
    //        enum "all-ones-repeating" {
    //          description "Repeating one bits";
    //        }
    //        enum "all-zeros-repeating" {
    //          description "Repeating zero bits";
    //        }
    //        enum "alternating-ones-zeros" {
    //          description "Alternating ones and zeros";
    //        }
    //        enum "alternating-double-ones-zeros" {
    //          description "Alternating pairs of ones and zeros";
    //        }
    //        enum "repeating-3-in-24" {
    //          description "3 bits in 24 are set";
    //        }
    //        enum "repeating-1-in-8" {
    //          description "1 bit in 8 is set";
    //        }
    //        enum "repeating-1-in-4" {
    //          description "1 bit in 4 is set";
    //        }
    //      }
    //    }
    //    leaf bert-error-rate {
    //      description "Bit error rate (10^-n for n > 0, and zero for n = 0)";
    //      type union {
    //        type string {
    //          pattern "<.*>|$.*";
    //        }
    //        type uint32 {
    //          range "0 .. 7";
    //        }
    //      }
    //    }
    //    leaf bert-period {
    //      description "Length of BERT test";
    //      units "seconds";
    //      type union {
    //        type string {
    //          pattern "<.*>|$.*";
    //        }
    //        type uint32 {
    //          range "1 .. 86400";
    //        }
    //      }
    //    }
    //  }
    //  container t1-options {
    //    description "T1 interface-specific options";
    //    // uses apply-advanced;
    //    leaf timeslots {
    //      description "Timeslots (1..24; for example, 1-3,4,9,22-24 (no space)";
    //      type string;
    //    }
    //    leaf disable-remote-alarm-detection {
    //      description "Disable detection of a remote alarm";
    //      type enumeration {
    //        enum "yellow" {
    //          description "Disable yellow alarm detection";
    //        }
    //      }
    //    }
    //    leaf loopback {
    //      description "Loopback mode";
    //      type enumeration {
    //        enum "local" {
    //          description "Local loopback";
    //        }
    //        enum "remote" {
    //          description "Remote loopback";
    //        }
    //        enum "payload" {
    //          description "Payload loopback";
    //        }
    //      }
    //    }
    //    leaf buildout {
    //      description "Line buildout";
    //      type enumeration {
    //        enum "0-132" {
    //          description "Line buildout is between 0-132 feet";
    //        }
    //        enum "133-265" {
    //          description "Line buildout is between 133-265 feet";
    //        }
    //        enum "266-398" {
    //          description "Line buildout is between 266-398 feet";
    //        }
    //        enum "399-531" {
    //          description "Line buildout is between 399-531 feet";
    //        }
    //        enum "532-655" {
    //          description "Line buildout is between 532-655 feet";
    //        }
    //        enum "long-0db" {
    //          description "Long buildout with 0 dB transmit attenuation";
    //        }
    //        enum "long-7.5db" {
    //          description "Long buildout with 7.5 dB transmit attenuation";
    //        }
    //        enum "long-15db" {
    //          description "Long buildout with 15 dB transmit attenuation";
    //        }
    //        enum "long-22.5db" {
    //          description "Long buildout with 22.5 dB transmit attenuation";
    //        }
    //      }
    //    }
    //    leaf byte-encoding {
    //      description "Byte encoding";
    //      type enumeration {
    //        enum "nx64" {
    //          description "8 bits per byte";
    //        }
    //        enum "nx56" {
    //          description "7 bits per byte";
    //        }
    //      }
    //    }
    //    leaf line-encoding {
    //      description "Line encoding";
    //      type enumeration {
    //        enum "ami" {
    //          description "Automatic mark inversion";
    //        }
    //        enum "b8zs" {
    //          description "8-bit zero suppression";
    //        }
    //      }
    //    }
    //    leaf invert-data {
    //      description "Invert data";
    //      type empty;
    //    }
    //    leaf framing {
    //      description "Framing mode";
    //      type enumeration {
    //        enum "sf" {
    //          description "Super frame";
    //        }
    //        enum "esf" {
    //          description "Extended super frame";
    //        }
    //      }
    //    }
    //    leaf fcs {
    //      description "Frame checksum";
    //      type enumeration {
    //        enum "32" {
    //          description "32-bit mode";
    //        }
    //        enum "16" {
    //          description "16-bit mode";
    //        }
    //      }
    //    }
    //    leaf idle-cycle-flag {
    //      description "Value to transmit in idle cycles";
    //      type enumeration {
    //        enum "flags" {
    //          description "Transmit 0x7E in idle cycles";
    //        }
    //        enum "ones" {
    //          description "Transmit 0xFF (all ones) in idle cycles";
    //        }
    //      }
    //    }
    //    leaf start-end-flag {
    //      description "Set start/end flags on transmission";
    //      type enumeration {
    //        enum "shared" {
    //          description "Share start/end flags on transmit";
    //        }
    //        enum "filler" {
    //          description "Send two idle cycles between start/end flags";
    //        }
    //      }
    //    }
    //    leaf bert-algorithm {
    //      description "Set BERT algorithm";
    //      type enumeration {
    //        enum "pseudo-2e3" {
    //          description "Pattern is 2^3 - 1";
    //        }
    //        enum "pseudo-2e4" {
    //          description "Pattern is 2^4 - 1";
    //        }
    //        enum "pseudo-2e5" {
    //          description "Pattern is 2^5 - 1";
    //        }
    //        enum "pseudo-2e6" {
    //          description "Pattern is 2^6 - 1";
    //        }
    //        enum "pseudo-2e7" {
    //          description "Pattern is 2^7 - 1";
    //        }
    //        enum "pseudo-2e9-o153" {
    //          description "Pattern is 2^9 - 1 (per O.153 standard)";
    //        }
    //        enum "pseudo-2e10" {
    //          description "Pattern is 2^10 - 1";
    //        }
    //        enum "pseudo-2e11-o152" {
    //          description "Pattern is 2^11 -1 (per O.152 standard)";
    //        }
    //        enum "pseudo-2e15-o151" {
    //          description "Pattern is 2^15 - 1 (per O.151 standard)";
    //        }
    //        enum "pseudo-2e17" {
    //          description "Pattern is 2^17 - 1";
    //        }
    //        enum "pseudo-2e18" {
    //          description "Pattern is 2^18 - 1";
    //        }
    //        enum "pseudo-2e20-o153" {
    //          description "Pattern is 2^20 - 1 (per O.153 standard)";
    //        }
    //        enum "pseudo-2e20-o151" {
    //          description "Pattern is 2^20 - 1 (per O.151 standard)";
    //        }
    //        enum "pseudo-2e21" {
    //          description "Pattern is 2^21 - 1";
    //        }
    //        enum "pseudo-2e22" {
    //          description "Pattern is 2^22 - 1";
    //        }
    //        enum "pseudo-2e23-o151" {
    //          description "Pattern is 2^23 (per O.151 standard)";
    //        }
    //        enum "pseudo-2e25" {
    //          description "Pattern is 2^25 - 1";
    //        }
    //        enum "pseudo-2e28" {
    //          description "Pattern is 2^28 - 1";
    //        }
    //        enum "pseudo-2e29" {
    //          description "Pattern is 2^29 - 1";
    //        }
    //        enum "pseudo-2e31" {
    //          description "Pattern is 2^31 - 1";
    //        }
    //        enum "pseudo-2e32" {
    //          description "Pattern is 2^32 - 1";
    //        }
    //        enum "all-ones-repeating" {
    //          description "Repeating one bits";
    //        }
    //        enum "all-zeros-repeating" {
    //          description "Repeating zero bits";
    //        }
    //        enum "alternating-ones-zeros" {
    //          description "Alternating ones and zeros";
    //        }
    //        enum "alternating-double-ones-zeros" {
    //          description "Alternating pairs of ones and zeros";
    //        }
    //        enum "repeating-3-in-24" {
    //          description "3 bits in 24 are set";
    //        }
    //        enum "repeating-1-in-8" {
    //          description "1 bit in 8 is set";
    //        }
    //        enum "repeating-1-in-4" {
    //          description "1 bit in 4 is set";
    //        }
    //      }
    //    }
    //    leaf bert-error-rate {
    //      description "Bit error rate (10^-n for n > 0, and zero for n = 0)";
    //      type union {
    //        type string {
    //          pattern "<.*>|$.*";
    //        }
    //        type uint32 {
    //          range "0 .. 7";
    //        }
    //      }
    //    }
    //    leaf bert-period {
    //      description "Length of BERT test";
    //      units "seconds";
    //      type union {
    //        type string {
    //          pattern "<.*>|$.*";
    //        }
    //        type uint32 {
    //          range "1 .. 86400";
    //        }
    //      }
    //    }
    //    leaf remote-loopback-respond {
    //      description "Respond to loop requests from remote end";
    //      type empty;
    //    }
    //    leaf crc-major-alarm-threshold {
    //      description "CRC Major alarm threshold value";
    //      default "5e-5";
    //      type enumeration {
    //        enum "1e-3" {
    //          description "1 crc error in 10^3 bits";
    //        }
    //        enum "5e-4" {
    //          description "5 crc errors in 10^4 bits";
    //        }
    //        enum "1e-4" {
    //          description "1 crc error in 10^4 bits";
    //        }
    //        enum "5e-5" {
    //          description "5 crc errors in 10^5 bits";
    //        }
    //        enum "1e-5" {
    //          description "1 crc error in 10^5 bits";
    //        }
    //      }
    //    }
    //    leaf crc-minor-alarm-threshold {
    //      description "CRC Minor alarm threshold value";
    //      default "5e-6";
    //      type enumeration {
    //        enum "1e-3" {
    //          description "1 crc error in 10^3 bits";
    //        }
    //        enum "5e-4" {
    //          description "5 crc errors in 10^4 bits";
    //        }
    //        enum "1e-4" {
    //          description "1 crc error in 10^4 bits";
    //        }
    //        enum "5e-5" {
    //          description "5 crc errors in 10^5 bits";
    //        }
    //        enum "1e-5" {
    //          description "1 crc error in 10^5 bits";
    //        }
    //        enum "5e-6" {
    //          description "5 crc errors in 10^6 bits";
    //        }
    //        enum "1e-6" {
    //          description "1 crc error in 10^6 bits";
    //        }
    //      }
    //    }
    //  }
    //  container ds0-options {
    //    description "DS-0 interface-specific options";
    //    // uses apply-advanced;
    //    leaf loopback {
    //      description "Loopback mode";
    //      type enumeration {
    //        enum "payload" {
    //          description "Payload loopback";
    //        }
    //      }
    //    }
    //    leaf byte-encoding {
    //      description "Byte encoding";
    //      type enumeration {
    //        enum "nx64" {
    //          description "8 bits per byte";
    //        }
    //        enum "nx56" {
    //          description "7 bits per byte";
    //        }
    //      }
    //    }
    //    leaf invert-data {
    //      description "Invert data";
    //      type empty;
    //    }
    //    leaf fcs {
    //      description "Frame checksum";
    //      type enumeration {
    //        enum "32" {
    //          description "32-bit mode";
    //        }
    //        enum "16" {
    //          description "16-bit mode";
    //        }
    //      }
    //    }
    //    leaf idle-cycle-flag {
    //      description "Value to transmit in idle cycles";
    //      type enumeration {
    //        enum "flags" {
    //          description "Transmit 0x7E in idle cycles";
    //        }
    //        enum "ones" {
    //          description "Transmit 0xFF (all ones) in idle cycles";
    //        }
    //      }
    //    }
    //    leaf start-end-flag {
    //      description "Set start/end flags on transmission";
    //      type enumeration {
    //        enum "shared" {
    //          description "Share start/end flags on transmit";
    //        }
    //        enum "filler" {
    //          description "Send two idle cycles between start/end flags";
    //        }
    //      }
    //    }
    //    leaf bert-algorithm {
    //      description "Set BERT algorithm";
    //      type enumeration {
    //        enum "pseudo-2e11-o152" {
    //          description "Pattern is 2^11 -1 (per O.152 standard)";
    //        }
    //        enum "pseudo-2e15-o151" {
    //          description "Pattern is 2^15 - 1 (per O.151 standard)";
    //        }
    //        enum "pseudo-2e20-o153" {
    //          description "Pattern is 2^20 - 1 (per O.153 standard)";
    //        }
    //        enum "pseudo-2e20-o151" {
    //          description "Pattern is 2^20 - 1 (per O.151 standard)";
    //        }
    //        enum "all-ones-repeating" {
    //          description "Repeating one bits";
    //        }
    //        enum "all-zeros-repeating" {
    //          description "Repeating zero bits";
    //        }
    //        enum "alternating-ones-zeros" {
    //          description "Alternating ones and zeros";
    //        }
    //        enum "alternating-double-ones-zeros" {
    //          description "Alternating pairs of ones and zeros";
    //        }
    //        enum "repeating-3-in-24" {
    //          description "3 bits in 24 are set";
    //        }
    //        enum "repeating-1-in-8" {
    //          description "1 bit in 8 is set";
    //        }
    //        enum "repeating-1-in-4" {
    //          description "1 bit in 4 is set";
    //        }
    //        enum "repeating-1-in-16" {
    //          description "1 bit in 16 is set";
    //        }
    //      }
    //    }
    //    leaf bert-error-rate {
    //      description "Bit error rate (10^-n for n > 0, and zero for n = 0)";
    //      type union {
    //        type string {
    //          pattern "<.*>|$.*";
    //        }
    //        type uint32 {
    //          range "0 .. 7";
    //        }
    //      }
    //    }
    //    leaf bert-period {
    //      description "Length of BERT test";
    //      units "seconds";
    //      type union {
    //        type string {
    //          pattern "<.*>|$.*";
    //        }
    //        type uint32 {
    //          range "1 .. 240";
    //        }
    //      }
    //    }
    //  }
    //  container serial-options {
    //    description "Serial interface-specific options";
    //    // uses apply-advanced;
    //    leaf line-protocol {
    //      description "Line protocol to be used";
    //      default "eia530";
    //      type enumeration {
    //        enum "eia530" {
    //          description "Line protocol EIA530";
    //        }
    //        enum "v.35" {
    //          description "Line protocol V.35";
    //        }
    //        enum "x.21" {
    //          description "Line protocol X.21";
    //        }
    //      }
    //    }
    //    choice control_leads_choice {
    //      case case_1 {
    //        container dte-options {
    //          description "DTE options/control leads";
    //          // uses apply-advanced;
    //          leaf ignore-all {
    //            description "Ignore all control leads";
    //            type empty;
    //          }
    //          container dtr {
    //            description "Data Transmit Ready signal handling";
    //            choice dtr_choices {
    //              case case_1 {
    //                leaf assert {
    //                  description "Assert DTR signal";
    //                  type empty;
    //                }
    //              }
    //              case case_2 {
    //                leaf de-assert {
    //                  description "Deassert DTR signal";
    //                  type empty;
    //                }
    //              }
    //              case case_3 {
    //                leaf normal {
    //                  description "Normal DTR signal";
    //                  type empty;
    //                }
    //              }
    //              case case_4 {
    //                container auto-synchronize {
    //                  presence "enable auto-synchronize";
    //                  description "Normal DTR signal, with autoresynchronization";
    //                  // uses apply-advanced;
    //                  leaf duration {
    //                    description "Duration of autoresynchronization";
    //                    units "milliseconds";
    //                    type union {
    //                      type string {
    //                        pattern "<.*>|$.*";
    //                      }
    //                      type uint16 {
    //                        range "1 .. 1000";
    //                      }
    //                    }
    //                  }
    //                  leaf interval {
    //                    description "Interval for autoresynchronization";
    //                    units "seconds";
    //                    type union {
    //                      type string {
    //                        pattern "<.*>|$.*";
    //                      }
    //                      type uint16 {
    //                        range "1 .. 31";
    //                      }
    //                    }
    //                  }
    //                }
    //              }
    //            }
    //          }
    //          leaf control-signal {
    //            description "X.21 control signal handling";
    //            type enumeration {
    //              enum "assert" {
    //                description "Assert control signal";
    //              }
    //              enum "de-assert" {
    //                description "Deassert control signal";
    //              }
    //              enum "normal" {
    //                description "Normal control signal";
    //              }
    //            }
    //          }
    //          leaf rts {
    //            description "Request To Send signal handling";
    //            type enumeration {
    //              enum "assert" {
    //                description "Assert RTS signal";
    //              }
    //              enum "de-assert" {
    //                description "Deassert RTS signal";
    //              }
    //              enum "normal" {
    //                description "Normal RTS signal";
    //              }
    //            }
    //          }
    //          leaf dcd {
    //            description "Data Carrier Detect signal handling";
    //            type enumeration {
    //              enum "require" {
    //                description "Require DCD signal";
    //              }
    //              enum "ignore" {
    //                description "Ignore DCD signal";
    //              }
    //              enum "normal" {
    //                description "Normal DCD signal";
    //              }
    //            }
    //          }
    //          leaf dsr {
    //            description "Data Set Ready signal handling";
    //            type enumeration {
    //              enum "require" {
    //                description "Require DSR signal";
    //              }
    //              enum "ignore" {
    //                description "Ignore DSR signal";
    //              }
    //              enum "normal" {
    //                description "Normal DSR signal";
    //              }
    //            }
    //          }
    //          leaf cts {
    //            description "Clear To Send signal handling";
    //            type enumeration {
    //              enum "require" {
    //                description "Require CTS signal";
    //              }
    //              enum "ignore" {
    //                description "Ignore CTS signal";
    //              }
    //              enum "normal" {
    //                description "Normal CTS signal";
    //              }
    //            }
    //          }
    //          leaf indication {
    //            description "X.21 Indication signal handling";
    //            type enumeration {
    //              enum "require" {
    //                description "Require Indication signal";
    //              }
    //              enum "ignore" {
    //                description "Ignore Indication signal";
    //              }
    //              enum "normal" {
    //                description "Normal Indication signal";
    //              }
    //            }
    //          }
    //          leaf tm {
    //            description "Test Mode signal handling";
    //            type enumeration {
    //              enum "require" {
    //                description "Require TM signal";
    //              }
    //              enum "ignore" {
    //                description "Ignore TM signal";
    //              }
    //              enum "normal" {
    //                description "Normal TM signal";
    //              }
    //            }
    //          }
    //        }
    //      }
    //      case case_2 {
    //        container dce-options {
    //          description "DCE options";
    //          // uses apply-advanced;
    //          leaf ignore-all {
    //            description "Ignore all control leads";
    //            type empty;
    //          }
    //          leaf dtr {
    //            description "Data Transmit Ready signal handling";
    //            type enumeration {
    //              enum "require" {
    //                description "Require Data Carrier Detect (DCD) signal";
    //              }
    //              enum "ignore" {
    //                description "Ignore Data Carrier Detect (DCD) signal";
    //              }
    //              enum "normal" {
    //                description "Normal Data Carrier Detect (DCD) signal";
    //              }
    //            }
    //          }
    //          leaf rts {
    //            description "Request To Send signal handling";
    //            type enumeration {
    //              enum "require" {
    //                description "Require Data Carrier Detect (DCD) signal";
    //              }
    //              enum "ignore" {
    //                description "Ignore Data Carrier Detect (DCD) signal";
    //              }
    //              enum "normal" {
    //                description "Normal Data Carrier Detect (DCD) signal";
    //              }
    //            }
    //          }
    //          leaf dcd {
    //            description "Data Carrier Detect signal handling";
    //            type enumeration {
    //              enum "assert" {
    //                description "Assert Request To Send (RTS) signal";
    //              }
    //              enum "de-assert" {
    //                description "Deassert Request To Send (RTS) signal";
    //              }
    //              enum "normal" {
    //                description "Normal Request To Send (RTS) signal";
    //              }
    //            }
    //          }
    //          leaf dsr {
    //            description "Data Set Ready signal handling";
    //            type enumeration {
    //              enum "assert" {
    //                description "Assert Request To Send (RTS) signal";
    //              }
    //              enum "de-assert" {
    //                description "Deassert Request To Send (RTS) signal";
    //              }
    //              enum "normal" {
    //                description "Normal Request To Send (RTS) signal";
    //              }
    //            }
    //          }
    //          leaf cts {
    //            description "Clear To Send signal handling";
    //            type enumeration {
    //              enum "assert" {
    //                description "Assert Request To Send (RTS) signal";
    //              }
    //              enum "de-assert" {
    //                description "Deassert Request To Send (RTS) signal";
    //              }
    //              enum "normal" {
    //                description "Normal Request To Send (RTS) signal";
    //              }
    //            }
    //          }
    //          leaf tm {
    //            description "Test Mode signal handling";
    //            type enumeration {
    //              enum "require" {
    //                description "Require TM signal";
    //              }
    //              enum "ignore" {
    //                description "Ignore TM signal";
    //              }
    //              enum "normal" {
    //                description "Normal TM signal";
    //              }
    //            }
    //          }
    //          leaf dce-loopback-override {
    //            description "DCE loopback override";
    //            type empty;
    //          }
    //        }
    //      }
    //    }
    //    leaf dtr-circuit {
    //      description "Data Transmit Ready circuit mode";
    //      type enumeration {
    //        enum "balanced" {
    //          description "Balanced signal";
    //        }
    //        enum "unbalanced" {
    //          description "Unbalanced signal";
    //        }
    //      }
    //    }
    //    leaf dtr-polarity {
    //      description "Data Transmit Ready signal polarity";
    //      type enumeration {
    //        enum "positive" {
    //          description "Positive polarity";
    //        }
    //        enum "negative" {
    //          description "Negative polarity";
    //        }
    //      }
    //    }
    //    leaf rts-polarity {
    //      description "Request To Send signal polarity";
    //      type enumeration {
    //        enum "positive" {
    //          description "Positive polarity";
    //        }
    //        enum "negative" {
    //          description "Negative polarity";
    //        }
    //      }
    //    }
    //    leaf control-polarity {
    //      description "X.21 Control signal polarity";
    //      type enumeration {
    //        enum "positive" {
    //          description "Positive polarity";
    //        }
    //        enum "negative" {
    //          description "Negative polarity";
    //        }
    //      }
    //    }
    //    leaf dcd-polarity {
    //      description "Data Carrier Detect signal polarity";
    //      type enumeration {
    //        enum "positive" {
    //          description "Positive polarity";
    //        }
    //        enum "negative" {
    //          description "Negative polarity";
    //        }
    //      }
    //    }
    //    leaf dsr-polarity {
    //      description "Data Set Ready signal polarity";
    //      type enumeration {
    //        enum "positive" {
    //          description "Positive polarity";
    //        }
    //        enum "negative" {
    //          description "Negative polarity";
    //        }
    //      }
    //    }
    //    leaf cts-polarity {
    //      description "Clear To Send signal polarity";
    //      type enumeration {
    //        enum "positive" {
    //          description "Positive polarity";
    //        }
    //        enum "negative" {
    //          description "Negative polarity";
    //        }
    //      }
    //    }
    //    leaf indication-polarity {
    //      description "X.21 Indication signal polarity";
    //      type enumeration {
    //        enum "positive" {
    //          description "Positive polarity";
    //        }
    //        enum "negative" {
    //          description "Negative polarity";
    //        }
    //      }
    //    }
    //    leaf tm-polarity {
    //      description "Test Mode signal polarity";
    //      type enumeration {
    //        enum "positive" {
    //          description "Positive polarity";
    //        }
    //        enum "negative" {
    //          description "Negative polarity";
    //        }
    //      }
    //    }
    //    leaf clocking-mode {
    //      description "Clock mode";
    //      type enumeration {
    //        enum "dce" {
    //          description "DCE timing (DTE mode only, not valid for X.21)";
    //        }
    //        enum "internal" {
    //          description "Internal baud timing";
    //        }
    //        enum "loop" {
    //          description "Loop timing";
    //        }
    //      }
    //    }
    //    leaf transmit-clock {
    //      description "Transmit clock phase";
    //      type enumeration {
    //        enum "invert" {
    //          description "Shift clock phase 180 degrees";
    //        }
    //      }
    //    }
    //    leaf clock-rate {
    //      description "Interface clock rate";
    //      type enumeration {
    //        enum "2.048mhz" {
    //          description "2.048 MHz";
    //        }
    //        enum "2.341mhz" {
    //          description "2.341 MHz";
    //        }
    //        enum "2.731mhz" {
    //          description "2.731 MHz";
    //        }
    //        enum "3.277mhz" {
    //          description "3.277 MHz";
    //        }
    //        enum "4.096mhz" {
    //          description "4.096 MHz";
    //        }
    //        enum "5.461mhz" {
    //          description "5.461 MHz";
    //        }
    //        enum "8.192mhz" {
    //          description "8.192 MHz";
    //        }
    //        enum "16.384mhz" {
    //          description "16.384 MHz";
    //        }
    //        enum "1.2khz" {
    //          description "1.2 KHz";
    //        }
    //        enum "2.4khz" {
    //          description "2.4 KHz";
    //        }
    //        enum "9.6khz" {
    //          description "9.6 KHz";
    //        }
    //        enum "19.2khz" {
    //          description "19.2 KHz";
    //        }
    //        enum "38.4khz" {
    //          description "38.4 KHz";
    //        }
    //        enum "56.0khz" {
    //          description "56.0 KHz";
    //        }
    //        enum "64.0khz" {
    //          description "64.0 KHz";
    //        }
    //        enum "72.0khz" {
    //          description "72.0 KHz";
    //        }
    //        enum "125.0khz" {
    //          description "125.0 KHz";
    //        }
    //        enum "148.0khz" {
    //          description "148.0 KHz";
    //        }
    //        enum "250.0khz" {
    //          description "250.0 KHz";
    //        }
    //        enum "500.0khz" {
    //          description "500.0 KHz";
    //        }
    //        enum "800.0khz" {
    //          description "800.0 KHz";
    //        }
    //        enum "1.0mhz" {
    //          description "1.0 MHz";
    //        }
    //        enum "1.3mhz" {
    //          description "1.3 MHz";
    //        }
    //        enum "2.0mhz" {
    //          description "2.0 MHz";
    //        }
    //        enum "4.0mhz" {
    //          description "4.0 MHz";
    //        }
    //        enum "8.0mhz" {
    //          description "8.0 MHz";
    //        }
    //      }
    //    }
    //    leaf loopback {
    //      description "Loopback mode";
    //      type enumeration {
    //        enum "local" {
    //          description "Local loopback";
    //        }
    //        enum "remote" {
    //          description "Remote/LIU loopback";
    //        }
    //        enum "dce-local" {
    //          description "DCE local loopback (DTE mode only)";
    //        }
    //        enum "dce-remote" {
    //          description "DCE remote loopback";
    //        }
    //      }
    //    }
    //    leaf encoding {
    //      description "Line encoding";
    //      type enumeration {
    //        enum "nrz" {
    //          description "Non-Return-To-Zero";
    //        }
    //        enum "nrzi" {
    //          description "Non-Return-To-Zero-Invertible";
    //        }
    //      }
    //    }
    //    leaf idle-cycle-flag {
    //      description "Value to transmit in idle cycles";
    //      type enumeration {
    //        enum "flags" {
    //          description "Transmit 0x7E in idle cycles";
    //        }
    //        enum "ones" {
    //          description "Transmit 0xFF (all ones) in idle cycles";
    //        }
    //      }
    //    }
    //  }
    //  choice gratuitous-arp-reply-choice {
    //    leaf gratuitous-arp-reply {
    //      description "Enable gratuitous ARP reply";
    //      type empty;
    //    }
    //    leaf no-gratuitous-arp-reply {
    //      description "Don't enable gratuitous ARP reply";
    //      type empty;
    //    }
    //  }
    //  choice no-gratuitous-arp-request-choice {
    //    leaf no-gratuitous-arp-request {
    //      description "Ignore gratuitous ARP request";
    //      type empty;
    //    }
    //    leaf no-no-gratuitous-arp-request {
    //      description "Don't ignore gratuitous ARP request";
    //      type empty;
    //    }
    //  }
    //  leaf arp-l2-validate {
    //    description "Validate ARP against L2";
    //    type empty;
    //  }
     container ether-options {
       description "Ethernet interface-specific options";
       // uses apply-advanced;
       choice loopback-choice {
         leaf loopback {
           description "Enable loopback";
           type empty;
         }
         leaf no-loopback {
           description "Don't enable loopback";
           type empty;
         }
       }
       leaf loopback-remote {
         description "Enable remote loopback";
         type empty;
       }
       choice source-filtering-choice {
         leaf source-filtering {
           description "Enable source address filtering";
           type empty;
         }
         leaf no-source-filtering {
           description "Don't enable source address filtering";
           type empty;
         }
       }
      //  container ethernet-switch-profile {
      //    description "Ethernet virtual LAN/media access control-level options";
      //    // uses apply-advanced;
      //    leaf-list tag-protocol-id {
      //      ordered-by user;
      //      description "IEEE 802.1q Tag Protocol Identifier values for VLAN-tagged frames";
      //      type string;
      //    }
      //    container ethernet-policer-profile {
      //      description "Ethernet level CoS-based policer configuration";
      //      // uses apply-advanced;
      //      container input-priority-map {
      //        description "Input policer priority map";
      //        uses cos_policer_input_priority_map;
      //      }
      //      container output-priority-map {
      //        description "Output policer priority map";
      //        uses cos_policer_output_priority_map;
      //      }
      //      list policer {
      //        key name;
      //        ordered-by user;
      //        description "Policer template definition";
      //        uses cos_policer;
      //      }
      //    }
      //    container storm-control {
      //      description "Storm control profile name to bind";
      //      // uses apply-advanced;
      //      leaf profile-name {
      //        description "Profile name";
      //        type string;
      //      }
      //    }
      //    container recovery-timeout {
      //      description "Recovery timeout for this interface";
      //      leaf time-in-seconds {
      //        units "seconds";
      //        type union {
      //          type string {
      //            pattern "<.*>|$.*";
      //          }
      //          type uint32 {
      //            range "10 .. 3600";
      //          }
      //        }
      //      }
      //    }
      //    choice mac-learn-enable-choice {
      //      leaf mac-learn-enable {
      //        description "Learn MAC addresses dynamically";
      //        type empty;
      //      }
      //      leaf no-mac-learn-enable {
      //        description "Don't learn MAC addresses dynamically";
      //        type empty;
      //      }
      //    }
      //  }
      //  leaf asynchronous-notification {
      //    description "Enable sending asynchronous notification to peer on CCC-down";
      //    type empty;
      //  }
       list source-address-filter {
         key name;
         description "Source address filters";
         leaf name {
           description "Remote MAC address";
           type jt:mac-addr;
         }
       }
       choice auto-negotiation-choice {
         leaf auto-negotiation {
           description "Enable auto-negotiation";
           type empty;
         }
         leaf no-auto-negotiation {
           description "Don't enable auto-negotiation";
           type empty;
         }
       }
       choice flow-control-choice {
         leaf flow-control {
           description "Enable flow control";
           type empty;
         }
         leaf no-flow-control {
           description "Don't enable flow control";
           type empty;
         }
       }
       container configured-flow-control {
         presence "enable configured-flow-control";
         description "Enable flow control";
         // uses apply-advanced;
         leaf rx-buffers {
           description "Enable/Disable Rx buffers";
           type enumeration {
             enum "on" {
               description "Enable Rx buffers";
             }
             enum "off" {
               description "Disable Rx buffers";
             }
           }
         }
         leaf tx-buffers {
           description "Enable/Disable Tx buffers";
           type enumeration {
             enum "on" {
               description "Enable Tx buffers";
             }
             enum "off" {
               description "Disable Tx buffers";
             }
           }
         }
       }
       leaf link-mode {
         description "Link duplex";
         type enumeration {
           enum "automatic" {
             description "Automatic negotiate duplex ";
           }
           enum "half-duplex" {
             description "Half-duplex operation";
           }
           enum "full-duplex" {
             description "Full-duplex operation";
           }
         }
       }
       container mpls {
         description "MPLS options";
         uses mpls_ifd_options;
       }
       leaf ignore-l3-incompletes {
         description "Ignore L3 incomplete errors";
         type empty;
       }
       leaf no-auto-mdix {
         description "Disable auto MDI/MDIX";
         type empty;
       }
       leaf fec {
         description "Forward Error Correction mode";
         type enumeration {
           enum "none" {
             description "FEC disabled";
           }
           enum "fec91" {
             description "IEEE 802.3bj Clause 91, Reed-Solomon FEC (RS-FEC)";
           }
           enum "fec74" {
             description "FEC74 enabled";
           }
           enum "fec108" {
             description "IEEE 802.3by Clause 108, Reed-Solomon FEC (RS-FEC) on 25g links";
           }
           enum "fec161" {
             description "IEEE 802.3ck Clause 161 for 100G electrical links";
           }
         }
       }
       container speed {
         description "Specify speed";
         choice automatic {
           case case_1 {
             container auto-negotiation {
               presence "enable auto-negotiation";
               description "Enable auto-negotiation";
               leaf auto-negotiate-10-100 {
                 description "Limits the auto-negotiation to 10m/100m only";
                 type empty;
               }
             }
           }
           case case_2 {
             leaf ethernet-10m {
               description "10Mbps";
               type empty;
             }
           }
           case case_3 {
             leaf ethernet-100m {
               description "100Mbps";
               type empty;
             }
           }
           case case_4 {
             leaf ethernet-1g {
               description "1Gbps";
               type empty;
             }
           }
           case case_5 {
             leaf ethernet-10g {
               description "10Gbps";
               type empty;
             }
           }
         }
       }
       container ieee-802.3ad {
         description "IEEE 802.3ad";
         // uses apply-advanced;
         container lacp {
           description "Link Aggregation Control Protocol configuration";
           // uses apply-advanced;
           leaf force-up {
             description "Keep the port up in absence of received LACPDU";
             type empty;
           }
           leaf port-priority {
             description "Priority of the port (0 ... 65535)";
             type union {
               type uint16;
               type string {
                 pattern "<.*>|$.*";
               }
             }
           }
         }
         leaf bundle {
           description "Join an aggregated Ethernet interface";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
         container link-protection-sub-group {
           description "Link Protection subgroup configuration";
           // uses apply-advanced;
           leaf subgroup-name {
             description "Name of the subgroup";
             type string {
               length "2 .. 64";
             }
           }
         }
         leaf port-priority {
           description "Link protection Priority of the port (0 ... 65535)";
           type union {
             type uint16;
             type string {
               pattern "<.*>|$.*";
             }
           }
         }
       }
       leaf ieee-802-3az-eee {
         description "IEEE 802.3az Energy Efficient Ethernet(EEE)";
         type empty;
       }
       container redundant-parent {
         description " Parent of this interface";
         // uses apply-advanced;
         leaf parent {
           description "Join a redundant ethernet interface";
           type union {
             type jt:interface-device;
             type string {
               pattern "<.*>|$.*";
             }
           }
         }
       }
       leaf autostate-exclude {
         description "Interface will not contribute to IRB state";
         type empty;
       }
     }
    //  container fibrechannel-options {
    //    description "Fibre Channel interface-specific options";
    //    // uses apply-advanced;
    //    choice loopback-choice {
    //      leaf loopback {
    //        description "Enable loopback";
    //        type empty;
    //      }
    //      leaf no-loopback {
    //        description "Don't enable loopback";
    //        type empty;
    //      }
    //    }
    //    leaf bb-sc-n {
    //      description "B2B state change number";
    //      type union {
    //        type string {
    //          pattern "<.*>|$.*";
    //        }
    //        type uint16 {
    //          range "0 .. 15";
    //        }
    //      }
    //    }
    //    leaf speed {
    //      description "Specify speed";
    //      type enumeration {
    //        enum "auto-negotiation" {
    //          description "Enable auto-negotiation";
    //        }
    //        enum "1g" {
    //          description "1Gbps";
    //        }
    //        enum "2g" {
    //          description "2Gbps";
    //        }
    //        enum "4g" {
    //          description "4Gbps";
    //        }
    //        enum "8g" {
    //          description "8Gbps";
    //        }
    //      }
    //    }
    //  }
     container gigether-options {
       description "Gigabit Ethernet interface-specific options";
       // uses apply-advanced;
       choice loopback-choice {
         leaf loopback {
           description "Enable loopback";
           type empty;
         }
         leaf no-loopback {
           description "Don't enable loopback";
           type empty;
         }
       }
       leaf loopback-remote {
         description "Enable remote loopback";
         type empty;
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       choice auto_negotiation_option {
         case case_1 {
           leaf no-auto-negotiation {
             description "Disable auto-negotiation";
             type empty;
           }
         }
         case case_2 {
           container auto-negotiation {
             presence "enable auto-negotiation";
             description "Enable auto-negotiation";
             leaf remote-fault {
               type enumeration {
                 enum "local-interface-offline" {
                   description "Disable local interface";
                 }
                 enum "local-interface-online" {
                   description "Enable local interface";
                 }
               }
             }
           }
         }
       }
       leaf asynchronous-notification {
         description "Enable sending asynchronous notification to peer on CCC-down";
         type empty;
       }
       list source-address-filter {
         key name;
         description "Source address filters";
         leaf name {
           description "Remote MAC address";
           type jt:mac-addr;
         }
       }
       leaf pad-to-minimum-frame-size {
         description "Pad Tx vlan tagged frame to minimum of 68 bytes";
         type empty;
       }
       container redundant-parent {
         description "Parent of this interface";
         // uses apply-advanced;
         leaf parent {
           description "Join a redundant-ethernet interface";
           type union {
             type jt:interface-device;
             type string {
               pattern "<.*>|$.*";
             }
           }
         }
       }
       container ieee-802.3ad {
         description "IEEE 802.3ad";
         // uses apply-advanced;
         container lacp {
           description "Link Aggregation Control Protocol configuration";
           // uses apply-advanced;
           leaf port-priority {
             description "Priority of the port (0 ... 65535)";
             type union {
               type uint16;
               type string {
                 pattern "<.*>|$.*";
               }
             }
           }
         }
         leaf bundle {
           description "Join an aggregated Ethernet interface";
           type union {
             type jt:interface-device;
             type string {
               pattern "<.*>|$.*";
             }
           }
         }
         leaf link-index {
           description "Desired child link index within the Aggregated Interface";
           type union {
             type string {
               pattern "<.*>|$.*";
             }
             type uint16 {
               range "0 .. 63";
             }
           }
         }
         choice type {
           case case_1 {
             leaf primary {
               description "Primary interface for link-protection mode";
               type empty;
             }
           }
           case case_2 {
             leaf backup {
               description "Backup interface for link-protection mode";
               type empty;
             }
           }
         }
         leaf distribution-list {
           description "Distribution list to which interface belongs";
           type string {
             length "1 .. 20";
           }
         }
       }
      //  container ethernet-switch-profile {
      //    description "Ethernet virtual LAN/media access control-level options";
      //    // uses apply-advanced;
      //    leaf-list tag-protocol-id {
      //      ordered-by user;
      //      description "IEEE 802.1q Tag Protocol Identifier values for VLAN-tagged frames";
      //      type string;
      //    }
      //    container ethernet-policer-profile {
      //      description "Ethernet level CoS-based policer configuration";
      //      // uses apply-advanced;
      //      container ieee802.1-priority-map {
      //        presence "enable ieee802.1-priority-map";
      //        description "Premium priority values for IEEE 802.1p bits";
      //        status deprecated;
      //        // uses apply-advanced;
      //        leaf-list premium {
      //          ordered-by user;
      //          description "Premium policer priority map";
      //          type union {
      //            type string {
      //              pattern "<.*>|$.*";
      //            }
      //            type uint32 {
      //              range "0 .. 7";
      //            }
      //          }
      //        }
      //      }
      //      container input-priority-map {
      //        description "Input policer priority map";
      //        uses cos_policer_input_priority_map;
      //      }
      //      container output-priority-map {
      //        description "Output policer priority map";
      //        uses cos_policer_output_priority_map;
      //      }
      //      list policer {
      //        key name;
      //        ordered-by user;
      //        description "Policer template definition";
      //        uses cos_policer;
      //      }
      //    }
      //    container accept-from {
      //      description "Accept traffic from or to specified remote MAC";
      //      status deprecated;
      //      // uses apply-advanced;
      //      list mac-address {
      //        key name;
      //        description "Remote MAC";
      //        uses mac_list;
      //      }
      //    }
      //    choice reject-the-rest-choice {
      //      leaf reject-the-rest {
      //        description "Accept traffic from only the specified MAC addresses";
      //        status deprecated;
      //        type empty;
      //      }
      //      leaf no-reject-the-rest {
      //        description "Don't accept traffic from only the specified MAC addresses";
      //        status deprecated;
      //        type empty;
      //      }
      //    }
      //    leaf mac-learn-enable {
      //      description "Learn MAC addresses dynamically";
      //      type empty;
      //    }
      //  }
       container mpls {
         description "MPLS options";
         uses mpls_ifd_options;
       }
       leaf ignore-l3-incompletes {
         description "Ignore L3 incomplete errors";
         type empty;
       }
      //  leaf no-auto-mdix {
      //    description "Disable auto MDI/MDIX";
      //    type empty;
      //  }
      //  leaf ieee-802-3az-eee {
      //    description "IEEE 802.3az Energy Efficient Ethernet(EEE)";
      //    type empty;
      //  }
       leaf mru {
         description "Maximum receive packet size";
         type union {
           type string {
             pattern "<.*>|$.*";
           }
           type uint32;
         }
       }
       leaf fec {
         description "Forward Error Correction mode";
         type enumeration {
           enum "none" {
             description "FEC disabled";
           }
           enum "fec91" {
             description "IEEE 802.3bj Clause 91, Reed-Solomon FEC (RS-FEC)";
           }
           enum "fec74" {
             description "FEC74 enabled";
           }
           enum "fec108" {
             description "IEEE 802.3by Clause 108, Reed-Solomon FEC (RS-FEC) on 25g links";
           }
           enum "fec161" {
             description "IEEE 802.3ck Clause 161 for 100G electrical links";
           }
         }
       }
       leaf speed {
         description "Speed mode";
         type enumeration {
           enum "1g" {
             description "Speed 1g";
           }
           enum "10g" {
             description "Speed 10g";
           }
         }
       }
     }
    //  container optics-options {
    //    description "Optics options";
    //    // uses apply-advanced;
    //    leaf wavelength {
    //      description "Wavelength of the optics (nanometers) for 50Ghz/100Ghz spacing";
    //      type enumeration {
    //        enum "1568.77" {
    //          description "1568.77 nm/191.1003 THz 50/100Ghz spacing";
    //        }
    //        enum "1568.36" {
    //          description "1568.36 nm/191.15000 THz 6.25/12.5/50GHz spacing";
    //        }
    //        enum "1568.31" {
    //          description "1568.31 nm/191.15625 THz 6.25GHz spacing";
    //        }
    //        enum "1568.26" {
    //          description "1568.26 nm/191.16250 THz 6.25/12.5GHz spacing";
    //        }
    //        enum "1568.21" {
    //          description "1568.21 nm/191.16875 THz 6.25GHz spacing";
    //        }
    //        enum "1568.16" {
    //          description "1568.16 nm/191.17500 THz 6.25/12.5GHz spacing";
    //        }
    //        enum "1568.11" {
    //          description "1568.11 nm/191.18125 THz 6.25GHz spacing";
    //        }
    //        enum "1568.05" {
    //          description "1568.05 nm/191.18750 THz 6.25/12.5GHz spacing";
    //        }
    //        enum "1568.00" {
    //          description "1568.00 nm/191.19375 THz 6.25GHz spacing";
    //        }
    //        enum "1567.95" {
    //          description "1567.95 nm/191.20000 THz 6.25/12.5/50/100GHz spacing";
    //        }
    //        enum "1567.90" {
    //          description "1567.90 nm/191.20625 THz 6.25GHz spacing";
    //        }
    //        enum "1567.85" {
    //          description "1567.85 nm/191.21250 THz 6.25/12.5GHz spacing";
    //        }
    //        enum "1567.80" {
    //          description "1567.80 nm/191.21875 THz 6.25GHz spacing";
    //        }
    //        enum "1567.75" {
    //          description "1567.75 nm/191.22500 THz 6.25/12.5GHz spacing";
    //        }
    //        enum "1567.70" {
    //          description "1567.70 nm/191.23125 THz 6.25GHz spacing";
    //        }
    //        enum "1567.64" {
    //          description "1567.64 nm/191.23750 THz 6.25/12.5GHz spacing";
    //        }
    //        enum "1567.59" {
    //          description "1567.59 nm/191.24375 THz 6.25GHz spacing";
    //        }
    //        enum "1567.54" {
    //          description "1567.54 nm/191.25000 THz 6.25/12.5/50GHz spacing";
    //        }
    //        enum "1567.49" {
    //          description "1567.49 nm/191.25625 THz 6.25GHz spacing";
    //        }
    //        enum "1567.44" {
    //          description "1567.44 nm/191.26250 THz 6.25/12.5GHz spacing";
    //        }
    //        enum "1567.39" {
    //          description "1567.39 nm/191.26875 THz 6.25GHz spacing";
    //        }
    //        enum "1567.34" {
    //          description "1567.34 nm/191.27500 THz 6.25/12.5GHz spacing";
    //        }
    //        enum "1567.29" {
    //          description "1567.29 nm/191.28125 THz 6.25GHz spacing";
    //        }
    //        enum "1567.23" {
    //          description "1567.23 nm/191.28750 THz 6.25/12.5GHz spacing";
    //        }
    //        enum "1567.18" {
    //          description "1567.18 nm/191.29375 THz 6.25GHz spacing";
    //        }
    //        enum "1567.13" {
    //          description "1567.13 nm/191.30000 THz 6.25/12.5/50/100GHz spacing";
    //        }
    //        enum "1567.08" {
    //          description "1567.08 nm/191.30625 THz 6.25GHz spacing";
    //        }
    //        enum "1567.03" {
    //          description "1567.03 nm/191.31250 THz 6.25/12.5GHz spacing";
    //        }
    //        enum "1566.98" {
    //          description "1566.98 nm/191.31875 THz 6.25GHz spacing";
    //        }
    //        enum "1566.93" {
    //          description "1566.93 nm/191.32500 THz 6.25/12.5GHz spacing";
    //        }
    //        enum "1566.88" {
    //          description "1566.88 nm/191.33125 THz 6.25GHz spacing";
    //        }
    //        enum "1566.83" {
    //          description "1566.83 nm/191.33750 THz 6.25/12.5GHz spacing";
    //        }
    //        enum "1566.77" {
    //          description "1566.77 nm/191.34375 THz 6.25GHz spacing";
    //        }
    //        enum "1566.72" {
    //          description "1566.72 nm/191.35000 THz 6.25/12.5/50GHz spacing";
    //        }
    //        enum "1566.67" {
    //          description "1566.67 nm/191.35625 THz 6.25GHz spacing";
    //        }
    //        enum "1566.62" {
    //          description "1566.62 nm/191.36250 THz 6.25/12.5GHz spacing";
    //        }
    //        enum "1566.57" {
    //          description "1566.57 nm/191.36875 THz 6.25GHz spacing";
    //        }
    //        enum "1566.52" {
    //          description "1566.52 nm/191.37500 THz 6.25/12.5/75GHz spacing";
    //        }
    //        enum "1566.47" {
    //          description "1566.47 nm/191.38125 THz 6.25GHz spacing";
    //        }
    //        enum "1566.42" {
    //          description "1566.42 nm/191.38750 THz 6.25/12.5GHz spacing";
    //        }
    //        enum "1566.36" {
    //          description "1566.36 nm/191.39375 THz 6.25GHz spacing";
    //        }
    //        enum "1566.31" {
    //          description "1566.31 nm/191.40000 THz 6.25/12.5/50/100GHz spacing";
    //        }
    //        enum "1566.26" {
    //          description "1566.26 nm/191.40625 THz 6.25GHz spacing";
    //        }
    //        enum "1566.21" {
    //          description "1566.21 nm/191.41250 THz 6.25/12.5GHz spacing";
    //        }
    //        enum "1566.16" {
    //          description "1566.16 nm/191.41875 THz 6.25GHz spacing";
    //        }
    //        enum "1566.11" {
    //          description "1566.11 nm/191.42500 THz 6.25/12.5GHz spacing";
    //        }
    //        enum "1566.06" {
    //          description "1566.06 nm/191.43125 THz 6.25GHz spacing";
    //        }
    //        enum "1566.01" {
    //          description "1566.01 nm/191.43750 THz 6.25/12.5GHz spacing";
    //        }
    //        enum "1565.96" {
    //          description "1565.96 nm/191.44375 THz 6.25GHz spacing";
    //        }
    //        enum "1565.90" {
    //          description "1565.90 nm/191.45000 THz 6.25/12.5/50/75GHz spacing";
    //        }
    //        enum "1565.85" {
    //          description "1565.85 nm/191.45625 THz 6.25GHz spacing";
    //        }
    //        enum "1565.80" {
    //          description "1565.80 nm/191.46250 THz 6.25/12.5GHz spacing";
    //        }
    //        enum "1565.75" {
    //          description "1565.75 nm/191.46875 THz 6.25GHz spacing";
    //        }
    //        enum "1565.70" {
    //          description "1565.70 nm/191.47500 THz 6.25/12.5GHz spacing";
    //        }
    //        enum "1565.65" {
    //          description "1565.65 nm/191.48125 THz 6.25GHz spacing";
    //        }
    //        enum "1565.60" {
    //          description "1565.60 nm/191.48750 THz 6.25/12.5GHz spacing";
    //        }
    //        enum "1565.55" {
    //          description "1565.55 nm/191.49375 THz 6.25GHz spacing";
    //        }
    //        enum "1565.50" {
    //          description "1565.50 nm/191.50000 THz 6.25/12.5/50/100GHz spacing";
    //        }
    //        enum "1565.44" {
    //          description "1565.44 nm/191.50625 THz 6.25GHz spacing";
    //        }
    //        enum "1565.39" {
    //          description "1565.39 nm/191.51250 THz 6.25/12.5GHz spacing";
    //        }
    //        enum "1565.34" {
    //          description "1565.34 nm/191.51875 THz 6.25GHz spacing";
    //        }
    //        enum "1565.29" {
    //          description "1565.29 nm/191.52500 THz 6.25/12.5/75GHz spacing";
    //        }
    //        enum "1565.24" {
    //          description "1565.24 nm/191.53125 THz 6.25GHz spacing";
    //        }
    //        enum "1565.19" {
    //          description "1565.19 nm/191.53750 THz 6.25/12.5GHz spacing";
    //        }
    //        enum "1565.14" {
    //          description "1565.14 nm/191.54375 THz 6.25GHz spacing";
    //        }
    //        enum "1565.09" {
    //          description "1565.09 nm/191.55000 THz 6.25/12.5/50GHz spacing";
    //        }
    //        enum "1565.04" {
    //          description "1565.04 nm/191.55625 THz 6.25GHz spacing";
    //        }
    //        enum "1564.99" {
    //          description "1564.99 nm/191.56250 THz 6.25/12.5GHz spacing";
    //        }
    //        enum "1564.93" {
    //          description "1564.93 nm/191.56875 THz 6.25GHz spacing";
    //        }
    //        enum "1564.88" {
    //          description "1564.88 nm/191.57500 THz 6.25/12.5GHz spacing";
    //        }
    //        enum "1564.83" {
    //          description "1564.83 nm/191.58125 THz 6.25GHz spacing";
    //        }
    //        enum "1564.78" {
    //          description "1564.78 nm/191.58750 THz 6.25/12.5GHz spacing";
    //        }
    //        enum "1564.73" {
    //          description "1564.73 nm/191.59375 THz 6.25GHz spacing";
    //        }
    //        enum "1564.68" {
    //          description "1564.68 nm/191.60000 THz 6.25/12.5/50/75/100GHz spacing";
    //        }
    //        enum "1564.63" {
    //          description "1564.63 nm/191.60625 THz 6.25GHz spacing";
    //        }
    //        enum "1564.58" {
    //          description "1564.58 nm/191.61250 THz 6.25/12.5GHz spacing";
    //        }
    //        enum "1564.53" {
    //          description "1564.53 nm/191.61875 THz 6.25GHz spacing";
    //        }
    //        enum "1564.47" {
    //          description "1564.47 nm/191.62500 THz 6.25/12.5GHz spacing";
    //        }
    //        enum "1564.42" {
    //          description "1564.42 nm/191.63125 THz 6.25GHz spacing";
    //        }
    //        enum "1564.37" {
    //          description "1564.37 nm/191.63750 THz 6.25/12.5GHz spacing";
    //        }
    //        enum "1564.32" {
    //          description "1564.32 nm/191.64375 THz 6.25GHz spacing";
    //        }
    //        enum "1564.27" {
    //          description "1564.27 nm/191.65000 THz 6.25/12.5/50GHz spacing";
    //        }
    //        enum "1564.22" {
    //          description "1564.22 nm/191.65625 THz 6.25GHz spacing";
    //        }
    //        enum "1564.17" {
    //          description "1564.17 nm/191.66250 THz 6.25/12.5GHz spacing";
    //        }
    //        enum "1564.12" {
    //          description "1564.12 nm/191.66875 THz 6.25GHz spacing";
    //        }
    //        enum "1564.07" {
    //          description "1564.07 nm/191.67500 THz 6.25/12.5/75GHz spacing";
    //        }
    //        enum "1564.02" {
    //          description "1564.02 nm/191.68125 THz 6.25GHz spacing";
    //        }
    //        enum "1563.96" {
    //          description "1563.96 nm/191.68750 THz 6.25/12.5GHz spacing";
    //        }
    //        enum "1563.91" {
    //          description "1563.91 nm/191.69375 THz 6.25GHz spacing";
    //        }
    //        enum "1563.86" {
    //          description "1563.86 nm/191.70000 THz 6.25/12.5/50/100GHz spacing";
    //        }
    //        enum "1563.81" {
    //          description "1563.81 nm/191.70625 THz 6.25GHz spacing";
    //        }
    //        enum "1563.76" {
    //          description "1563.76 nm/191.71250 THz 6.25/12.5GHz spacing";
    //        }
    //        enum "1563.71" {
    //          description "1563.71 nm/191.71875 THz 6.25GHz spacing";
    //        }
    //        enum "1563.66" {
    //          description "1563.66 nm/191.72500 THz 6.25/12.5GHz spacing";
    //        }
    //        enum "1563.61" {
    //          description "1563.61 nm/191.73125 THz 6.25GHz spacing";
    //        }
    //        enum "1563.56" {
    //          description "1563.56 nm/191.73750 THz 6.25/12.5GHz spacing";
    //        }
    //        enum "1563.51" {
    //          description "1563.51 nm/191.74375 THz 6.25GHz spacing";
    //        }
    //        enum "1563.45" {
    //          description "1563.45 nm/191.75000 THz 6.25/12.5/50/75GHz spacing";
    //        }
    //        enum "1563.40" {
    //          description "1563.40 nm/191.75625 THz 6.25GHz spacing";
    //        }
    //        enum "1563.35" {
    //          description "1563.35 nm/191.76250 THz 6.25/12.5GHz spacing";
    //        }
    //        enum "1563.30" {
    //          description "1563.30 nm/191.76875 THz 6.25GHz spacing";
    //        }
    //        enum "1563.25" {
    //          description "1563.25 nm/191.77500 THz 6.25/12.5GHz spacing";
    //        }
    //        enum "1563.20" {
    //          description "1563.20 nm/191.78125 THz 6.25GHz spacing";
    //        }
    //        enum "1563.15" {
    //          description "1563.15 nm/191.78750 THz 6.25/12.5GHz spacing";
    //        }
    //        enum "1563.10" {
    //          description "1563.10 nm/191.79375 THz 6.25GHz spacing";
    //        }
    //        enum "1563.05" {
    //          description "1563.05 nm/191.80000 THz 6.25/12.5/50/100GHz spacing";
    //        }
    //        enum "1563.00" {
    //          description "1563.00 nm/191.80625 THz 6.25GHz spacing";
    //        }
    //        enum "1562.95" {
    //          description "1562.95 nm/191.81250 THz 6.25/12.5GHz spacing";
    //        }
    //        enum "1562.89" {
    //          description "1562.89 nm/191.81875 THz 6.25GHz spacing";
    //        }
    //        enum "1562.84" {
    //          description "1562.84 nm/191.82500 THz 6.25/12.5/75GHz spacing";
    //        }
    //        enum "1562.79" {
    //          description "1562.79 nm/191.83125 THz 6.25GHz spacing";
    //        }
    //        enum "1562.74" {
    //          description "1562.74 nm/191.83750 THz 6.25/12.5GHz spacing";
    //        }
    //        enum "1562.69" {
    //          description "1562.69 nm/191.84375 THz 6.25GHz spacing";
    //        }
    //        enum "1562.64" {
    //          description "1562.64 nm/191.85000 THz 6.25/12.5/50GHz spacing";
    //        }
    //        enum "1562.59" {
    //          description "1562.59 nm/191.85625 THz 6.25GHz spacing";
    //        }
    //        enum "1562.54" {
    //          description "1562.54 nm/191.86250 THz 6.25/12.5GHz spacing";
    //        }
    //        enum "1562.49" {
    //          description "1562.49 nm/191.86875 THz 6.25GHz spacing";
    //        }
    //        enum "1562.44" {
    //          description "1562.44 nm/191.87500 THz 6.25/12.5GHz spacing";
    //        }
    //        enum "1562.39" {
    //          description "1562.39 nm/191.88125 THz 6.25GHz spacing";
    //        }
    //        enum "1562.33" {
    //          description "1562.33 nm/191.88750 THz 6.25/12.5GHz spacing";
    //        }
    //        enum "1562.28" {
    //          description "1562.28 nm/191.89375 THz 6.25GHz spacing";
    //        }
    //        enum "1562.23" {
    //          description "1562.23 nm/191.90000 THz 6.25/12.5/50/75/100GHz spacing";
    //        }
    //        enum "1562.18" {
    //          description "1562.18 nm/191.90625 THz 6.25GHz spacing";
    //        }
    //        enum "1562.13" {
    //          description "1562.13 nm/191.91250 THz 6.25/12.5GHz spacing";
    //        }
    //        enum "1562.08" {
    //          description "1562.08 nm/191.91875 THz 6.25GHz spacing";
    //        }
    //        enum "1562.03" {
    //          description "1562.03 nm/191.92500 THz 6.25/12.5GHz spacing";
    //        }
    //        enum "1561.98" {
    //          description "1561.98 nm/191.93125 THz 6.25GHz spacing";
    //        }
    //        enum "1561.93" {
    //          description "1561.93 nm/191.93750 THz 6.25/12.5GHz spacing";
    //        }
    //        enum "1561.88" {
    //          description "1561.88 nm/191.94375 THz 6.25GHz spacing";
    //        }
    //        enum "1561.83" {
    //          description "1561.83 nm/191.95000 THz 6.25/12.5/50GHz spacing";
    //        }
    //        enum "1561.77" {
    //          description "1561.77 nm/191.95625 THz 6.25GHz spacing";
    //        }
    //        enum "1561.72" {
    //          description "1561.72 nm/191.96250 THz 6.25/12.5GHz spacing";
    //        }
    //        enum "1561.67" {
    //          description "1561.67 nm/191.96875 THz 6.25GHz spacing";
    //        }
    //        enum "1561.62" {
    //          description "1561.62 nm/191.97500 THz 6.25/12.5/75GHz spacing";
    //        }
    //        enum "1561.57" {
    //          description "1561.57 nm/191.98125 THz 6.25GHz spacing";
    //        }
    //        enum "1561.52" {
    //          description "1561.52 nm/191.98750 THz 6.25/12.5GHz spacing";
    //        }
    //        enum "1561.47" {
    //          description "1561.47 nm/191.99375 THz 6.25GHz spacing";
    //        }
    //        enum "1561.42" {
    //          description "1561.42 nm/192.00000 THz 6.25/12.5/50/100GHz spacing";
    //        }
    //        enum "1561.37" {
    //          description "1561.37 nm/192.00625 THz 6.25GHz spacing";
    //        }
    //        enum "1561.32" {
    //          description "1561.32 nm/192.01250 THz 6.25/12.5GHz spacing";
    //        }
    //        enum "1561.27" {
    //          description "1561.27 nm/192.01875 THz 6.25GHz spacing";
    //        }
    //        enum "1561.22" {
    //          description "1561.22 nm/192.02500 THz 6.25/12.5GHz spacing";
    //        }
    //        enum "1561.16" {
    //          description "1561.16 nm/192.03125 THz 6.25GHz spacing";
    //        }
    //        enum "1561.11" {
    //          description "1561.11 nm/192.03750 THz 6.25/12.5GHz spacing";
    //        }
    //        enum "1561.06" {
    //          description "1561.06 nm/192.04375 THz 6.25GHz spacing";
    //        }
    //        enum "1561.01" {
    //          description "1561.01 nm/192.05000 THz 6.25/12.5/50G/75Hz spacing";
    //        }
    //        enum "1560.96" {
    //          description "1560.96 nm/192.05625 THz 6.25GHz spacing";
    //        }
    //        enum "1560.91" {
    //          description "1560.91 nm/192.06250 THz 6.25/12.5GHz spacing";
    //        }
    //        enum "1560.86" {
    //          description "1560.86 nm/192.06875 THz 6.25GHz spacing";
    //        }
    //        enum "1560.81" {
    //          description "1560.81 nm/192.07500 THz 6.25/12.5GHz spacing";
    //        }
    //        enum "1560.76" {
    //          description "1560.76 nm/192.08125 THz 6.25GHz spacing";
    //        }
    //        enum "1560.71" {
    //          description "1560.71 nm/192.08750 THz 6.25/12.5GHz spacing";
    //        }
    //        enum "1560.66" {
    //          description "1560.66 nm/192.09375 THz 6.25GHz spacing";
    //        }
    //        enum "1560.61" {
    //          description "1560.61 nm/192.10000 THz 6.25/12.5/50/100GHz spacing";
    //        }
    //        enum "1560.56" {
    //          description "1560.56 nm/192.10625 THz 6.25GHz spacing";
    //        }
    //        enum "1560.50" {
    //          description "1560.50 nm/192.11250 THz 6.25/12.5GHz spacing";
    //        }
    //        enum "1560.45" {
    //          description "1560.45 nm/192.11875 THz 6.25GHz spacing";
    //        }
    //        enum "1560.40" {
    //          description "1560.40 nm/192.12500 THz 6.25/12.5/75GHz spacing";
    //        }
    //        enum "1560.35" {
    //          description "1560.35 nm/192.13125 THz 6.25GHz spacing";
    //        }
    //        enum "1560.30" {
    //          description "1560.30 nm/192.13750 THz 6.25/12.5GHz spacing";
    //        }
    //        enum "1560.25" {
    //          description "1560.25 nm/192.14375 THz 6.25GHz spacing";
    //        }
    //        enum "1560.20" {
    //          description "1560.20 nm/192.15000 THz 6.25/12.5/50GHz spacing";
    //        }
    //        enum "1560.15" {
    //          description "1560.15 nm/192.15625 THz 6.25GHz spacing";
    //        }
    //        enum "1560.10" {
    //          description "1560.10 nm/192.16250 THz 6.25/12.5GHz spacing";
    //        }
    //        enum "1560.05" {
    //          description "1560.05 nm/192.16875 THz 6.25GHz spacing";
    //        }
    //        enum "1560.00" {
    //          description "1560.00 nm/192.17500 THz 6.25/12.5GHz spacing";
    //        }
    //        enum "1559.95" {
    //          description "1559.95 nm/192.18125 THz 6.25GHz spacing";
    //        }
    //        enum "1559.90" {
    //          description "1559.90 nm/192.18750 THz 6.25/12.5GHz spacing";
    //        }
    //        enum "1559.84" {
    //          description "1559.84 nm/192.19375 THz 6.25GHz spacing";
    //        }
    //        enum "1559.79" {
    //          description "1559.79 nm/192.20000 THz 6.25/12.5/50/75/100GHz spacing";
    //        }
    //        enum "1559.74" {
    //          description "1559.74 nm/192.20625 THz 6.25GHz spacing";
    //        }
    //        enum "1559.69" {
    //          description "1559.69 nm/192.21250 THz 6.25/12.5GHz spacing";
    //        }
    //        enum "1559.64" {
    //          description "1559.64 nm/192.21875 THz 6.25GHz spacing";
    //        }
    //        enum "1559.59" {
    //          description "1559.59 nm/192.22500 THz 6.25/12.5GHz spacing";
    //        }
    //        enum "1559.54" {
    //          description "1559.54 nm/192.23125 THz 6.25GHz spacing";
    //        }
    //        enum "1559.49" {
    //          description "1559.49 nm/192.23750 THz 6.25/12.5GHz spacing";
    //        }
    //        enum "1559.44" {
    //          description "1559.44 nm/192.24375 THz 6.25GHz spacing";
    //        }
    //        enum "1559.39" {
    //          description "1559.39 nm/192.25000 THz 6.25/12.5/50GHz spacing";
    //        }
    //        enum "1559.34" {
    //          description "1559.34 nm/192.25625 THz 6.25GHz spacing";
    //        }
    //        enum "1559.29" {
    //          description "1559.29 nm/192.26250 THz 6.25/12.5GHz spacing";
    //        }
    //        enum "1559.24" {
    //          description "1559.24 nm/192.26875 THz 6.25GHz spacing";
    //        }
    //        enum "1559.19" {
    //          description "1559.19 nm/192.27500 THz 6.25/12.5/75GHz spacing";
    //        }
    //        enum "1559.14" {
    //          description "1559.14 nm/192.28125 THz 6.25GHz spacing";
    //        }
    //        enum "1559.08" {
    //          description "1559.08 nm/192.28750 THz 6.25/12.5GHz spacing";
    //        }
    //        enum "1559.03" {
    //          description "1559.03 nm/192.29375 THz 6.25GHz spacing";
    //        }
    //        enum "1558.98" {
    //          description "1558.98 nm/192.30000 THz 6.25/12.5/50/100GHz spacing";
    //        }
    //        enum "1558.93" {
    //          description "1558.93 nm/192.30625 THz 6.25GHz spacing";
    //        }
    //        enum "1558.88" {
    //          description "1558.88 nm/192.31250 THz 6.25/12.5GHz spacing";
    //        }
    //        enum "1558.83" {
    //          description "1558.83 nm/192.31875 THz 6.25GHz spacing";
    //        }
    //        enum "1558.78" {
    //          description "1558.78 nm/192.32500 THz 6.25/12.5GHz spacing";
    //        }
    //        enum "1558.73" {
    //          description "1558.73 nm/192.33125 THz 6.25GHz spacing";
    //        }
    //        enum "1558.68" {
    //          description "1558.68 nm/192.33750 THz 6.25/12.5GHz spacing";
    //        }
    //        enum "1558.63" {
    //          description "1558.63 nm/192.34375 THz 6.25GHz spacing";
    //        }
    //        enum "1558.58" {
    //          description "1558.58 nm/192.35000 THz 6.25/12.5/50/75GHz spacing";
    //        }
    //        enum "1558.53" {
    //          description "1558.53 nm/192.35625 THz 6.25GHz spacing";
    //        }
    //        enum "1558.48" {
    //          description "1558.48 nm/192.36250 THz 6.25/12.5GHz spacing";
    //        }
    //        enum "1558.43" {
    //          description "1558.43 nm/192.36875 THz 6.25GHz spacing";
    //        }
    //        enum "1558.38" {
    //          description "1558.38 nm/192.37500 THz 6.25/12.5GHz spacing";
    //        }
    //        enum "1558.32" {
    //          description "1558.32 nm/192.38125 THz 6.25GHz spacing";
    //        }
    //        enum "1558.27" {
    //          description "1558.27 nm/192.38750 THz 6.25/12.5GHz spacing";
    //        }
    //        enum "1558.22" {
    //          description "1558.22 nm/192.39375 THz 6.25GHz spacing";
    //        }
    //        enum "1558.17" {
    //          description "1558.17 nm/192.40000 THz 6.25/12.5/50/100GHz spacing";
    //        }
    //        enum "1558.12" {
    //          description "1558.12 nm/192.40625 THz 6.25GHz spacing";
    //        }
    //        enum "1558.07" {
    //          description "1558.07 nm/192.41250 THz 6.25/12.5GHz spacing";
    //        }
    //        enum "1558.02" {
    //          description "1558.02 nm/192.41875 THz 6.25GHz spacing";
    //        }
    //        enum "1557.97" {
    //          description "1557.97 nm/192.42500 THz 6.25/12.5/75GHz spacing";
    //        }
    //        enum "1557.92" {
    //          description "1557.92 nm/192.43125 THz 6.25GHz spacing";
    //        }
    //        enum "1557.87" {
    //          description "1557.87 nm/192.43750 THz 6.25/12.5GHz spacing";
    //        }
    //        enum "1557.82" {
    //          description "1557.82 nm/192.44375 THz 6.25GHz spacing";
    //        }
    //        enum "1557.77" {
    //          description "1557.77 nm/192.45000 THz 6.25/12.5/50GHz spacing";
    //        }
    //        enum "1557.72" {
    //          description "1557.72 nm/192.45625 THz 6.25GHz spacing";
    //        }
    //        enum "1557.67" {
    //          description "1557.67 nm/192.46250 THz 6.25/12.5GHz spacing";
    //        }
    //        enum "1557.62" {
    //          description "1557.62 nm/192.46875 THz 6.25GHz spacing";
    //        }
    //        enum "1557.57" {
    //          description "1557.57 nm/192.47500 THz 6.25/12.5GHz spacing";
    //        }
    //        enum "1557.52" {
    //          description "1557.52 nm/192.48125 THz 6.25GHz spacing";
    //        }
    //        enum "1557.46" {
    //          description "1557.46 nm/192.48750 THz 6.25/12.5GHz spacing";
    //        }
    //        enum "1557.41" {
    //          description "1557.41 nm/192.49375 THz 6.25GHz spacing";
    //        }
    //        enum "1557.36" {
    //          description "1557.36 nm/192.50000 THz 6.25/12.5/50/75/100GHz spacing";
    //        }
    //        enum "1557.31" {
    //          description "1557.31 nm/192.50625 THz 6.25GHz spacing";
    //        }
    //        enum "1557.26" {
    //          description "1557.26 nm/192.51250 THz 6.25/12.5GHz spacing";
    //        }
    //        enum "1557.21" {
    //          description "1557.21 nm/192.51875 THz 6.25GHz spacing";
    //        }
    //        enum "1557.16" {
    //          description "1557.16 nm/192.52500 THz 6.25/12.5GHz spacing";
    //        }
    //        enum "1557.11" {
    //          description "1557.11 nm/192.53125 THz 6.25GHz spacing";
    //        }
    //        enum "1557.06" {
    //          description "1557.06 nm/192.53750 THz 6.25/12.5GHz spacing";
    //        }
    //        enum "1557.01" {
    //          description "1557.01 nm/192.54375 THz 6.25GHz spacing";
    //        }
    //        enum "1556.96" {
    //          description "1556.96 nm/192.55000 THz 6.25/12.5/50GHz spacing";
    //        }
    //        enum "1556.91" {
    //          description "1556.91 nm/192.55625 THz 6.25GHz spacing";
    //        }
    //        enum "1556.86" {
    //          description "1556.86 nm/192.56250 THz 6.25/12.5GHz spacing";
    //        }
    //        enum "1556.81" {
    //          description "1556.81 nm/192.56875 THz 6.25GHz spacing";
    //        }
    //        enum "1556.76" {
    //          description "1556.76 nm/192.57500 THz 6.25/12.5/75GHz spacing";
    //        }
    //        enum "1556.71" {
    //          description "1556.71 nm/192.58125 THz 6.25GHz spacing";
    //        }
    //        enum "1556.66" {
    //          description "1556.66 nm/192.58750 THz 6.25/12.5GHz spacing";
    //        }
    //        enum "1556.61" {
    //          description "1556.61 nm/192.59375 THz 6.25GHz spacing";
    //        }
    //        enum "1556.55" {
    //          description "1556.55 nm/192.60000 THz 6.25/12.5/50/100GHz spacing";
    //        }
    //        enum "1556.50" {
    //          description "1556.50 nm/192.60625 THz 6.25GHz spacing";
    //        }
    //        enum "1556.45" {
    //          description "1556.45 nm/192.61250 THz 6.25/12.5GHz spacing";
    //        }
    //        enum "1556.40" {
    //          description "1556.40 nm/192.61875 THz 6.25GHz spacing";
    //        }
    //        enum "1556.35" {
    //          description "1556.35 nm/192.62500 THz 6.25/12.5GHz spacing";
    //        }
    //        enum "1556.30" {
    //          description "1556.30 nm/192.63125 THz 6.25GHz spacing";
    //        }
    //        enum "1556.25" {
    //          description "1556.25 nm/192.63750 THz 6.25/12.5GHz spacing";
    //        }
    //        enum "1556.20" {
    //          description "1556.20 nm/192.64375 THz 6.25GHz spacing";
    //        }
    //        enum "1556.15" {
    //          description "1556.15 nm/192.65000 THz 6.25/12.5/50/75GHz spacing";
    //        }
    //        enum "1556.10" {
    //          description "1556.10 nm/192.65625 THz 6.25GHz spacing";
    //        }
    //        enum "1556.05" {
    //          description "1556.05 nm/192.66250 THz 6.25/12.5GHz spacing";
    //        }
    //        enum "1556.00" {
    //          description "1556.00 nm/192.66875 THz 6.25GHz spacing";
    //        }
    //        enum "1555.95" {
    //          description "1555.95 nm/192.67500 THz 6.25/12.5GHz spacing";
    //        }
    //        enum "1555.90" {
    //          description "1555.90 nm/192.68125 THz 6.25GHz spacing";
    //        }
    //        enum "1555.85" {
    //          description "1555.85 nm/192.68750 THz 6.25/12.5GHz spacing";
    //        }
    //        enum "1555.80" {
    //          description "1555.80 nm/192.69375 THz 6.25GHz spacing";
    //        }
    //        enum "1555.75" {
    //          description "1555.75 nm/192.70000 THz 6.25/12.5/50/100GHz spacing";
    //        }
    //        enum "1555.70" {
    //          description "1555.70 nm/192.70625 THz 6.25GHz spacing";
    //        }
    //        enum "1555.65" {
    //          description "1555.65 nm/192.71250 THz 6.25/12.5GHz spacing";
    //        }
    //        enum "1555.60" {
    //          description "1555.60 nm/192.71875 THz 6.25GHz spacing";
    //        }
    //        enum "1555.55" {
    //          description "1555.55 nm/192.72500 THz 6.25/12.5/75GHz spacing";
    //        }
    //        enum "1555.49" {
    //          description "1555.49 nm/192.73125 THz 6.25GHz spacing";
    //        }
    //        enum "1555.44" {
    //          description "1555.44 nm/192.73750 THz 6.25/12.5GHz spacing";
    //        }
    //        enum "1555.39" {
    //          description "1555.39 nm/192.74375 THz 6.25GHz spacing";
    //        }
    //        enum "1555.34" {
    //          description "1555.34 nm/192.75000 THz 6.25/12.5/50GHz spacing";
    //        }
    //        enum "1555.29" {
    //          description "1555.29 nm/192.75625 THz 6.25GHz spacing";
    //        }
    //        enum "1555.24" {
    //          description "1555.24 nm/192.76250 THz 6.25/12.5GHz spacing";
    //        }
    //        enum "1555.19" {
    //          description "1555.19 nm/192.76875 THz 6.25GHz spacing";
    //        }
    //        enum "1555.14" {
    //          description "1555.14 nm/192.77500 THz 6.25/12.5GHz spacing";
    //        }
    //        enum "1555.09" {
    //          description "1555.09 nm/192.78125 THz 6.25GHz spacing";
    //        }
    //        enum "1555.04" {
    //          description "1555.04 nm/192.78750 THz 6.25/12.5GHz spacing";
    //        }
    //        enum "1554.99" {
    //          description "1554.99 nm/192.79375 THz 6.25GHz spacing";
    //        }
    //        enum "1554.94" {
    //          description "1554.94 nm/192.80000 THz 6.25/12.5/50/75/100GHz spacing";
    //        }
    //        enum "1554.89" {
    //          description "1554.89 nm/192.80625 THz 6.25GHz spacing";
    //        }
    //        enum "1554.84" {
    //          description "1554.84 nm/192.81250 THz 6.25/12.5GHz spacing";
    //        }
    //        enum "1554.79" {
    //          description "1554.79 nm/192.81875 THz 6.25GHz spacing";
    //        }
    //        enum "1554.74" {
    //          description "1554.74 nm/192.82500 THz 6.25/12.5GHz spacing";
    //        }
    //        enum "1554.69" {
    //          description "1554.69 nm/192.83125 THz 6.25GHz spacing";
    //        }
    //        enum "1554.64" {
    //          description "1554.64 nm/192.83750 THz 6.25/12.5GHz spacing";
    //        }
    //        enum "1554.59" {
    //          description "1554.59 nm/192.84375 THz 6.25GHz spacing";
    //        }
    //        enum "1554.54" {
    //          description "1554.54 nm/192.85000 THz 6.25/12.5/50GHz spacing";
    //        }
    //        enum "1554.49" {
    //          description "1554.49 nm/192.85625 THz 6.25GHz spacing";
    //        }
    //        enum "1554.44" {
    //          description "1554.44 nm/192.86250 THz 6.25/12.5GHz spacing";
    //        }
    //        enum "1554.39" {
    //          description "1554.39 nm/192.86875 THz 6.25GHz spacing";
    //        }
    //        enum "1554.34" {
    //          description "1554.34 nm/192.87500 THz 6.25/12.5/75GHz spacing";
    //        }
    //        enum "1554.29" {
    //          description "1554.29 nm/192.88125 THz 6.25GHz spacing";
    //        }
    //        enum "1554.23" {
    //          description "1554.23 nm/192.88750 THz 6.25/12.5GHz spacing";
    //        }
    //        enum "1554.18" {
    //          description "1554.18 nm/192.89375 THz 6.25GHz spacing";
    //        }
    //        enum "1554.13" {
    //          description "1554.13 nm/192.90000 THz 6.25/12.5/50/100GHz spacing";
    //        }
    //        enum "1554.08" {
    //          description "1554.08 nm/192.90625 THz 6.25GHz spacing";
    //        }
    //        enum "1554.03" {
    //          description "1554.03 nm/192.91250 THz 6.25/12.5GHz spacing";
    //        }
    //        enum "1553.98" {
    //          description "1553.98 nm/192.91875 THz 6.25GHz spacing";
    //        }
    //        enum "1553.93" {
    //          description "1553.93 nm/192.92500 THz 6.25/12.5GHz spacing";
    //        }
    //        enum "1553.88" {
    //          description "1553.88 nm/192.93125 THz 6.25GHz spacing";
    //        }
    //        enum "1553.83" {
    //          description "1553.83 nm/192.93750 THz 6.25/12.5GHz spacing";
    //        }
    //        enum "1553.78" {
    //          description "1553.78 nm/192.94375 THz 6.25GHz spacing";
    //        }
    //        enum "1553.73" {
    //          description "1553.73 nm/192.95000 THz 6.25/12.5/50/75GHz spacing";
    //        }
    //        enum "1553.68" {
    //          description "1553.68 nm/192.95625 THz 6.25GHz spacing";
    //        }
    //        enum "1553.63" {
    //          description "1553.63 nm/192.96250 THz 6.25/12.5GHz spacing";
    //        }
    //        enum "1553.58" {
    //          description "1553.58 nm/192.96875 THz 6.25GHz spacing";
    //        }
    //        enum "1553.53" {
    //          description "1553.53 nm/192.97500 THz 6.25/12.5GHz spacing";
    //        }
    //        enum "1553.48" {
    //          description "1553.48 nm/192.98125 THz 6.25GHz spacing";
    //        }
    //        enum "1553.43" {
    //          description "1553.43 nm/192.98750 THz 6.25/12.5GHz spacing";
    //        }
    //        enum "1553.38" {
    //          description "1553.38 nm/192.99375 THz 6.25GHz spacing";
    //        }
    //        enum "1553.33" {
    //          description "1553.33 nm/193.00000 THz 6.25/12.5/50/100GHz spacing";
    //        }
    //        enum "1553.28" {
    //          description "1553.28 nm/193.00625 THz 6.25GHz spacing";
    //        }
    //        enum "1553.23" {
    //          description "1553.23 nm/193.01250 THz 6.25/12.5GHz spacing";
    //        }
    //        enum "1553.18" {
    //          description "1553.18 nm/193.01875 THz 6.25GHz spacing";
    //        }
    //        enum "1553.13" {
    //          description "1553.13 nm/193.02500 THz 6.25/12.5/75GHz spacing";
    //        }
    //        enum "1553.08" {
    //          description "1553.08 nm/193.03125 THz 6.25GHz spacing";
    //        }
    //        enum "1553.03" {
    //          description "1553.03 nm/193.03750 THz 6.25/12.5GHz spacing";
    //        }
    //        enum "1552.98" {
    //          description "1552.98 nm/193.04375 THz 6.25GHz spacing";
    //        }
    //        enum "1552.93" {
    //          description "1552.93 nm/193.05000 THz 6.25/12.5/50GHz spacing";
    //        }
    //        enum "1552.88" {
    //          description "1552.88 nm/193.05625 THz 6.25GHz spacing";
    //        }
    //        enum "1552.83" {
    //          description "1552.83 nm/193.06250 THz 6.25/12.5GHz spacing";
    //        }
    //        enum "1552.78" {
    //          description "1552.78 nm/193.06875 THz 6.25GHz spacing";
    //        }
    //        enum "1552.73" {
    //          description "1552.73 nm/193.07500 THz 6.25/12.5GHz spacing";
    //        }
    //        enum "1552.68" {
    //          description "1552.68 nm/193.08125 THz 6.25GHz spacing";
    //        }
    //        enum "1552.62" {
    //          description "1552.62 nm/193.08750 THz 6.25/12.5GHz spacing";
    //        }
    //        enum "1552.57" {
    //          description "1552.57 nm/193.09375 THz 6.25GHz spacing";
    //        }
    //        enum "1552.52" {
    //          description "1552.52 nm/193.10000 THz 6.25/12.5/50/75/100GHz spacing";
    //        }
    //        enum "1552.47" {
    //          description "1552.47 nm/193.10625 THz 6.25GHz spacing";
    //        }
    //        enum "1552.42" {
    //          description "1552.42 nm/193.11250 THz 6.25/12.5GHz spacing";
    //        }
    //        enum "1552.37" {
    //          description "1552.37 nm/193.11875 THz 6.25GHz spacing";
    //        }
    //        enum "1552.32" {
    //          description "1552.32 nm/193.12500 THz 6.25/12.5GHz spacing";
    //        }
    //        enum "1552.27" {
    //          description "1552.27 nm/193.13125 THz 6.25GHz spacing";
    //        }
    //        enum "1552.22" {
    //          description "1552.22 nm/193.13750 THz 6.25/12.5GHz spacing";
    //        }
    //        enum "1552.17" {
    //          description "1552.17 nm/193.14375 THz 6.25GHz spacing";
    //        }
    //        enum "1552.12" {
    //          description "1552.12 nm/193.15000 THz 6.25/12.5/50GHz spacing";
    //        }
    //        enum "1552.07" {
    //          description "1552.07 nm/193.15625 THz 6.25GHz spacing";
    //        }
    //        enum "1552.02" {
    //          description "1552.02 nm/193.16250 THz 6.25/12.5GHz spacing";
    //        }
    //        enum "1551.97" {
    //          description "1551.97 nm/193.16875 THz 6.25GHz spacing";
    //        }
    //        enum "1551.92" {
    //          description "1551.92 nm/193.17500 THz 6.25/12.5/75GHz spacing";
    //        }
    //        enum "1551.87" {
    //          description "1551.87 nm/193.18125 THz 6.25GHz spacing";
    //        }
    //        enum "1551.82" {
    //          description "1551.82 nm/193.18750 THz 6.25/12.5GHz spacing";
    //        }
    //        enum "1551.77" {
    //          description "1551.77 nm/193.19375 THz 6.25GHz spacing";
    //        }
    //        enum "1551.72" {
    //          description "1551.72 nm/193.20000 THz 6.25/12.5/50/100GHz spacing";
    //        }
    //        enum "1551.67" {
    //          description "1551.67 nm/193.20625 THz 6.25GHz spacing";
    //        }
    //        enum "1551.62" {
    //          description "1551.62 nm/193.21250 THz 6.25/12.5GHz spacing";
    //        }
    //        enum "1551.57" {
    //          description "1551.57 nm/193.21875 THz 6.25GHz spacing";
    //        }
    //        enum "1551.52" {
    //          description "1551.52 nm/193.22500 THz 6.25/12.5GHz spacing";
    //        }
    //        enum "1551.47" {
    //          description "1551.47 nm/193.23125 THz 6.25GHz spacing";
    //        }
    //        enum "1551.42" {
    //          description "1551.42 nm/193.23750 THz 6.25/12.5GHz spacing";
    //        }
    //        enum "1551.37" {
    //          description "1551.37 nm/193.24375 THz 6.25GHz spacing";
    //        }
    //        enum "1551.32" {
    //          description "1551.32 nm/193.25000 THz 6.25/12.5/50/75GHz spacing";
    //        }
    //        enum "1551.27" {
    //          description "1551.27 nm/193.25625 THz 6.25GHz spacing";
    //        }
    //        enum "1551.22" {
    //          description "1551.22 nm/193.26250 THz 6.25/12.5GHz spacing";
    //        }
    //        enum "1551.17" {
    //          description "1551.17 nm/193.26875 THz 6.25GHz spacing";
    //        }
    //        enum "1551.12" {
    //          description "1551.12 nm/193.27500 THz 6.25/12.5GHz spacing";
    //        }
    //        enum "1551.07" {
    //          description "1551.07 nm/193.28125 THz 6.25GHz spacing";
    //        }
    //        enum "1551.02" {
    //          description "1551.02 nm/193.28750 THz 6.25/12.5GHz spacing";
    //        }
    //        enum "1550.97" {
    //          description "1550.97 nm/193.29375 THz 6.25GHz spacing";
    //        }
    //        enum "1550.92" {
    //          description "1550.92 nm/193.30000 THz 6.25/12.5/50/100GHz spacing";
    //        }
    //        enum "1550.87" {
    //          description "1550.87 nm/193.30625 THz 6.25GHz spacing";
    //        }
    //        enum "1550.82" {
    //          description "1550.82 nm/193.31250 THz 6.25/12.5GHz spacing";
    //        }
    //        enum "1550.77" {
    //          description "1550.77 nm/193.31875 THz 6.25GHz spacing";
    //        }
    //        enum "1550.72" {
    //          description "1550.72 nm/193.32500 THz 6.25/12.5/75GHz spacing";
    //        }
    //        enum "1550.67" {
    //          description "1550.67 nm/193.33125 THz 6.25GHz spacing";
    //        }
    //        enum "1550.62" {
    //          description "1550.62 nm/193.33750 THz 6.25/12.5GHz spacing";
    //        }
    //        enum "1550.57" {
    //          description "1550.57 nm/193.34375 THz 6.25GHz spacing";
    //        }
    //        enum "1550.52" {
    //          description "1550.52 nm/193.35000 THz 6.25/12.5/50GHz spacing";
    //        }
    //        enum "1550.47" {
    //          description "1550.47 nm/193.35625 THz 6.25GHz spacing";
    //        }
    //        enum "1550.42" {
    //          description "1550.42 nm/193.36250 THz 6.25/12.5GHz spacing";
    //        }
    //        enum "1550.37" {
    //          description "1550.37 nm/193.36875 THz 6.25GHz spacing";
    //        }
    //        enum "1550.32" {
    //          description "1550.32 nm/193.37500 THz 6.25/12.5GHz spacing";
    //        }
    //        enum "1550.27" {
    //          description "1550.27 nm/193.38125 THz 6.25GHz spacing";
    //        }
    //        enum "1550.22" {
    //          description "1550.22 nm/193.38750 THz 6.25/12.5GHz spacing";
    //        }
    //        enum "1550.17" {
    //          description "1550.17 nm/193.39375 THz 6.25GHz spacing";
    //        }
    //        enum "1550.12" {
    //          description "1550.12 nm/193.40000 THz 6.25/12.5/50/75/100GHz spacing";
    //        }
    //        enum "1550.07" {
    //          description "1550.07 nm/193.40625 THz 6.25GHz spacing";
    //        }
    //        enum "1550.02" {
    //          description "1550.02 nm/193.41250 THz 6.25/12.5GHz spacing";
    //        }
    //        enum "1549.97" {
    //          description "1549.97 nm/193.41875 THz 6.25GHz spacing";
    //        }
    //        enum "1549.92" {
    //          description "1549.92 nm/193.42500 THz 6.25/12.5GHz spacing";
    //        }
    //        enum "1549.87" {
    //          description "1549.87 nm/193.43125 THz 6.25GHz spacing";
    //        }
    //        enum "1549.82" {
    //          description "1549.82 nm/193.43750 THz 6.25/12.5GHz spacing";
    //        }
    //        enum "1549.77" {
    //          description "1549.77 nm/193.44375 THz 6.25GHz spacing";
    //        }
    //        enum "1549.72" {
    //          description "1549.72 nm/193.45000 THz 6.25/12.5/50GHz spacing";
    //        }
    //        enum "1549.67" {
    //          description "1549.67 nm/193.45625 THz 6.25GHz spacing";
    //        }
    //        enum "1549.62" {
    //          description "1549.62 nm/193.46250 THz 6.25/12.5GHz spacing";
    //        }
    //        enum "1549.57" {
    //          description "1549.57 nm/193.46875 THz 6.25GHz spacing";
    //        }
    //        enum "1549.52" {
    //          description "1549.52 nm/193.47500 THz 6.25/12.5/75GHz spacing";
    //        }
    //        enum "1549.47" {
    //          description "1549.47 nm/193.48125 THz 6.25GHz spacing";
    //        }
    //        enum "1549.42" {
    //          description "1549.42 nm/193.48750 THz 6.25/12.5GHz spacing";
    //        }
    //        enum "1549.37" {
    //          description "1549.37 nm/193.49375 THz 6.25GHz spacing";
    //        }
    //        enum "1549.32" {
    //          description "1549.32 nm/193.50000 THz 6.25/12.5/50/100GHz spacing";
    //        }
    //        enum "1549.26" {
    //          description "1549.26 nm/193.50625 THz 6.25GHz spacing";
    //        }
    //        enum "1549.21" {
    //          description "1549.21 nm/193.51250 THz 6.25/12.5GHz spacing";
    //        }
    //        enum "1549.16" {
    //          description "1549.16 nm/193.51875 THz 6.25GHz spacing";
    //        }
    //        enum "1549.11" {
    //          description "1549.11 nm/193.52500 THz 6.25/12.5GHz spacing";
    //        }
    //        enum "1549.06" {
    //          description "1549.06 nm/193.53125 THz 6.25GHz spacing";
    //        }
    //        enum "1549.01" {
    //          description "1549.01 nm/193.53750 THz 6.25/12.5GHz spacing";
    //        }
    //        enum "1548.96" {
    //          description "1548.96 nm/193.54375 THz 6.25GHz spacing";
    //        }
    //        enum "1548.91" {
    //          description "1548.91 nm/193.55000 THz 6.25/12.5/50G/75Hz spacing";
    //        }
    //        enum "1548.86" {
    //          description "1548.86 nm/193.55625 THz 6.25GHz spacing";
    //        }
    //        enum "1548.81" {
    //          description "1548.81 nm/193.56250 THz 6.25/12.5GHz spacing";
    //        }
    //        enum "1548.76" {
    //          description "1548.76 nm/193.56875 THz 6.25GHz spacing";
    //        }
    //        enum "1548.71" {
    //          description "1548.71 nm/193.57500 THz 6.25/12.5GHz spacing";
    //        }
    //        enum "1548.66" {
    //          description "1548.66 nm/193.58125 THz 6.25GHz spacing";
    //        }
    //        enum "1548.61" {
    //          description "1548.61 nm/193.58750 THz 6.25/12.5GHz spacing";
    //        }
    //        enum "1548.56" {
    //          description "1548.56 nm/193.59375 THz 6.25GHz spacing";
    //        }
    //        enum "1548.51" {
    //          description "1548.51 nm/193.60000 THz 6.25/12.5/50/100GHz spacing";
    //        }
    //        enum "1548.46" {
    //          description "1548.46 nm/193.60625 THz 6.25GHz spacing";
    //        }
    //        enum "1548.41" {
    //          description "1548.41 nm/193.61250 THz 6.25/12.5GHz spacing";
    //        }
    //        enum "1548.36" {
    //          description "1548.36 nm/193.61875 THz 6.25GHz spacing";
    //        }
    //        enum "1548.31" {
    //          description "1548.31 nm/193.62500 THz 6.25/12.5/75GHz spacing";
    //        }
    //        enum "1548.26" {
    //          description "1548.26 nm/193.63125 THz 6.25GHz spacing";
    //        }
    //        enum "1548.21" {
    //          description "1548.21 nm/193.63750 THz 6.25/12.5GHz spacing";
    //        }
    //        enum "1548.16" {
    //          description "1548.16 nm/193.64375 THz 6.25GHz spacing";
    //        }
    //        enum "1548.11" {
    //          description "1548.11 nm/193.65000 THz 6.25/12.5/50GHz spacing";
    //        }
    //        enum "1548.06" {
    //          description "1548.06 nm/193.65625 THz 6.25GHz spacing";
    //        }
    //        enum "1548.02" {
    //          description "1548.02 nm/193.66250 THz 6.25/12.5GHz spacing";
    //        }
    //        enum "1547.97" {
    //          description "1547.97 nm/193.66875 THz 6.25GHz spacing";
    //        }
    //        enum "1547.92" {
    //          description "1547.92 nm/193.67500 THz 6.25/12.5GHz spacing";
    //        }
    //        enum "1547.87" {
    //          description "1547.87 nm/193.68125 THz 6.25GHz spacing";
    //        }
    //        enum "1547.82" {
    //          description "1547.82 nm/193.68750 THz 6.25/12.5GHz spacing";
    //        }
    //        enum "1547.77" {
    //          description "1547.77 nm/193.69375 THz 6.25GHz spacing";
    //        }
    //        enum "1547.72" {
    //          description "1547.72 nm/193.70000 THz 6.25/12.5/50/75/100GHz spacing";
    //        }
    //        enum "1547.67" {
    //          description "1547.67 nm/193.70625 THz 6.25GHz spacing";
    //        }
    //        enum "1547.62" {
    //          description "1547.62 nm/193.71250 THz 6.25/12.5GHz spacing";
    //        }
    //        enum "1547.57" {
    //          description "1547.57 nm/193.71875 THz 6.25GHz spacing";
    //        }
    //        enum "1547.52" {
    //          description "1547.52 nm/193.72500 THz 6.25/12.5GHz spacing";
    //        }
    //        enum "1547.47" {
    //          description "1547.47 nm/193.73125 THz 6.25GHz spacing";
    //        }
    //        enum "1547.42" {
    //          description "1547.42 nm/193.73750 THz 6.25/12.5GHz spacing";
    //        }
    //        enum "1547.37" {
    //          description "1547.37 nm/193.74375 THz 6.25GHz spacing";
    //        }
    //        enum "1547.32" {
    //          description "1547.32 nm/193.75000 THz 6.25/12.5/50GHz spacing";
    //        }
    //        enum "1547.27" {
    //          description "1547.27 nm/193.75625 THz 6.25GHz spacing";
    //        }
    //        enum "1547.22" {
    //          description "1547.22 nm/193.76250 THz 6.25/12.5GHz spacing";
    //        }
    //        enum "1547.17" {
    //          description "1547.17 nm/193.76875 THz 6.25GHz spacing";
    //        }
    //        enum "1547.12" {
    //          description "1547.12 nm/193.77500 THz 6.25/12.5/75GHz spacing";
    //        }
    //        enum "1547.07" {
    //          description "1547.07 nm/193.78125 THz 6.25GHz spacing";
    //        }
    //        enum "1547.02" {
    //          description "1547.02 nm/193.78750 THz 6.25/12.5GHz spacing";
    //        }
    //        enum "1546.97" {
    //          description "1546.97 nm/193.79375 THz 6.25GHz spacing";
    //        }
    //        enum "1546.92" {
    //          description "1546.92 nm/193.80000 THz 6.25/12.5/50/100GHz spacing";
    //        }
    //        enum "1546.87" {
    //          description "1546.87 nm/193.80625 THz 6.25GHz spacing";
    //        }
    //        enum "1546.82" {
    //          description "1546.82 nm/193.81250 THz 6.25/12.5GHz spacing";
    //        }
    //        enum "1546.77" {
    //          description "1546.77 nm/193.81875 THz 6.25GHz spacing";
    //        }
    //        enum "1546.72" {
    //          description "1546.72 nm/193.82500 THz 6.25/12.5GHz spacing";
    //        }
    //        enum "1546.67" {
    //          description "1546.67 nm/193.83125 THz 6.25GHz spacing";
    //        }
    //        enum "1546.62" {
    //          description "1546.62 nm/193.83750 THz 6.25/12.5GHz spacing";
    //        }
    //        enum "1546.57" {
    //          description "1546.57 nm/193.84375 THz 6.25GHz spacing";
    //        }
    //        enum "1546.52" {
    //          description "1546.52 nm/193.85000 THz 6.25/12.5/50/75GHz spacing";
    //        }
    //        enum "1546.47" {
    //          description "1546.47 nm/193.85625 THz 6.25GHz spacing";
    //        }
    //        enum "1546.42" {
    //          description "1546.42 nm/193.86250 THz 6.25/12.5GHz spacing";
    //        }
    //        enum "1546.37" {
    //          description "1546.37 nm/193.86875 THz 6.25GHz spacing";
    //        }
    //        enum "1546.32" {
    //          description "1546.32 nm/193.87500 THz 6.25/12.5GHz spacing";
    //        }
    //        enum "1546.27" {
    //          description "1546.27 nm/193.88125 THz 6.25GHz spacing";
    //        }
    //        enum "1546.22" {
    //          description "1546.22 nm/193.88750 THz 6.25/12.5GHz spacing";
    //        }
    //        enum "1546.17" {
    //          description "1546.17 nm/193.89375 THz 6.25GHz spacing";
    //        }
    //        enum "1546.12" {
    //          description "1546.12 nm/193.90000 THz 6.25/12.5/50/100GHz spacing";
    //        }
    //        enum "1546.07" {
    //          description "1546.07 nm/193.90625 THz 6.25GHz spacing";
    //        }
    //        enum "1546.02" {
    //          description "1546.02 nm/193.91250 THz 6.25/12.5GHz spacing";
    //        }
    //        enum "1545.97" {
    //          description "1545.97 nm/193.91875 THz 6.25GHz spacing";
    //        }
    //        enum "1545.92" {
    //          description "1545.92 nm/193.92500 THz 6.25/12.5/75GHz spacing";
    //        }
    //        enum "1545.87" {
    //          description "1545.87 nm/193.93125 THz 6.25GHz spacing";
    //        }
    //        enum "1545.82" {
    //          description "1545.82 nm/193.93750 THz 6.25/12.5GHz spacing";
    //        }
    //        enum "1545.77" {
    //          description "1545.77 nm/193.94375 THz 6.25GHz spacing";
    //        }
    //        enum "1545.72" {
    //          description "1545.72 nm/193.95000 THz 6.25/12.5/50GHz spacing";
    //        }
    //        enum "1545.67" {
    //          description "1545.67 nm/193.95625 THz 6.25GHz spacing";
    //        }
    //        enum "1545.62" {
    //          description "1545.62 nm/193.96250 THz 6.25/12.5GHz spacing";
    //        }
    //        enum "1545.57" {
    //          description "1545.57 nm/193.96875 THz 6.25GHz spacing";
    //        }
    //        enum "1545.52" {
    //          description "1545.52 nm/193.97500 THz 6.25/12.5GHz spacing";
    //        }
    //        enum "1545.47" {
    //          description "1545.47 nm/193.98125 THz 6.25GHz spacing";
    //        }
    //        enum "1545.42" {
    //          description "1545.42 nm/193.98750 THz 6.25/12.5GHz spacing";
    //        }
    //        enum "1545.37" {
    //          description "1545.37 nm/193.99375 THz 6.25GHz spacing";
    //        }
    //        enum "1545.32" {
    //          description "1545.32 nm/194.00000 THz 6.25/12.5/50/75/100GHz spacing";
    //        }
    //        enum "1545.27" {
    //          description "1545.27 nm/194.00625 THz 6.25GHz spacing";
    //        }
    //        enum "1545.22" {
    //          description "1545.22 nm/194.01250 THz 6.25/12.5GHz spacing";
    //        }
    //        enum "1545.17" {
    //          description "1545.17 nm/194.01875 THz 6.25GHz spacing";
    //        }
    //        enum "1545.12" {
    //          description "1545.12 nm/194.02500 THz 6.25/12.5GHz spacing";
    //        }
    //        enum "1545.07" {
    //          description "1545.07 nm/194.03125 THz 6.25GHz spacing";
    //        }
    //        enum "1545.02" {
    //          description "1545.02 nm/194.03750 THz 6.25/12.5GHz spacing";
    //        }
    //        enum "1544.97" {
    //          description "1544.97 nm/194.04375 THz 6.25GHz spacing";
    //        }
    //        enum "1544.92" {
    //          description "1544.92 nm/194.05000 THz 6.25/12.5/50GHz spacing";
    //        }
    //        enum "1544.87" {
    //          description "1544.87 nm/194.05625 THz 6.25GHz spacing";
    //        }
    //        enum "1544.82" {
    //          description "1544.82 nm/194.06250 THz 6.25/12.5GHz spacing";
    //        }
    //        enum "1544.77" {
    //          description "1544.77 nm/194.06875 THz 6.25GHz spacing";
    //        }
    //        enum "1544.72" {
    //          description "1544.72 nm/194.07500 THz 6.25/12.5/75GHz spacing";
    //        }
    //        enum "1544.68" {
    //          description "1544.68 nm/194.08125 THz 6.25GHz spacing";
    //        }
    //        enum "1544.63" {
    //          description "1544.63 nm/194.08750 THz 6.25/12.5GHz spacing";
    //        }
    //        enum "1544.58" {
    //          description "1544.58 nm/194.09375 THz 6.25GHz spacing";
    //        }
    //        enum "1544.53" {
    //          description "1544.53 nm/194.10000 THz 6.25/12.5/50/100GHz spacing";
    //        }
    //        enum "1544.48" {
    //          description "1544.48 nm/194.10625 THz 6.25GHz spacing";
    //        }
    //        enum "1544.43" {
    //          description "1544.43 nm/194.11250 THz 6.25/12.5GHz spacing";
    //        }
    //        enum "1544.38" {
    //          description "1544.38 nm/194.11875 THz 6.25GHz spacing";
    //        }
    //        enum "1544.33" {
    //          description "1544.33 nm/194.12500 THz 6.25/12.5GHz spacing";
    //        }
    //        enum "1544.28" {
    //          description "1544.28 nm/194.13125 THz 6.25GHz spacing";
    //        }
    //        enum "1544.23" {
    //          description "1544.23 nm/194.13750 THz 6.25/12.5GHz spacing";
    //        }
    //        enum "1544.18" {
    //          description "1544.18 nm/194.14375 THz 6.25GHz spacing";
    //        }
    //        enum "1544.13" {
    //          description "1544.13 nm/194.15000 THz 6.25/12.5/50/75GHz spacing";
    //        }
    //        enum "1544.08" {
    //          description "1544.08 nm/194.15625 THz 6.25GHz spacing";
    //        }
    //        enum "1544.03" {
    //          description "1544.03 nm/194.16250 THz 6.25/12.5GHz spacing";
    //        }
    //        enum "1543.98" {
    //          description "1543.98 nm/194.16875 THz 6.25GHz spacing";
    //        }
    //        enum "1543.93" {
    //          description "1543.93 nm/194.17500 THz 6.25/12.5GHz spacing";
    //        }
    //        enum "1543.88" {
    //          description "1543.88 nm/194.18125 THz 6.25GHz spacing";
    //        }
    //        enum "1543.83" {
    //          description "1543.83 nm/194.18750 THz 6.25/12.5GHz spacing";
    //        }
    //        enum "1543.78" {
    //          description "1543.78 nm/194.19375 THz 6.25GHz spacing";
    //        }
    //        enum "1543.73" {
    //          description "1543.73 nm/194.20000 THz 6.25/12.5/50/100GHz spacing";
    //        }
    //        enum "1543.68" {
    //          description "1543.68 nm/194.20625 THz 6.25GHz spacing";
    //        }
    //        enum "1543.63" {
    //          description "1543.63 nm/194.21250 THz 6.25/12.5GHz spacing";
    //        }
    //        enum "1543.58" {
    //          description "1543.58 nm/194.21875 THz 6.25GHz spacing";
    //        }
    //        enum "1543.53" {
    //          description "1543.53 nm/194.22500 THz 6.25/12.5/75GHz spacing";
    //        }
    //        enum "1543.48" {
    //          description "1543.48 nm/194.23125 THz 6.25GHz spacing";
    //        }
    //        enum "1543.43" {
    //          description "1543.43 nm/194.23750 THz 6.25/12.5GHz spacing";
    //        }
    //        enum "1543.38" {
    //          description "1543.38 nm/194.24375 THz 6.25GHz spacing";
    //        }
    //        enum "1543.33" {
    //          description "1543.33 nm/194.25000 THz 6.25/12.5/50GHz spacing";
    //        }
    //        enum "1543.28" {
    //          description "1543.28 nm/194.25625 THz 6.25GHz spacing";
    //        }
    //        enum "1543.23" {
    //          description "1543.23 nm/194.26250 THz 6.25/12.5GHz spacing";
    //        }
    //        enum "1543.18" {
    //          description "1543.18 nm/194.26875 THz 6.25GHz spacing";
    //        }
    //        enum "1543.13" {
    //          description "1543.13 nm/194.27500 THz 6.25/12.5GHz spacing";
    //        }
    //        enum "1543.08" {
    //          description "1543.08 nm/194.28125 THz 6.25GHz spacing";
    //        }
    //        enum "1543.04" {
    //          description "1543.04 nm/194.28750 THz 6.25/12.5GHz spacing";
    //        }
    //        enum "1542.99" {
    //          description "1542.99 nm/194.29375 THz 6.25GHz spacing";
    //        }
    //        enum "1542.94" {
    //          description "1542.94 nm/194.30000 THz 6.25/12.5/50/75/100GHz spacing";
    //        }
    //        enum "1542.89" {
    //          description "1542.89 nm/194.30625 THz 6.25GHz spacing";
    //        }
    //        enum "1542.84" {
    //          description "1542.84 nm/194.31250 THz 6.25/12.5GHz spacing";
    //        }
    //        enum "1542.79" {
    //          description "1542.79 nm/194.31875 THz 6.25GHz spacing";
    //        }
    //        enum "1542.74" {
    //          description "1542.74 nm/194.32500 THz 6.25/12.5GHz spacing";
    //        }
    //        enum "1542.69" {
    //          description "1542.69 nm/194.33125 THz 6.25GHz spacing";
    //        }
    //        enum "1542.64" {
    //          description "1542.64 nm/194.33750 THz 6.25/12.5GHz spacing";
    //        }
    //        enum "1542.59" {
    //          description "1542.59 nm/194.34375 THz 6.25GHz spacing";
    //        }
    //        enum "1542.54" {
    //          description "1542.54 nm/194.35000 THz 6.25/12.5/50GHz spacing";
    //        }
    //        enum "1542.49" {
    //          description "1542.49 nm/194.35625 THz 6.25GHz spacing";
    //        }
    //        enum "1542.44" {
    //          description "1542.44 nm/194.36250 THz 6.25/12.5GHz spacing";
    //        }
    //        enum "1542.39" {
    //          description "1542.39 nm/194.36875 THz 6.25GHz spacing";
    //        }
    //        enum "1542.34" {
    //          description "1542.34 nm/194.37500 THz 6.25/12.5/75GHz spacing";
    //        }
    //        enum "1542.29" {
    //          description "1542.29 nm/194.38125 THz 6.25GHz spacing";
    //        }
    //        enum "1542.24" {
    //          description "1542.24 nm/194.38750 THz 6.25/12.5GHz spacing";
    //        }
    //        enum "1542.19" {
    //          description "1542.19 nm/194.39375 THz 6.25GHz spacing";
    //        }
    //        enum "1542.14" {
    //          description "1542.14 nm/194.40000 THz 6.25/12.5/50/100GHz spacing";
    //        }
    //        enum "1542.09" {
    //          description "1542.09 nm/194.40625 THz 6.25GHz spacing";
    //        }
    //        enum "1542.04" {
    //          description "1542.04 nm/194.41250 THz 6.25/12.5GHz spacing";
    //        }
    //        enum "1541.99" {
    //          description "1541.99 nm/194.41875 THz 6.25GHz spacing";
    //        }
    //        enum "1541.94" {
    //          description "1541.94 nm/194.42500 THz 6.25/12.5GHz spacing";
    //        }
    //        enum "1541.89" {
    //          description "1541.89 nm/194.43125 THz 6.25GHz spacing";
    //        }
    //        enum "1541.84" {
    //          description "1541.84 nm/194.43750 THz 6.25/12.5GHz spacing";
    //        }
    //        enum "1541.80" {
    //          description "1541.80 nm/194.44375 THz 6.25GHz spacing";
    //        }
    //        enum "1541.75" {
    //          description "1541.75 nm/194.45000 THz 6.25/12.5/50/75GHz spacing";
    //        }
    //        enum "1541.70" {
    //          description "1541.70 nm/194.45625 THz 6.25GHz spacing";
    //        }
    //        enum "1541.65" {
    //          description "1541.65 nm/194.46250 THz 6.25/12.5GHz spacing";
    //        }
    //        enum "1541.60" {
    //          description "1541.60 nm/194.46875 THz 6.25GHz spacing";
    //        }
    //        enum "1541.55" {
    //          description "1541.55 nm/194.47500 THz 6.25/12.5GHz spacing";
    //        }
    //        enum "1541.50" {
    //          description "1541.50 nm/194.48125 THz 6.25GHz spacing";
    //        }
    //        enum "1541.45" {
    //          description "1541.45 nm/194.48750 THz 6.25/12.5GHz spacing";
    //        }
    //        enum "1541.40" {
    //          description "1541.40 nm/194.49375 THz 6.25GHz spacing";
    //        }
    //        enum "1541.35" {
    //          description "1541.35 nm/194.50000 THz 6.25/12.5/50/100GHz spacing";
    //        }
    //        enum "1541.30" {
    //          description "1541.30 nm/194.50625 THz 6.25GHz spacing";
    //        }
    //        enum "1541.25" {
    //          description "1541.25 nm/194.51250 THz 6.25/12.5GHz spacing";
    //        }
    //        enum "1541.20" {
    //          description "1541.20 nm/194.51875 THz 6.25GHz spacing";
    //        }
    //        enum "1541.15" {
    //          description "1541.15 nm/194.52500 THz 6.25/12.5/75GHz spacing";
    //        }
    //        enum "1541.10" {
    //          description "1541.10 nm/194.53125 THz 6.25GHz spacing";
    //        }
    //        enum "1541.05" {
    //          description "1541.05 nm/194.53750 THz 6.25/12.5GHz spacing";
    //        }
    //        enum "1541.00" {
    //          description "1541.00 nm/194.54375 THz 6.25GHz spacing";
    //        }
    //        enum "1540.95" {
    //          description "1540.95 nm/194.55000 THz 6.25/12.5/50GHz spacing";
    //        }
    //        enum "1540.90" {
    //          description "1540.90 nm/194.55625 THz 6.25GHz spacing";
    //        }
    //        enum "1540.85" {
    //          description "1540.85 nm/194.56250 THz 6.25/12.5GHz spacing";
    //        }
    //        enum "1540.80" {
    //          description "1540.80 nm/194.56875 THz 6.25GHz spacing";
    //        }
    //        enum "1540.76" {
    //          description "1540.76 nm/194.57500 THz 6.25/12.5GHz spacing";
    //        }
    //        enum "1540.71" {
    //          description "1540.71 nm/194.58125 THz 6.25GHz spacing";
    //        }
    //        enum "1540.66" {
    //          description "1540.66 nm/194.58750 THz 6.25/12.5GHz spacing";
    //        }
    //        enum "1540.61" {
    //          description "1540.61 nm/194.59375 THz 6.25GHz spacing";
    //        }
    //        enum "1540.56" {
    //          description "1540.56 nm/194.60000 THz 6.25/12.5/50/75/100GHz spacing";
    //        }
    //        enum "1540.51" {
    //          description "1540.51 nm/194.60625 THz 6.25GHz spacing";
    //        }
    //        enum "1540.46" {
    //          description "1540.46 nm/194.61250 THz 6.25/12.5GHz spacing";
    //        }
    //        enum "1540.41" {
    //          description "1540.41 nm/194.61875 THz 6.25GHz spacing";
    //        }
    //        enum "1540.36" {
    //          description "1540.36 nm/194.62500 THz 6.25/12.5GHz spacing";
    //        }
    //        enum "1540.31" {
    //          description "1540.31 nm/194.63125 THz 6.25GHz spacing";
    //        }
    //        enum "1540.26" {
    //          description "1540.26 nm/194.63750 THz 6.25/12.5GHz spacing";
    //        }
    //        enum "1540.21" {
    //          description "1540.21 nm/194.64375 THz 6.25GHz spacing";
    //        }
    //        enum "1540.16" {
    //          description "1540.16 nm/194.65000 THz 6.25/12.5/50GHz spacing";
    //        }
    //        enum "1540.11" {
    //          description "1540.11 nm/194.65625 THz 6.25GHz spacing";
    //        }
    //        enum "1540.06" {
    //          description "1540.06 nm/194.66250 THz 6.25/12.5GHz spacing";
    //        }
    //        enum "1540.01" {
    //          description "1540.01 nm/194.66875 THz 6.25GHz spacing";
    //        }
    //        enum "1539.96" {
    //          description "1539.96 nm/194.67500 THz 6.25/12.5/50/75GHz spacing";
    //        }
    //        enum "1539.91" {
    //          description "1539.91 nm/194.68125 THz 6.25GHz spacing";
    //        }
    //        enum "1539.86" {
    //          description "1539.86 nm/194.68750 THz 6.25/12.5GHz spacing";
    //        }
    //        enum "1539.82" {
    //          description "1539.82 nm/194.69375 THz 6.25GHz spacing";
    //        }
    //        enum "1539.77" {
    //          description "1539.77 nm/194.70000 THz 6.25/12.5/50/100GHz spacing";
    //        }
    //        enum "1539.72" {
    //          description "1539.72 nm/194.70625 THz 6.25GHz spacing";
    //        }
    //        enum "1539.67" {
    //          description "1539.67 nm/194.71250 THz 6.25/12.5GHz spacing";
    //        }
    //        enum "1539.62" {
    //          description "1539.62 nm/194.71875 THz 6.25GHz spacing";
    //        }
    //        enum "1539.57" {
    //          description "1539.57 nm/194.72500 THz 6.25/12.5GHz spacing";
    //        }
    //        enum "1539.52" {
    //          description "1539.52 nm/194.73125 THz 6.25GHz spacing";
    //        }
    //        enum "1539.47" {
    //          description "1539.47 nm/194.73750 THz 6.25/12.5GHz spacing";
    //        }
    //        enum "1539.42" {
    //          description "1539.42 nm/194.74375 THz 6.25GHz spacing";
    //        }
    //        enum "1539.37" {
    //          description "1539.37 nm/194.75000 THz 6.25/12.5/50/75GHz spacing";
    //        }
    //        enum "1539.32" {
    //          description "1539.32 nm/194.75625 THz 6.25GHz spacing";
    //        }
    //        enum "1539.27" {
    //          description "1539.27 nm/194.76250 THz 6.25/12.5GHz spacing";
    //        }
    //        enum "1539.22" {
    //          description "1539.22 nm/194.76875 THz 6.25GHz spacing";
    //        }
    //        enum "1539.17" {
    //          description "1539.17 nm/194.77500 THz 6.25/12.5GHz spacing";
    //        }
    //        enum "1539.12" {
    //          description "1539.12 nm/194.78125 THz 6.25GHz spacing";
    //        }
    //        enum "1539.07" {
    //          description "1539.07 nm/194.78750 THz 6.25/12.5GHz spacing";
    //        }
    //        enum "1539.03" {
    //          description "1539.03 nm/194.79375 THz 6.25GHz spacing";
    //        }
    //        enum "1538.98" {
    //          description "1538.98 nm/194.80000 THz 6.25/12.5/50/100GHz spacing";
    //        }
    //        enum "1538.93" {
    //          description "1538.93 nm/194.80625 THz 6.25GHz spacing";
    //        }
    //        enum "1538.88" {
    //          description "1538.88 nm/194.81250 THz 6.25/12.5GHz spacing";
    //        }
    //        enum "1538.83" {
    //          description "1538.83 nm/194.81875 THz 6.25GHz spacing";
    //        }
    //        enum "1538.78" {
    //          description "1538.78 nm/194.82500 THz 6.25/12.5/75GHz spacing";
    //        }
    //        enum "1538.73" {
    //          description "1538.73 nm/194.83125 THz 6.25GHz spacing";
    //        }
    //        enum "1538.68" {
    //          description "1538.68 nm/194.83750 THz 6.25/12.5GHz spacing";
    //        }
    //        enum "1538.63" {
    //          description "1538.63 nm/194.84375 THz 6.25GHz spacing";
    //        }
    //        enum "1538.58" {
    //          description "1538.58 nm/194.85000 THz 6.25/12.5/50GHz spacing";
    //        }
    //        enum "1538.53" {
    //          description "1538.53 nm/194.85625 THz 6.25GHz spacing";
    //        }
    //        enum "1538.48" {
    //          description "1538.48 nm/194.86250 THz 6.25/12.5GHz spacing";
    //        }
    //        enum "1538.43" {
    //          description "1538.43 nm/194.86875 THz 6.25GHz spacing";
    //        }
    //        enum "1538.38" {
    //          description "1538.38 nm/194.87500 THz 6.25/12.5/75GHz spacing";
    //        }
    //        enum "1538.33" {
    //          description "1538.33 nm/194.88125 THz 6.25GHz spacing";
    //        }
    //        enum "1538.28" {
    //          description "1538.28 nm/194.88750 THz 6.25/12.5GHz spacing";
    //        }
    //        enum "1538.24" {
    //          description "1538.24 nm/194.89375 THz 6.25GHz spacing";
    //        }
    //        enum "1538.19" {
    //          description "1538.19 nm/194.90000 THz 6.25/12.5/50/75/100GHz spacing";
    //        }
    //        enum "1538.14" {
    //          description "1538.14 nm/194.90625 THz 6.25GHz spacing";
    //        }
    //        enum "1538.09" {
    //          description "1538.09 nm/194.91250 THz 6.25/12.5GHz spacing";
    //        }
    //        enum "1538.04" {
    //          description "1538.04 nm/194.91875 THz 6.25GHz spacing";
    //        }
    //        enum "1537.99" {
    //          description "1537.99 nm/194.92500 THz 6.25/12.5GHz spacing";
    //        }
    //        enum "1537.94" {
    //          description "1537.94 nm/194.93125 THz 6.25GHz spacing";
    //        }
    //        enum "1537.89" {
    //          description "1537.89 nm/194.93750 THz 6.25/12.5GHz spacing";
    //        }
    //        enum "1537.84" {
    //          description "1537.84 nm/194.94375 THz 6.25GHz spacing";
    //        }
    //        enum "1537.79" {
    //          description "1537.79 nm/194.95000 THz 6.25/12.5/50GHz spacing";
    //        }
    //        enum "1537.74" {
    //          description "1537.74 nm/194.95625 THz 6.25GHz spacing";
    //        }
    //        enum "1537.69" {
    //          description "1537.69 nm/194.96250 THz 6.25/12.5GHz spacing";
    //        }
    //        enum "1537.64" {
    //          description "1537.64 nm/194.96875 THz 6.25GHz spacing";
    //        }
    //        enum "1537.59" {
    //          description "1537.59 nm/194.97500 THz 6.25/12.5/75GHz spacing";
    //        }
    //        enum "1537.55" {
    //          description "1537.55 nm/194.98125 THz 6.25GHz spacing";
    //        }
    //        enum "1537.50" {
    //          description "1537.50 nm/194.98750 THz 6.25/12.5GHz spacing";
    //        }
    //        enum "1537.45" {
    //          description "1537.45 nm/194.99375 THz 6.25GHz spacing";
    //        }
    //        enum "1537.40" {
    //          description "1537.40 nm/195.00000 THz 6.25/12.5/50/100GHz spacing";
    //        }
    //        enum "1537.35" {
    //          description "1537.35 nm/195.00625 THz 6.25GHz spacing";
    //        }
    //        enum "1537.30" {
    //          description "1537.30 nm/195.01250 THz 6.25/12.5GHz spacing";
    //        }
    //        enum "1537.25" {
    //          description "1537.25 nm/195.01875 THz 6.25GHz spacing";
    //        }
    //        enum "1537.20" {
    //          description "1537.20 nm/195.02500 THz 6.25/12.5GHz spacing";
    //        }
    //        enum "1537.15" {
    //          description "1537.15 nm/195.03125 THz 6.25GHz spacing";
    //        }
    //        enum "1537.10" {
    //          description "1537.10 nm/195.03750 THz 6.25/12.5GHz spacing";
    //        }
    //        enum "1537.05" {
    //          description "1537.05 nm/195.04375 THz 6.25GHz spacing";
    //        }
    //        enum "1537.00" {
    //          description "1537.00 nm/195.05000 THz 6.25/12.5/50/75GHz spacing";
    //        }
    //        enum "1536.95" {
    //          description "1536.95 nm/195.05625 THz 6.25GHz spacing";
    //        }
    //        enum "1536.90" {
    //          description "1536.90 nm/195.06250 THz 6.25/12.5GHz spacing";
    //        }
    //        enum "1536.86" {
    //          description "1536.86 nm/195.06875 THz 6.25GHz spacing";
    //        }
    //        enum "1536.81" {
    //          description "1536.81 nm/195.07500 THz 6.25/12.5GHz spacing";
    //        }
    //        enum "1536.76" {
    //          description "1536.76 nm/195.08125 THz 6.25GHz spacing";
    //        }
    //        enum "1536.71" {
    //          description "1536.71 nm/195.08750 THz 6.25/12.5GHz spacing";
    //        }
    //        enum "1536.66" {
    //          description "1536.66 nm/195.09375 THz 6.25GHz spacing";
    //        }
    //        enum "1536.61" {
    //          description "1536.61 nm/195.10000 THz 6.25/12.5/50/100GHz spacing";
    //        }
    //        enum "1536.56" {
    //          description "1536.56 nm/195.10625 THz 6.25GHz spacing";
    //        }
    //        enum "1536.51" {
    //          description "1536.51 nm/195.11250 THz 6.25/12.5GHz spacing";
    //        }
    //        enum "1536.46" {
    //          description "1536.46 nm/195.11875 THz 6.25GHz spacing";
    //        }
    //        enum "1536.41" {
    //          description "1536.41 nm/195.12500 THz 6.25/12.5/75GHz spacing";
    //        }
    //        enum "1536.36" {
    //          description "1536.36 nm/195.13125 THz 6.25GHz spacing";
    //        }
    //        enum "1536.31" {
    //          description "1536.31 nm/195.13750 THz 6.25/12.5GHz spacing";
    //        }
    //        enum "1536.26" {
    //          description "1536.26 nm/195.14375 THz 6.25GHz spacing";
    //        }
    //        enum "1536.22" {
    //          description "1536.22 nm/195.15000 THz 6.25/12.5/50GHz spacing";
    //        }
    //        enum "1536.17" {
    //          description "1536.17 nm/195.15625 THz 6.25GHz spacing";
    //        }
    //        enum "1536.12" {
    //          description "1536.12 nm/195.16250 THz 6.25/12.5GHz spacing";
    //        }
    //        enum "1536.07" {
    //          description "1536.07 nm/195.16875 THz 6.25GHz spacing";
    //        }
    //        enum "1536.02" {
    //          description "1536.02 nm/195.17500 THz 6.25/12.5GHz spacing";
    //        }
    //        enum "1535.97" {
    //          description "1535.97 nm/195.18125 THz 6.25GHz spacing";
    //        }
    //        enum "1535.92" {
    //          description "1535.92 nm/195.18750 THz 6.25/12.5GHz spacing";
    //        }
    //        enum "1535.87" {
    //          description "1535.87 nm/195.19375 THz 6.25GHz spacing";
    //        }
    //        enum "1535.82" {
    //          description "1535.82 nm/195.20000 THz 6.25/12.5/50/75/100GHz spacing";
    //        }
    //        enum "1535.77" {
    //          description "1535.77 nm/195.20625 THz 6.25GHz spacing";
    //        }
    //        enum "1535.72" {
    //          description "1535.72 nm/195.21250 THz 6.25/12.5GHz spacing";
    //        }
    //        enum "1535.67" {
    //          description "1535.67 nm/195.21875 THz 6.25GHz spacing";
    //        }
    //        enum "1535.63" {
    //          description "1535.63 nm/195.22500 THz 6.25/12.5GHz spacing";
    //        }
    //        enum "1535.58" {
    //          description "1535.58 nm/195.23125 THz 6.25GHz spacing";
    //        }
    //        enum "1535.53" {
    //          description "1535.53 nm/195.23750 THz 6.25/12.5GHz spacing";
    //        }
    //        enum "1535.48" {
    //          description "1535.48 nm/195.24375 THz 6.25GHz spacing";
    //        }
    //        enum "1535.43" {
    //          description "1535.43 nm/195.25000 THz 6.25/12.5/50GHz spacing";
    //        }
    //        enum "1535.38" {
    //          description "1535.38 nm/195.25625 THz 6.25GHz spacing";
    //        }
    //        enum "1535.33" {
    //          description "1535.33 nm/195.26250 THz 6.25/12.5GHz spacing";
    //        }
    //        enum "1535.28" {
    //          description "1535.28 nm/195.26875 THz 6.25GHz spacing";
    //        }
    //        enum "1535.23" {
    //          description "1535.23 nm/195.27500 THz 6.25/12.5/75GHz spacing";
    //        }
    //        enum "1535.18" {
    //          description "1535.18 nm/195.28125 THz 6.25GHz spacing";
    //        }
    //        enum "1535.13" {
    //          description "1535.13 nm/195.28750 THz 6.25/12.5GHz spacing";
    //        }
    //        enum "1535.08" {
    //          description "1535.08 nm/195.29375 THz 6.25GHz spacing";
    //        }
    //        enum "1535.04" {
    //          description "1535.04 nm/195.30000 THz 6.25/12.5/50/100GHz spacing";
    //        }
    //        enum "1534.99" {
    //          description "1534.99 nm/195.30625 THz 6.25GHz spacing";
    //        }
    //        enum "1534.94" {
    //          description "1534.94 nm/195.31250 THz 6.25/12.5GHz spacing";
    //        }
    //        enum "1534.89" {
    //          description "1534.89 nm/195.31875 THz 6.25GHz spacing";
    //        }
    //        enum "1534.84" {
    //          description "1534.84 nm/195.32500 THz 6.25/12.5GHz spacing";
    //        }
    //        enum "1534.79" {
    //          description "1534.79 nm/195.33125 THz 6.25GHz spacing";
    //        }
    //        enum "1534.74" {
    //          description "1534.74 nm/195.33750 THz 6.25/12.5GHz spacing";
    //        }
    //        enum "1534.69" {
    //          description "1534.69 nm/195.34375 THz 6.25GHz spacing";
    //        }
    //        enum "1534.64" {
    //          description "1534.64 nm/195.35000 THz 6.25/12.5/50/75GHz spacing";
    //        }
    //        enum "1534.59" {
    //          description "1534.59 nm/195.35625 THz 6.25GHz spacing";
    //        }
    //        enum "1534.54" {
    //          description "1534.54 nm/195.36250 THz 6.25/12.5GHz spacing";
    //        }
    //        enum "1534.50" {
    //          description "1534.50 nm/195.36875 THz 6.25GHz spacing";
    //        }
    //        enum "1534.45" {
    //          description "1534.45 nm/195.37500 THz 6.25/12.5GHz spacing";
    //        }
    //        enum "1534.40" {
    //          description "1534.40 nm/195.38125 THz 6.25GHz spacing";
    //        }
    //        enum "1534.35" {
    //          description "1534.35 nm/195.38750 THz 6.25/12.5GHz spacing";
    //        }
    //        enum "1534.30" {
    //          description "1534.30 nm/195.39375 THz 6.25GHz spacing";
    //        }
    //        enum "1534.25" {
    //          description "1534.25 nm/195.40000 THz 6.25/12.5/50/100GHz spacing";
    //        }
    //        enum "1534.20" {
    //          description "1534.20 nm/195.40625 THz 6.25GHz spacing";
    //        }
    //        enum "1534.15" {
    //          description "1534.15 nm/195.41250 THz 6.25/12.5GHz spacing";
    //        }
    //        enum "1534.10" {
    //          description "1534.10 nm/195.41875 THz 6.25GHz spacing";
    //        }
    //        enum "1534.05" {
    //          description "1534.05 nm/195.42500 THz 6.25/12.5/75GHz spacing";
    //        }
    //        enum "1534.00" {
    //          description "1534.00 nm/195.43125 THz 6.25GHz spacing";
    //        }
    //        enum "1533.96" {
    //          description "1533.96 nm/195.43750 THz 6.25/12.5GHz spacing";
    //        }
    //        enum "1533.91" {
    //          description "1533.91 nm/195.44375 THz 6.25GHz spacing";
    //        }
    //        enum "1533.86" {
    //          description "1533.86 nm/195.45000 THz 6.25/12.5/50GHz spacing";
    //        }
    //        enum "1533.81" {
    //          description "1533.81 nm/195.45625 THz 6.25GHz spacing";
    //        }
    //        enum "1533.76" {
    //          description "1533.76 nm/195.46250 THz 6.25/12.5GHz spacing";
    //        }
    //        enum "1533.71" {
    //          description "1533.71 nm/195.46875 THz 6.25GHz spacing";
    //        }
    //        enum "1533.66" {
    //          description "1533.66 nm/195.47500 THz 6.25/12.5GHz spacing";
    //        }
    //        enum "1533.61" {
    //          description "1533.61 nm/195.48125 THz 6.25GHz spacing";
    //        }
    //        enum "1533.56" {
    //          description "1533.56 nm/195.48750 THz 6.25/12.5GHz spacing";
    //        }
    //        enum "1533.51" {
    //          description "1533.51 nm/195.49375 THz 6.25GHz spacing";
    //        }
    //        enum "1533.47" {
    //          description "1533.47 nm/195.50000 THz 6.25/12.5/50/75/100GHz spacing";
    //        }
    //        enum "1533.42" {
    //          description "1533.42 nm/195.50625 THz 6.25GHz spacing";
    //        }
    //        enum "1533.37" {
    //          description "1533.37 nm/195.51250 THz 6.25/12.5GHz spacing";
    //        }
    //        enum "1533.32" {
    //          description "1533.32 nm/195.51875 THz 6.25GHz spacing";
    //        }
    //        enum "1533.27" {
    //          description "1533.27 nm/195.52500 THz 6.25/12.5GHz spacing";
    //        }
    //        enum "1533.22" {
    //          description "1533.22 nm/195.53125 THz 6.25GHz spacing";
    //        }
    //        enum "1533.17" {
    //          description "1533.17 nm/195.53750 THz 6.25/12.5GHz spacing";
    //        }
    //        enum "1533.12" {
    //          description "1533.12 nm/195.54375 THz 6.25GHz spacing";
    //        }
    //        enum "1533.07" {
    //          description "1533.07 nm/195.55000 THz 6.25/12.5/50GHz spacing";
    //        }
    //        enum "1533.02" {
    //          description "1533.02 nm/195.55625 THz 6.25GHz spacing";
    //        }
    //        enum "1532.98" {
    //          description "1532.98 nm/195.56250 THz 6.25/12.5GHz spacing";
    //        }
    //        enum "1532.93" {
    //          description "1532.93 nm/195.56875 THz 6.25GHz spacing";
    //        }
    //        enum "1532.88" {
    //          description "1532.88 nm/195.57500 THz 6.25/12.5/75GHz spacing";
    //        }
    //        enum "1532.83" {
    //          description "1532.83 nm/195.58125 THz 6.25GHz spacing";
    //        }
    //        enum "1532.78" {
    //          description "1532.78 nm/195.58750 THz 6.25/12.5GHz spacing";
    //        }
    //        enum "1532.73" {
    //          description "1532.73 nm/195.59375 THz 6.25GHz spacing";
    //        }
    //        enum "1532.68" {
    //          description "1532.68 nm/195.60000 THz 6.25/12.5/50/100GHz spacing";
    //        }
    //        enum "1532.63" {
    //          description "1532.63 nm/195.60625 THz 6.25GHz spacing";
    //        }
    //        enum "1532.58" {
    //          description "1532.58 nm/195.61250 THz 6.25/12.5GHz spacing";
    //        }
    //        enum "1532.53" {
    //          description "1532.53 nm/195.61875 THz 6.25GHz spacing";
    //        }
    //        enum "1532.49" {
    //          description "1532.49 nm/195.62500 THz 6.25/12.5GHz spacing";
    //        }
    //        enum "1532.44" {
    //          description "1532.44 nm/195.63125 THz 6.25GHz spacing";
    //        }
    //        enum "1532.39" {
    //          description "1532.39 nm/195.63750 THz 6.25/12.5GHz spacing";
    //        }
    //        enum "1532.34" {
    //          description "1532.34 nm/195.64375 THz 6.25GHz spacing";
    //        }
    //        enum "1532.29" {
    //          description "1532.29 nm/195.65000 THz 6.25/12.5/50/75GHz spacing";
    //        }
    //        enum "1532.24" {
    //          description "1532.24 nm/195.65625 THz 6.25GHz spacing";
    //        }
    //        enum "1532.19" {
    //          description "1532.19 nm/195.66250 THz 6.25/12.5GHz spacing";
    //        }
    //        enum "1532.14" {
    //          description "1532.14 nm/195.66875 THz 6.25GHz spacing";
    //        }
    //        enum "1532.09" {
    //          description "1532.09 nm/195.67500 THz 6.25/12.5GHz spacing";
    //        }
    //        enum "1532.04" {
    //          description "1532.04 nm/195.68125 THz 6.25GHz spacing";
    //        }
    //        enum "1532.00" {
    //          description "1532.00 nm/195.68750 THz 6.25/12.5GHz spacing";
    //        }
    //        enum "1531.95" {
    //          description "1531.95 nm/195.69375 THz 6.25GHz spacing";
    //        }
    //        enum "1531.90" {
    //          description "1531.90 nm/195.70000 THz 6.25/12.5/50/100GHz spacing";
    //        }
    //        enum "1531.85" {
    //          description "1531.85 nm/195.70625 THz 6.25GHz spacing";
    //        }
    //        enum "1531.80" {
    //          description "1531.80 nm/195.71250 THz 6.25/12.5GHz spacing";
    //        }
    //        enum "1531.75" {
    //          description "1531.75 nm/195.71875 THz 6.25GHz spacing";
    //        }
    //        enum "1531.70" {
    //          description "1531.70 nm/195.72500 THz 6.25/12.5/75GHz spacing";
    //        }
    //        enum "1531.65" {
    //          description "1531.65 nm/195.73125 THz 6.25GHz spacing";
    //        }
    //        enum "1531.60" {
    //          description "1531.60 nm/195.73750 THz 6.25/12.5GHz spacing";
    //        }
    //        enum "1531.56" {
    //          description "1531.56 nm/195.74375 THz 6.25GHz spacing";
    //        }
    //        enum "1531.51" {
    //          description "1531.51 nm/195.75000 THz 6.25/12.5/50GHz spacing";
    //        }
    //        enum "1531.46" {
    //          description "1531.46 nm/195.75625 THz 6.25GHz spacing";
    //        }
    //        enum "1531.41" {
    //          description "1531.41 nm/195.76250 THz 6.25/12.5GHz spacing";
    //        }
    //        enum "1531.36" {
    //          description "1531.36 nm/195.76875 THz 6.25GHz spacing";
    //        }
    //        enum "1531.31" {
    //          description "1531.31 nm/195.77500 THz 6.25/12.5GHz spacing";
    //        }
    //        enum "1531.26" {
    //          description "1531.26 nm/195.78125 THz 6.25GHz spacing";
    //        }
    //        enum "1531.21" {
    //          description "1531.21 nm/195.78750 THz 6.25/12.5GHz spacing";
    //        }
    //        enum "1531.16" {
    //          description "1531.16 nm/195.79375 THz 6.25GHz spacing";
    //        }
    //        enum "1531.12" {
    //          description "1531.12 nm/195.80000 THz 6.25/12.5/50/75/100GHz spacing";
    //        }
    //        enum "1531.07" {
    //          description "1531.07 nm/195.80625 THz 6.25GHz spacing";
    //        }
    //        enum "1531.02" {
    //          description "1531.02 nm/195.81250 THz 6.25/12.5GHz spacing";
    //        }
    //        enum "1530.97" {
    //          description "1530.97 nm/195.81875 THz 6.25GHz spacing";
    //        }
    //        enum "1530.92" {
    //          description "1530.92 nm/195.82500 THz 6.25/12.5GHz spacing";
    //        }
    //        enum "1530.87" {
    //          description "1530.87 nm/195.83125 THz 6.25GHz spacing";
    //        }
    //        enum "1530.82" {
    //          description "1530.82 nm/195.83750 THz 6.25/12.5GHz spacing";
    //        }
    //        enum "1530.77" {
    //          description "1530.77 nm/195.84375 THz 6.25GHz spacing";
    //        }
    //        enum "1530.72" {
    //          description "1530.72 nm/195.85000 THz 6.25/12.5/50GHz spacing";
    //        }
    //        enum "1530.68" {
    //          description "1530.68 nm/195.85625 THz 6.25GHz spacing";
    //        }
    //        enum "1530.63" {
    //          description "1530.63 nm/195.86250 THz 6.25/12.5GHz spacing";
    //        }
    //        enum "1530.58" {
    //          description "1530.58 nm/195.86875 THz 6.25GHz spacing";
    //        }
    //        enum "1530.53" {
    //          description "1530.53 nm/195.87500 THz 6.25/12.5/75GHz spacing";
    //        }
    //        enum "1530.48" {
    //          description "1530.48 nm/195.88125 THz 6.25GHz spacing";
    //        }
    //        enum "1530.43" {
    //          description "1530.43 nm/195.88750 THz 6.25/12.5GHz spacing";
    //        }
    //        enum "1530.38" {
    //          description "1530.38 nm/195.89375 THz 6.25GHz spacing";
    //        }
    //        enum "1530.33" {
    //          description "1530.33 nm/195.90000 THz 6.25/12.5/50/100GHz spacing";
    //        }
    //        enum "1530.29" {
    //          description "1530.29 nm/195.90625 THz 6.25GHz spacing";
    //        }
    //        enum "1530.24" {
    //          description "1530.24 nm/195.91250 THz 6.25/12.5GHz spacing";
    //        }
    //        enum "1530.19" {
    //          description "1530.19 nm/195.91875 THz 6.25GHz spacing";
    //        }
    //        enum "1530.14" {
    //          description "1530.14 nm/195.92500 THz 6.25/12.5GHz spacing";
    //        }
    //        enum "1530.09" {
    //          description "1530.09 nm/195.93125 THz 6.25GHz spacing";
    //        }
    //        enum "1530.04" {
    //          description "1530.04 nm/195.93750 THz 6.25/12.5GHz spacing";
    //        }
    //        enum "1529.99" {
    //          description "1529.99 nm/195.94375 THz 6.25GHz spacing";
    //        }
    //        enum "1529.94" {
    //          description "1529.94 nm/195.95000 THz 6.25/12.5/50/75GHz spacing";
    //        }
    //        enum "1529.89" {
    //          description "1529.89 nm/195.95625 THz 6.25GHz spacing";
    //        }
    //        enum "1529.85" {
    //          description "1529.85 nm/195.96250 THz 6.25/12.5GHz spacing";
    //        }
    //        enum "1529.80" {
    //          description "1529.80 nm/195.96875 THz 6.25GHz spacing";
    //        }
    //        enum "1529.75" {
    //          description "1529.75 nm/195.97500 THz 6.25/12.5GHz spacing";
    //        }
    //        enum "1529.70" {
    //          description "1529.70 nm/195.98125 THz 6.25GHz spacing";
    //        }
    //        enum "1529.65" {
    //          description "1529.65 nm/195.98750 THz 6.25/12.5GHz spacing";
    //        }
    //        enum "1529.60" {
    //          description "1529.60 nm/195.99375 THz 6.25GHz spacing";
    //        }
    //        enum "1529.55" {
    //          description "1529.55 nm/196.00000 THz 6.25/12.5/50/100GHz spacing";
    //        }
    //        enum "1529.50" {
    //          description "1529.50 nm/196.00625 THz 6.25GHz spacing";
    //        }
    //        enum "1529.46" {
    //          description "1529.46 nm/196.01250 THz 6.25/12.5GHz spacing";
    //        }
    //        enum "1529.41" {
    //          description "1529.41 nm/196.01875 THz 6.25GHz spacing";
    //        }
    //        enum "1529.36" {
    //          description "1529.36 nm/196.02500 THz 6.25/12.5/75GHz spacing";
    //        }
    //        enum "1529.31" {
    //          description "1529.31 nm/196.03125 THz 6.25GHz spacing";
    //        }
    //        enum "1529.26" {
    //          description "1529.26 nm/196.03750 THz 6.25/12.5GHz spacing";
    //        }
    //        enum "1529.21" {
    //          description "1529.21 nm/196.04375 THz 6.25GHz spacing";
    //        }
    //        enum "1529.16" {
    //          description "1529.16 nm/196.05000 THz 6.25/12.5/50GHz spacing";
    //        }
    //        enum "1529.11" {
    //          description "1529.11 nm/196.05625 THz 6.25GHz spacing";
    //        }
    //        enum "1529.07" {
    //          description "1529.07 nm/196.06250 THz 6.25/12.5GHz spacing";
    //        }
    //        enum "1529.02" {
    //          description "1529.02 nm/196.06875 THz 6.25GHz spacing";
    //        }
    //        enum "1528.97" {
    //          description "1528.97 nm/196.07500 THz 6.25/12.5GHz spacing";
    //        }
    //        enum "1528.92" {
    //          description "1528.92 nm/196.08125 THz 6.25GHz spacing";
    //        }
    //        enum "1528.87" {
    //          description "1528.87 nm/196.08750 THz 6.25/12.5GHz spacing";
    //        }
    //        enum "1528.82" {
    //          description "1528.82 nm/196.09375 THz 6.25GHz spacing";
    //        }
    //        enum "1528.77" {
    //          description "1528.77 nm/196.10000 THz 6.25/12.5/50/75/100GHz spacing";
    //        }
    //        enum "1528.38" {
    //          description "1528.38 nm/196.15040 THz 50Ghz spacing";
    //        }
    //      }
    //    }
    //    leaf tx-power {
    //      description "Transmit laser output power";
    //      units "dBm";
    //      type string {
    //      }
    //    }
    //    container loopback {
    //      presence "enable loopback";
    //      description "Put the optics in loopback mode";
    //      // uses apply-advanced;
    //      leaf loopbacktype {
    //        description "Set loopback type";
    //        type enumeration {
    //          enum "media-side-out" {
    //            description "Loop media side output back to input";
    //          }
    //          enum "media-side-in" {
    //            description "Loop media side input back to output";
    //          }
    //          enum "host-side-out" {
    //            description "Loop host side output back to input";
    //          }
    //          enum "host-side-in" {
    //            description "Loop host side input back to output";
    //          }
    //        }
    //      }
    //    }
    //    leaf los-warning-threshold {
    //      description "LOS warning threshold";
    //      units "dBm";
    //      type string;
    //    }
    //    leaf los-alarm-threshold {
    //      description "LOS alarm threshold";
    //      units "dBm";
    //      type string;
    //    }
    //    leaf modulation-format {
    //      description "Type of Modulation Format";
    //      type enumeration {
    //        enum "16qam" {
    //          description "16-QAM Modulation Format";
    //        }
    //        enum "8qam" {
    //          description "8-QAM MOdulation Format";
    //        }
    //        enum "qpsk" {
    //          description "QPSK Modulation Format";
    //        }
    //      }
    //    }
    //    choice laser-enable-choice {
    //      leaf laser-enable {
    //        description "Enable Laser";
    //        type empty;
    //      }
    //      leaf no-laser-enable {
    //        description "Don't enable Laser";
    //        type empty;
    //      }
    //    }
    //    choice is-ma-choice {
    //      leaf is-ma {
    //        description "Link is enabled with alarms masked";
    //        type empty;
    //      }
    //      leaf no-is-ma {
    //        description "Don't link is enabled with alarms masked";
    //        type empty;
    //      }
    //    }
    //    leaf encoding {
    //      description "Line encoding";
    //      type enumeration {
    //        enum "differential" {
    //          description "Differential phase line encoding";
    //        }
    //        enum "non-differential" {
    //          description "Non-differential phase line encoding";
    //        }
    //      }
    //    }
    //    leaf fec {
    //      description "Forward Error Correction mode";
    //      type enumeration {
    //        enum "sdfec" {
    //          description "Sky-Compatible Soft Decision Forward Error Correction";
    //        }
    //        enum "sdfec25" {
    //          description "Denali-Compatible Soft Decision Forward Error Correction with 25 percent overhead";
    //        }
    //        enum "hgfec" {
    //          description "High Gain Forward Error Correction";
    //        }
    //        enum "sdfec15" {
    //          description "Soft Decision Forward Error Correction with 15 percent overhead";
    //        }
    //      }
    //    }
    //    leaf high-polarization {
    //      description "High polarization tracking mode";
    //      type empty;
    //    }
    //    container application {
    //      description "Config Host and Media Code";
    //      // uses apply-advanced;
    //      leaf hostid {
    //        description "Enter Host Code";
    //        type union {
    //          type string {
    //            pattern "<.*>|$.*";
    //          }
    //          type uint32 {
    //            range "1 .. 300";
    //          }
    //        }
    //      }
    //      leaf mediaid {
    //        description "Enter Media Code";
    //        type union {
    //          type string {
    //            pattern "<.*>|$.*";
    //          }
    //          type uint32 {
    //            range "1 .. 300";
    //          }
    //        }
    //      }
    //      leaf domainid {
    //        description "Enter Domain ID";
    //        type union {
    //          type string {
    //            pattern "<.*>|$.*";
    //          }
    //          type uint32 {
    //            range "0 .. 300";
    //          }
    //        }
    //      }
    //    }
    //    container signal-degrade {
    //      description "Signal degrade thresholds";
    //      // uses apply-advanced;
    //      leaf interval {
    //        description "Time interval";
    //        default "10";
    //        units "milliseconds";
    //        type union {
    //          type string {
    //            pattern "<.*>|$.*";
    //          }
    //          type uint32 {
    //            range "1 .. 1000";
    //          }
    //        }
    //      }
    //      leaf ber-threshold-clear {
    //        description "Ber threshold for signal degrade clear (format: xe-n, example: 4.5e-3)";
    //        type string {
    //        }
    //      }
    //      leaf ber-threshold-signal-degrade {
    //        description "Ber threshold for signal-degrade (format: xe-n, example: 4.5e-3)";
    //        type string {
    //        }
    //      }
    //      leaf q-threshold-signal-degrade-clear {
    //        description "Q threshold for signal-degrade clear (e.g. 14.26)";
    //        units "dB";
    //        type string;
    //      }
    //      leaf q-threshold-signal-degrade {
    //        description "Q threshold for signal-degrade (e.g. 9.26)";
    //        units "dB";
    //        type string;
    //      }
    //    }
    //    list alarm {
    //      key name;
    //      ordered-by user;
    //      description "Set optic alarms";
    //      leaf name {
    //        type enumeration {
    //          enum "low-light-alarm" {
    //            description "Enable low light alarm";
    //          }
    //        }
    //      }
    //      // uses apply-advanced;
    //      choice actiontype {
    //        case case_1 {
    //          leaf syslog {
    //            type empty;
    //          }
    //        }
    //        case case_2 {
    //          leaf link-down {
    //            type empty;
    //          }
    //        }
    //      }
    //    }
    //    container tca {
    //      description "Set tca for optic alarms";
    //      // uses apply-advanced;
    //      container tx-power-high-tca {
    //        description "Tx power high TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute tx power high TCA in dBm";
    //          type string {
    //          }
    //        }
    //        leaf threshold-24hrs {
    //          description "Threshold for 24 hour tx power high TCA in dBm";
    //          type string {
    //          }
    //        }
    //      }
    //      container tx-power-low-tca {
    //        description "Tx power low TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute tx power low TCA in dBm";
    //          type string {
    //          }
    //        }
    //        leaf threshold-24hrs {
    //          description "Threshold for 24 hour tx power low TCA in dBm";
    //          type string {
    //          }
    //        }
    //      }
    //      container rx-power-high-tca {
    //        description "Rx power high TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute rx power high TCA in dBm";
    //          type string {
    //          }
    //        }
    //        leaf threshold-24hrs {
    //          description "Threshold for 24 hour rx power high TCA in dBm";
    //          type string {
    //          }
    //        }
    //      }
    //      container rx-power-low-tca {
    //        description "Rx power low TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute rx power low TCA in dBm";
    //          type string {
    //          }
    //        }
    //        leaf threshold-24hrs {
    //          description "Threshold for 24 hour rx power low TCA in dBm";
    //          type string {
    //          }
    //        }
    //      }
    //      container rx-signal-power-high-tca {
    //        description "Rx signal power high TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute rx signal power high TCA in dBm";
    //          type string {
    //          }
    //        }
    //        leaf threshold-24hrs {
    //          description "Threshold for 24 hour rx signal power high TCA in dBm";
    //          type string {
    //          }
    //        }
    //      }
    //      container rx-signal-power-low-tca {
    //        description "Rx signal power low TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute rx signal power low TCA in dBm";
    //          type string {
    //          }
    //        }
    //        leaf threshold-24hrs {
    //          description "Threshold for 24 hour rx signal power low TCA in dBm";
    //          type string {
    //          }
    //        }
    //      }
    //      container temperature-high-tca {
    //        description "Temperature high TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute high temperature TCA in celsius";
    //          type string {
    //          }
    //        }
    //        leaf threshold-24hrs {
    //          description "Threshold for 24 hour high temperature TCA in celsius";
    //          type string {
    //          }
    //        }
    //      }
    //      container temperature-low-tca {
    //        description "Temperature low TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute low temperature TCA in celsius";
    //          type string {
    //          }
    //        }
    //        leaf threshold-24hrs {
    //          description "Threshold for 24 hour low temperature TCA in celsius";
    //          type string {
    //          }
    //        }
    //      }
    //      container carrier-frequency-offset-high-tca {
    //        description "Carrier frequency offset high TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute frequency offset high TCA in MHz";
    //          type string {
    //          }
    //        }
    //        leaf threshold-24hrs {
    //          description "Threshold for 24 hour frequency offset high TCA in MHz";
    //          type string {
    //          }
    //        }
    //      }
    //      container carrier-frequency-offset-low-tca {
    //        description "Carrier frequency offset low TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute frequency offset low TCA in MHz";
    //          type string {
    //          }
    //        }
    //        leaf threshold-24hrs {
    //          description "Threshold for 24 hour frequency offset low TCA in MHz";
    //          type string {
    //          }
    //        }
    //      }
    //      container fec-ber {
    //        description "Optics Errored Seconds Threshold crossing defect trigger";
    //        choice enable-tca-choice {
    //          leaf enable-tca {
    //            description "Enable the Optics errored seconds threshold crossing alert";
    //            type empty;
    //          }
    //          leaf no-enable-tca {
    //            description "Don't enable the Optics errored seconds threshold crossing alert";
    //            type empty;
    //          }
    //        }
    //        leaf threshold {
    //          description "TCA threshold for BER value in format: xe-n, x is an integer or decimal number, n = 0..9";
    //          default "10e-3";
    //          type string {
    //          }
    //        }
    //        leaf threshold-24hrs {
    //          description "TCA threshold for BER value in format: xe-n, x is an integer or decimal number, n = 0..9";
    //          default "10e-3";
    //          type string {
    //          }
    //        }
    //      }
    //      container tec-current-high-tca {
    //        description "TEC Current high TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute TEC Current high TCA in mA";
    //          type string {
    //          }
    //        }
    //        leaf threshold-24hrs {
    //          description "Threshold for 24 hour TEC Current high TCA in mA";
    //          type string {
    //          }
    //        }
    //      }
    //      container tec-current-low-tca {
    //        description "TEC Current low TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute TEC Current low TCA in mA";
    //          type string {
    //          }
    //        }
    //        leaf threshold-24hrs {
    //          description "Threshold for 24 hour TEC Current low TCA in mA";
    //          type string {
    //          }
    //        }
    //      }
    //      container residual-isi-high-tca {
    //        description "Residual ISI high TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute Residual ISI high TCA in ps/nm";
    //          type string {
    //          }
    //        }
    //        leaf threshold-24hrs {
    //          description "Threshold for 24 hour Residual ISI high TCA in ps/nm";
    //          type string {
    //          }
    //        }
    //      }
    //      container residual-isi-low-tca {
    //        description "Residual ISI low TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute Residual ISI low TCA in ps/nm";
    //          type string {
    //          }
    //        }
    //        leaf threshold-24hrs {
    //          description "Threshold for 24 hour Residual ISI low TCA in ps/nm";
    //          type string {
    //          }
    //        }
    //      }
    //      container pam-histogram-high-tca {
    //        description "PAM Histogram high TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute PAM Histogram high TCA";
    //          type string {
    //          }
    //        }
    //        leaf threshold-24hrs {
    //          description "Threshold for 24 hour PAM Histogram high TCA";
    //          type string {
    //          }
    //        }
    //      }
    //      container snr-low-tca {
    //        description "SNR low TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute SNR low TCA in dBm ";
    //          type string {
    //          }
    //        }
    //        leaf threshold-24hrs {
    //          description "Threshold for 24 hour SNR low TCA in dBm";
    //          type string {
    //          }
    //        }
    //      }
    //      container fec-corrected-errors-high-tca {
    //        description "FEC Corrected Error High Threshold crossing defect trigger";
    //        // uses apply-advanced;
    //        choice enable-tca-choice {
    //          leaf enable-tca {
    //            description "Enable the FEC Corrected Errors threshold crossing alert";
    //            type empty;
    //          }
    //          leaf no-enable-tca {
    //            description "Don't enable the FEC Corrected Errors threshold crossing alert";
    //            type empty;
    //          }
    //        }
    //        leaf threshold {
    //          description "FEC Corrected-Errs value in format: xe-n, x is an integer or decimal number, n = 0..9";
    //          default "10e-3";
    //          type string {
    //          }
    //        }
    //        leaf threshold-24hrs {
    //          description "FEC Corrected-Errs value in format: xe-n, x is an integer or decimal number, n = 0..9";
    //          default "10e-3";
    //          type string {
    //          }
    //        }
    //      }
    //      container fec-ucorrected-words-high-tca {
    //        description "FEC UCorrected Words High Threshold crossing defect trigger";
    //        // uses apply-advanced;
    //        choice enable-tca-choice {
    //          leaf enable-tca {
    //            description "Enable the FEC UCorrected Words threshold crossing alert";
    //            type empty;
    //          }
    //          leaf no-enable-tca {
    //            description "Don't enable the FEC UCorrected Words threshold crossing alert";
    //            type empty;
    //          }
    //        }
    //        leaf threshold {
    //          description "FEC UCorrected-Words value in format: xe-n, x is an integer or decimal number, n = 0..9";
    //          default "10e-3";
    //          type string {
    //          }
    //        }
    //        leaf threshold-24hrs {
    //          description "FEC UCorrected-Words value in format: xe-n, x is an integer or decimal number, n = 0..9";
    //          default "10e-3";
    //          type string {
    //          }
    //        }
    //      }
    //      container laser-frequency-error-high-tca {
    //        description "Laser frequency error high TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute frequency error high TCA in MHz";
    //          type string {
    //          }
    //        }
    //        leaf threshold-24hrs {
    //          description "Threshold for 24 hour frequency error high TCA in MHz";
    //          type string {
    //          }
    //        }
    //      }
    //      container laser-frequency-error-low-tca {
    //        description "Laser frequency error low TCA";
    //        // uses apply-advanced;
    //        choice enable-tca-choice {
    //          leaf enable-tca {
    //            description "Enable tca";
    //            type empty;
    //          }
    //          leaf no-enable-tca {
    //            description "Don't enable tca";
    //            type empty;
    //          }
    //        }
    //        leaf threshold {
    //          description "Threshold for 15 minute frequency error low TCA in MHz";
    //          type string {
    //          }
    //        }
    //        leaf threshold-24hrs {
    //          description "Threshold for 24 hour frequency error low TCA in MHz";
    //          type string {
    //          }
    //        }
    //      }
    //    }
    //    list warning {
    //      key name;
    //      ordered-by user;
    //      description "Set optic warnings";
    //      leaf name {
    //        type enumeration {
    //          enum "low-light-warning" {
    //            description "Enable low light warning";
    //          }
    //        }
    //      }
    //      // uses apply-advanced;
    //      choice actiontype {
    //        case case_1 {
    //          leaf syslog {
    //            description "Set action as syslog";
    //            type empty;
    //          }
    //        }
    //        case case_2 {
    //          leaf link-down {
    //            description "Set action as link-down";
    //            type empty;
    //          }
    //        }
    //      }
    //    }
    //    leaf low-power-mode {
    //      description "Force optics to low power mode";
    //      type empty;
    //    }
    //    leaf host-side-fec {
    //      description "Host side optics FEC ON/OFF";
    //      type enumeration {
    //        enum "off" {
    //          description "Host side FEC OFF for optics";
    //        }
    //        enum "on" {
    //          description "Host side FEC ON for optics";
    //        }
    //      }
    //    }
    //    leaf media-side-fec {
    //      description "Media side FEC ON/OFF";
    //      type enumeration {
    //        enum "off" {
    //          description "Media side FEC OFF for optics";
    //        }
    //        enum "on" {
    //          description "Media side FEC ON for optics";
    //        }
    //      }
    //    }
    //    choice lane-info {
    //      case case_1 {
    //        list lane {
    //          key name;
    //          description "Media lane number";
    //          leaf name {
    //            description "Lane number";
    //            type union {
    //              type string {
    //                pattern "<.*>|$.*";
    //              }
    //              type uint32 {
    //                range "0 .. 7";
    //              }
    //            }
    //          }
    //          // uses apply-advanced;
    //          leaf tx-laser {
    //            description "Transmit Laser ON/OFF";
    //            type enumeration {
    //              enum "off" {
    //                description "Transmit laser OFF for optics";
    //              }
    //              enum "on" {
    //                description "Transmit laser ON for optics";
    //              }
    //            }
    //          }
    //          leaf rx-output {
    //            description "Receive output ON/OFF";
    //            type enumeration {
    //              enum "off" {
    //                description "Receive output OFF for optics";
    //              }
    //              enum "on" {
    //                description "Receive output ON for optics";
    //              }
    //            }
    //          }
    //          leaf tx-cdr {
    //            description "Transmit Clock and Data Recovery ON/OFF";
    //            type enumeration {
    //              enum "off" {
    //                description "Transmit Clock and Data Recovery OFF for optics";
    //              }
    //              enum "on" {
    //                description "Transmit Clock and Data Recovery ON for optics";
    //              }
    //            }
    //          }
    //          leaf rx-cdr {
    //            description "Receive Clock and Data Recovery ON/OFF";
    //            type enumeration {
    //              enum "off" {
    //                description "Receive Clock and Data Recovery OFF for optics";
    //              }
    //              enum "on" {
    //                description "Receive Clock and Data Recovery ON for optics";
    //              }
    //            }
    //          }
    //          leaf tx-input-equalization-adaptive {
    //            description "Transmit adaptive equalization ON/OFF";
    //            type enumeration {
    //              enum "off" {
    //                description "Transmit adaptive equalization OFF for optics";
    //              }
    //              enum "on" {
    //                description "Transmit adaptive equalization ON for optics";
    //              }
    //            }
    //          }
    //          leaf tx-input-equalization-manual {
    //            description "Transmit manual equalization for optics";
    //            units "dB";
    //            type union {
    //              type string {
    //                pattern "<.*>|$.*";
    //              }
    //              type int32 {
    //                range "0 .. 15";
    //              }
    //            }
    //          }
    //          leaf rx-output-emphasis {
    //            description "Receive output emphasis for optics";
    //            units "dB";
    //            type union {
    //              type string {
    //                pattern "<.*>|$.*";
    //              }
    //              type int32 {
    //                range "0 .. 15";
    //              }
    //            }
    //          }
    //          leaf rx-output-amplitude {
    //            description "Receive output amplitude setting";
    //            type enumeration {
    //              enum "400mV" {
    //                description "No equalization for 100mV - 400mV amplitude";
    //              }
    //              enum "600mV" {
    //                description "No equalization for 300mV - 600mV amplitude";
    //              }
    //              enum "800mV" {
    //                description "No equalization for 400mV - 800mV amplitude";
    //              }
    //              enum "1200mV" {
    //                description "No equalization for 600mV - 1200mV amplitude";
    //              }
    //            }
    //          }
    //          leaf tx-squelch {
    //            description "Transmit squelch ON/OFF";
    //            type enumeration {
    //              enum "off" {
    //                description "Transmit squelch OFF for optics";
    //              }
    //              enum "on" {
    //                description "Transmit squelch ON for optics";
    //              }
    //            }
    //          }
    //          leaf rx-squelch {
    //            description "Receive squelch ON/OFF";
    //            type enumeration {
    //              enum "off" {
    //                description "Receive squelch OFF for optics";
    //              }
    //              enum "on" {
    //                description "Receive squelch ON for optics";
    //              }
    //            }
    //          }
    //          leaf tx-rate-select {
    //            description "Transmit rate select for optics";
    //            type union {
    //              type string {
    //                pattern "<.*>|$.*";
    //              }
    //              type int32 {
    //                range "0 .. 3";
    //              }
    //            }
    //          }
    //          leaf rx-rate-select {
    //            description "Receive rate select for optics";
    //            type union {
    //              type string {
    //                pattern "<.*>|$.*";
    //              }
    //              type int32 {
    //                range "0 .. 3";
    //              }
    //            }
    //          }
    //        }
    //      }
    //      case case_2 {
    //        container lane-all {
    //          presence "enable lane-all";
    //          description "Apply settings to all lane";
    //          // uses apply-advanced;
    //          leaf tx-laser {
    //            description "Transmit Laser ON/OFF";
    //            type enumeration {
    //              enum "off" {
    //                description "Transmit laser OFF for optics";
    //              }
    //              enum "on" {
    //                description "Transmit laser ON for optics";
    //              }
    //            }
    //          }
    //          leaf rx-output {
    //            description "Receive output ON/OFF";
    //            type enumeration {
    //              enum "off" {
    //                description "Receive output OFF for optics";
    //              }
    //              enum "on" {
    //                description "Receive output ON for optics";
    //              }
    //            }
    //          }
    //          leaf tx-cdr {
    //            description "Transmit Clock and Data Recovery ON/OFF";
    //            type enumeration {
    //              enum "off" {
    //                description "Transmit Clock and Data Recovery OFF for optics";
    //              }
    //              enum "on" {
    //                description "Transmit Clock and Data Recovery ON for optics";
    //              }
    //            }
    //          }
    //          leaf rx-cdr {
    //            description "Receive Clock and Data Recovery ON/OFF";
    //            type enumeration {
    //              enum "off" {
    //                description "Receive Clock and Data Recovery OFF for optics";
    //              }
    //              enum "on" {
    //                description "Receive Clock and Data Recovery ON for optics";
    //              }
    //            }
    //          }
    //          leaf tx-input-equalization-adaptive {
    //            description "Transmit adaptive equalization ON/OFF";
    //            type enumeration {
    //              enum "off" {
    //                description "Transmit adaptive equalization OFF for optics";
    //              }
    //              enum "on" {
    //                description "Transmit adaptive equalization ON for optics";
    //              }
    //            }
    //          }
    //          leaf tx-input-equalization-manual {
    //            description "Transmit manual equalization for optics";
    //            units "dB";
    //            type union {
    //              type string {
    //                pattern "<.*>|$.*";
    //              }
    //              type int32 {
    //                range "0 .. 15";
    //              }
    //            }
    //          }
    //          leaf rx-output-emphasis {
    //            description "Receive output emphasis for optics";
    //            units "dB";
    //            type union {
    //              type string {
    //                pattern "<.*>|$.*";
    //              }
    //              type int32 {
    //                range "0 .. 15";
    //              }
    //            }
    //          }
    //          leaf rx-output-amplitude {
    //            description "Receive output amplitude setting";
    //            type enumeration {
    //              enum "400mV" {
    //                description "No equalization for 100mV - 400mV amplitude";
    //              }
    //              enum "600mV" {
    //                description "No equalization for 300mV - 600mV amplitude";
    //              }
    //              enum "800mV" {
    //                description "No equalization for 400mV - 800mV amplitude";
    //              }
    //              enum "1200mV" {
    //                description "No equalization for 600mV - 1200mV amplitude";
    //              }
    //            }
    //          }
    //          leaf tx-squelch {
    //            description "Transmit squelch ON/OFF";
    //            type enumeration {
    //              enum "off" {
    //                description "Transmit squelch OFF for optics";
    //              }
    //              enum "on" {
    //                description "Transmit squelch ON for optics";
    //              }
    //            }
    //          }
    //          leaf rx-squelch {
    //            description "Receive squelch ON/OFF";
    //            type enumeration {
    //              enum "off" {
    //                description "Receive squelch OFF for optics";
    //              }
    //              enum "on" {
    //                description "Receive squelch ON for optics";
    //              }
    //            }
    //          }
    //          leaf tx-rate-select {
    //            description "Transmit rate select for optics";
    //            type union {
    //              type string {
    //                pattern "<.*>|$.*";
    //              }
    //              type int32 {
    //                range "0 .. 3";
    //              }
    //            }
    //          }
    //          leaf rx-rate-select {
    //            description "Receive rate select for optics";
    //            type union {
    //              type string {
    //                pattern "<.*>|$.*";
    //              }
    //              type int32 {
    //                range "0 .. 3";
    //              }
    //            }
    //          }
    //        }
    //      }
    //    }
    //  }
    //  container otn-options {
    //    description "Optical Transmission Network interface-specific options";
    //    uses otn_options_type;
    //  }
    //  container tdm-options {
    //    description "Time division multiplexing (TDM) interface-specific options";
    //    uses tdm_options_type;
    //  }
    //  container och-options {
    //    description "Optical channel configuration options";
    //    uses och-attributes;
    //  }
    //  container otu-options {
    //    description "Optical transmission unit configuration options";
    //    uses otu-attributes;
    //  }
    //  container odu-options {
    //    description "Optical data unit configuration options";
    //    uses odu-attributes;
    //  }
    //  container ett-options {
    //    description "Transport ethernet client configuration options";
    //    uses ett-attributes;
    //  }
    //  container fastether-options {
    //    description "Fast Ethernet interface-specific options";
    //    // uses apply-advanced;
    //    choice loopback-choice {
    //      leaf loopback {
    //        description "Enable loopback";
    //        type empty;
    //      }
    //      leaf no-loopback {
    //        description "Don't enable loopback";
    //        type empty;
    //      }
    //    }
    //    choice flow-control-choice {
    //      leaf flow-control {
    //        description "Enable flow control";
    //        type empty;
    //      }
    //      leaf no-flow-control {
    //        description "Don't enable flow control";
    //        type empty;
    //      }
    //    }
    //    choice source-filtering-choice {
    //      leaf source-filtering {
    //        description "Enable source address filtering";
    //        type empty;
    //      }
    //      leaf no-source-filtering {
    //        description "Don't enable source address filtering";
    //        type empty;
    //      }
    //    }
    //    leaf ingress-rate-limit {
    //      description "Ingress rate at port";
    //      units "megabits per second";
    //      type union {
    //        type string {
    //          pattern "<.*>|$.*";
    //        }
    //        type uint32 {
    //          range "1 .. 100";
    //        }
    //      }
    //    }
    //    list source-address-filter {
    //      key name;
    //      ordered-by user;
    //      description "Source address filters";
    //      leaf name {
    //        description "Remote MAC address";
    //        type jt:mac-addr;
    //      }
    //    }
    //    container redundant-parent {
    //      description " Parent of this interface";
    //      // uses apply-advanced;
    //      leaf parent {
    //        description "Join a redundant ethernet interface";
    //        type union {
    //          type jt:interface-device;
    //          type string {
    //            pattern "<.*>|$.*";
    //          }
    //        }
    //      }
    //    }
    //    container ieee-802.3ad {
    //      description "IEEE 802.3ad";
    //      // uses apply-advanced;
    //      container lacp {
    //        description "Link Aggregation Control Protocol configuration";
    //        // uses apply-advanced;
    //        leaf port-priority {
    //          description "Priority of the port (0 ... 65535)";
    //          type union {
    //            type uint16;
    //            type string {
    //              pattern "<.*>|$.*";
    //            }
    //          }
    //        }
    //      }
    //      leaf bundle {
    //        description "Join an aggregated Ethernet interface";
    //        type union {
    //          type jt:interface-device;
    //          type string {
    //            pattern "<.*>|$.*";
    //          }
    //        }
    //      }
    //      choice type {
    //        case case_1 {
    //          leaf primary {
    //            description "Primary interface for link-protection mode";
    //            type empty;
    //          }
    //        }
    //        case case_2 {
    //          leaf backup {
    //            description "Backup interface for link-protection mode";
    //            type empty;
    //          }
    //        }
    //      }
    //    }
    //    container mpls {
    //      description "MPLS options";
    //      uses mpls_ifd_options;
    //    }
    //    leaf ignore-l3-incompletes {
    //      description "Ignore L3 incomplete errors";
    //      type empty;
    //    }
    //  }
    //  container redundant-ether-options {
    //    description "Ethernet redundancy options";
    //    // uses apply-advanced;
    //    leaf redundancy-group {
    //      description "Redundancy group of this interface";
    //      type union {
    //        type string {
    //          pattern "<.*>|$.*";
    //        }
    //        type uint16 {
    //          range "1 .. 128";
    //        }
    //      }
    //    }
    //    choice loopback-choice {
    //      leaf loopback {
    //        description "Enable loopback";
    //        type empty;
    //      }
    //      leaf no-loopback {
    //        description "Don't enable loopback";
    //        type empty;
    //      }
    //    }
    //    choice flow-control-choice {
    //      leaf flow-control {
    //        description "Enable flow control";
    //        type empty;
    //      }
    //      leaf no-flow-control {
    //        description "Don't enable flow control";
    //        type empty;
    //      }
    //    }
    //    choice source-filtering-choice {
    //      leaf source-filtering {
    //        description "Enable source address filtering";
    //        type empty;
    //      }
    //      leaf no-source-filtering {
    //        description "Don't enable source address filtering";
    //        type empty;
    //      }
    //    }
    //    list source-address-filter {
    //      key name;
    //      ordered-by user;
    //      description "Source address filters";
    //      leaf name {
    //        description "Remote MAC address";
    //        type jt:mac-addr;
    //      }
    //    }
    //    leaf link-speed {
    //      description "Link speed of individual interface that joins the RETH";
    //      type enumeration {
    //        enum "10m" {
    //          description "Links are 10M";
    //        }
    //        enum "100m" {
    //          description "Links are 100M";
    //        }
    //        enum "1g" {
    //          description "Links are 1G";
    //        }
    //        enum "10g" {
    //          description "Links are 10G";
    //        }
    //        enum "25g" {
    //          description "Links are 25G";
    //        }
    //      }
    //    }
    //    leaf minimum-links {
    //      description "Minimum number of active links";
    //      default "1";
    //      type union {
    //        type string {
    //          pattern "<.*>|$.*";
    //        }
    //        type uint16 {
    //          range "1 .. 8";
    //        }
    //      }
    //    }
    //    container lacp {
    //      description "Link Aggregation Control Protocol configuration";
    //      // uses apply-advanced;
    //      choice mode {
    //        case case_1 {
    //          leaf active {
    //            description "Initiate transmission of LACP packets";
    //            type empty;
    //          }
    //        }
    //        case case_2 {
    //          leaf passive {
    //            description "Respond to LACP packets";
    //            type empty;
    //          }
    //        }
    //      }
    //      leaf periodic {
    //        description "Timer interval for periodic transmission of LACP packets";
    //        type enumeration {
    //          enum "fast" {
    //            description "Receive packets every second";
    //          }
    //          enum "slow" {
    //            description "Receive packets every 30 seconds";
    //          }
    //        }
    //      }
    //    }
    //  }
     container aggregated-ether-options {
       description "Aggregated Ethernet interface-specific options";
       // uses apply-advanced;
       choice loopback-choice {
         leaf loopback {
           description "Enable loopback";
           type empty;
         }
         leaf no-loopback {
           description "Don't enable loopback";
           type empty;
         }
       }
      //  choice flow-control-choice {
      //    leaf flow-control {
      //      description "Enable flow control";
      //      type empty;
      //    }
      //    leaf no-flow-control {
      //      description "Don't enable flow control";
      //      type empty;
      //    }
      //  }
       choice source-filtering-choice {
         leaf source-filtering {
           description "Enable source address filtering";
           type empty;
         }
         leaf no-source-filtering {
           description "Don't enable source address filtering";
           type empty;
         }
       }
      //  leaf autostate-exclude {
      //    description "Interface will not contribute to IRB state";
      //    type empty;
      //  }
      //  container link-protection {
      //    presence "enable link-protection";
      //    description "Enable link protection mode";
      //    // uses apply-advanced;
      //    leaf revertive {
      //      description "Revert back from active backup link to primary, if primary is UP";
      //      type empty;
      //    }
      //    leaf non-revertive {
      //      description "Do not revert back (default mode) from active backup link to primary, if primary is UP";
      //      type empty;
      //    }
      //    leaf backup-state {
      //      description "Link protection backup link state";
      //      default "accept-data";
      //      type enumeration {
      //        enum "accept-data" {
      //          description "Accept data on receive channel of backup link";
      //        }
      //        enum "discard-data" {
      //          description "Discard data on receive channel of backup link";
      //        }
      //        enum "down" {
      //          description "Backup link is marked down";
      //        }
      //      }
      //    }
      //    container rtg-config {
      //      presence "enable rtg-config";
      //      description "RTG enable on AE";
      //      // uses apply-advanced;
      //      leaf preempt-cutover-timer {
      //        description "RTG preempt-cutover-timer in seconds";
      //        default "1";
      //        type union {
      //          type string {
      //            pattern "<.*>|$.*";
      //          }
      //          type uint32 {
      //            range "0 .. 255";
      //          }
      //        }
      //      }
      //    }
      //  }
      //  choice fcoe-lag-choice {
      //    leaf fcoe-lag {
      //      description "Enable FIP/FCoE LAG";
      //      type empty;
      //    }
      //    leaf no-fcoe-lag {
      //      description "Don't enable FIP/FCoE LAG";
      //      type empty;
      //    }
      //  }
       list source-address-filter {
         key name;
         ordered-by user;
         description "Source address filters";
         leaf name {
           description "Remote MAC address";
           type jt:mac-addr;
         }
       }
      //  container load-balance {
      //    uses aggregate-load-balance;
      //  }
       container bfd-liveness-detection {
         description "Bidirectional Forwarding Detection (BFD) options";
         // uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 9000";
             }
           }
         }
         choice adaptation-choice {
           case case_1 {
             leaf no-adaptation {
               description "Disable adaptation";
               type empty;
             }
           }
         }
         container transmit-interval {
           description "Transmit-interval options";
           // uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           // uses apply-advanced;
           leaf threshold {
             description "High detection-time triggering a trap";
             units "milliseconds";
             type union {
               type uint32;
               type string {
                 pattern "<.*>|$.*";
               }
             }
           }
         }
         container authentication {
           description "Authentication options";
           // uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         container damping {
           description "BFD flap damping parameters";
           // uses apply-advanced;
           leaf suppress {
             description "Suppress threshold for figure-of-merit value";
             default "5000";
             type union {
               type string {
                 pattern "<.*>|$.*";
               }
               type uint32 {
                 range "1000 .. 200000";
               }
             }
           }
           leaf reuse {
             description "Reuse threshold for figure-of-merit value";
             default "1000";
             type union {
               type string {
                 pattern "<.*>|$.*";
               }
               type uint32 {
                 range "1000 .. 200000";
               }
             }
           }
           leaf max-suppress-time {
             description "Maximum hold-down time";
             default "600";
             units "seconds";
             type union {
               type string {
                 pattern "<.*>|$.*";
               }
               type uint32 {
                 range "1 .. 20000";
               }
             }
           }
           leaf half-life-interval {
             description "Decay half life interval";
             default "30";
             units "seconds";
             type union {
               type string {
                 pattern "<.*>|$.*";
               }
               type uint32 {
                 range "1 .. 600";
               }
             }
           }
           leaf increment {
             description "Increments applied to figure-of-merit value for every flap";
             default "1000";
             type union {
               type string {
                 pattern "<.*>|$.*";
               }
               type uint32 {
                 range "1000 .. 20000";
               }
             }
           }
         }
         leaf neighbor {
           description "BFD neighbor address";
           type jt:ipaddr;
         }
         leaf local-address {
           description "BFD local address";
           type jt:ipaddr;
         }
         leaf holddown-interval {
           description "Time to hold the session-UP notification to the client";
           units "milliseconds";
           type union {
             type string {
               pattern "<.*>|$.*";
             }
             type uint32 {
               range "0 .. 255000";
             }
           }
         }
       }
       leaf minimum-links {
         description "Minimum number of aggregated links";
         type union {
           type string {
             pattern "<.*>|$.*";
           }
           type uint16;
         }
       }
       container minimum-bandwidth {
         presence "enable minimum-bandwidth";
         description "Minimum bandwidth configured for aggregated bundle";
         // uses apply-advanced;
         leaf bw-value {
           description "Bandwidth value";
           default "1";
           type union {
             type uint64;
             type string {
               pattern "<.*>|$.*";
             }
           }
         }
         leaf bw-unit {
           description "Bandwidth unit";
           type enumeration {
             enum "bps" {
               description "Links are in bits per sec";
             }
             enum "kbps" {
               description "Links are in kilo bits per sec";
             }
             enum "mbps" {
               description "Links are in mega bits per sec";
             }
             enum "gbps" {
               description "Links are in giga bits per sec ";
             }
           }
         }
       }
       container targeted-options {
         presence "enable targeted-options";
         description "Targeting specific options";
         // uses apply-advanced;
         leaf type {
           description "Targeting type of AE bundle";
           type enumeration {
             enum "auto" {
               description "Targeting type is Auto";
             }
             enum "manual" {
               description "Targeting type is Manual";
             }
           }
         }
         choice redundancy_choice {
           case case_1 {
             leaf logical-interface-fpc-redundancy {
               description "Enable FPC redundancy for logical interfaces";
               type empty;
             }
           }
           case case_2 {
             leaf logical-interface-chassis-redundancy {
               description "Enable CHASSIS redundancy for logical interfaces";
               type empty;
             }
           }
         }
         container rebalance-periodic {
           presence "enable rebalance-periodic";
           // uses apply-advanced;
           leaf start-time {
             description "Start time of the rebalance operation ( Wall clock time )";
             type jt:time-of-day;
           }
           leaf interval {
             description "Interval of the rebalance operation in hrs";
             type union {
               type string {
                 pattern "<.*>|$.*";
               }
               type uint32 {
                 range "1 .. 24";
               }
             }
           }
         }
         leaf rebalance-subscriber-granularity {
           description "Max subscriber aggregate weight";
           type union {
             type string {
               pattern "<.*>|$.*";
             }
             type uint32 {
               range "1 .. 65535";
             }
           }
         }
       }
       choice redundancy_choice {
         case case_1 {
           leaf logical-interface-fpc-redundancy {
             description "Enable FPC redundancy for logical interfaces";
             type empty;
           }
         }
         case case_2 {
           leaf logical-interface-chassis-redundancy {
             description "Enable CHASSIS redundancy for logical interfaces";
             type empty;
           }
         }
       }
      //  container rebalance-periodic {
      //    // uses apply-advanced;
      //    leaf start-time {
      //      description "Start time of the rebalance operation ( Wall clock time )";
      //      type jt:time-of-day;
      //    }
      //    leaf interval {
      //      description "Interval of the rebalance operation in hrs";
      //      type union {
      //        type string {
      //          pattern "<.*>|$.*";
      //        }
      //        type uint32 {
      //          range "1 .. 24";
      //        }
      //      }
      //    }
      //  }
      //  leaf pad-to-minimum-frame-size {
      //    description "Pad Tx vlan tagged frame to minimum of 68 bytes";
      //    type empty;
      //  }
       leaf link-speed {
         description "Link speed of individual interface that joins the AE";
         type enumeration {
           enum "10m" {
             description "Links are 10M";
           }
           enum "100m" {
             description "Links are 100M";
           }
           enum "1g" {
             description "Links are 1G";
           }
           enum "2.5g" {
             description "Links are 2.5G";
           }
           enum "5g" {
             description "Links are 5G";
           }
           enum "8g" {
             description "Links are 8G";
           }
           enum "10g" {
             description "Links are 10G";
           }
           enum "25g" {
             description "Links are 25G";
           }
           enum "40g" {
             description "Links are 40G";
           }
           enum "50g" {
             description "Links are 50G";
           }
           enum "80g" {
             description "Links are 80G";
           }
           enum "100g" {
             description "Links are 100G";
           }
           enum "200g" {
             description "Links are 200G";
           }
           enum "400g" {
             description "Links are 400G";
           }
           enum "800g" {
             description "Links are 800G";
           }
           enum "oc192" {
             description "Links are OC-192";
           }
           enum "mixed" {
             description "Links are various speeds";
           }
         }
       }
       container local-bias {
         presence "enable local-bias";
         description "Turn on local bias functionality";
         // uses apply-advanced;
         leaf disable {
           description "Disable local-bias";
           type empty;
         }
       }
       leaf resilient-hash {
         description "Turn on resilient-hash";
         type empty;
       }
      //  container dlb {
      //    description "Enable DLB on LAG";
      //    // uses apply-advanced;
      //    choice mode {
      //      case case_1 {
      //        leaf per-packet {
      //          description "Per-packet link assignment";
      //          type empty;
      //        }
      //      }
      //      case case_2 {
      //        leaf assigned-flow {
      //          description "Fixed link assignment";
      //          type empty;
      //        }
      //      }
      //      case case_3 {
      //        container flowlet {
      //          presence "enable flowlet";
      //          description "Inactivity-based link assignment";
      //          // uses apply-advanced;
      //          leaf inactivity-interval {
      //            description " Minimum inactivity interval in micro-seconds for link re-assignment";
      //            default "256";
      //            type union {
      //              type string {
      //                pattern "<.*>|$.*";
      //              }
      //              type uint32;
      //            }
      //          }
      //        }
      //      }
      //    }
      //  }
      //  container lacp {
      //    description "Link Aggregation Control Protocol configuration";
      //    // uses apply-advanced;
      //    choice mode {
      //      case case_1 {
      //        leaf active {
      //          description "Initiate transmission of LACP packets";
      //          type empty;
      //        }
      //      }
      //      case case_2 {
      //        leaf passive {
      //          description "Respond to LACP packets";
      //          type empty;
      //        }
      //      }
      //    }
      //    leaf periodic {
      //      description "Timer interval for periodic transmission of LACP packets";
      //      type enumeration {
      //        enum "fast" {
      //          description "Receive packets every second";
      //        }
      //        enum "slow" {
      //          description "Receive packets every 30 seconds";
      //        }
      //      }
      //    }
      //    leaf multiplier {
      //      description "LACP timeout detection multiplier";
      //      type union {
      //        type string {
      //          pattern "<.*>|$.*";
      //        }
      //        type uint32 {
      //          range "3 .. 30";
      //        }
      //      }
      //    }
      //   //  leaf fast-failover {
      //   //    description "To turn on LACP fast-failover";
      //   //    type empty;
      //   //  }
      //   //  container link-protection {
      //   //    presence "enable link-protection";
      //   //    // uses apply-advanced;
      //   //    leaf disable {
      //   //      description "To turn off LACP link-protection";
      //   //      type empty;
      //   //    }
      //   //    choice mode {
      //   //      case case_1 {
      //   //        leaf revertive {
      //   //          description "Switch links when better priority link comes up";
      //   //          type empty;
      //   //        }
      //   //      }
      //   //      case case_2 {
      //   //        leaf non-revertive {
      //   //          description "Do not switch links when better priority link comes up";
      //   //          type empty;
      //   //        }
      //   //      }
      //   //    }
      //   //    container rtg-config {
      //   //      presence "enable rtg-config";
      //   //      description "RTG Feature enable on AE";
      //   //      // uses apply-advanced;
      //   //      leaf preempt-cutover-timer {
      //   //        description "RTG preempt-cutover-timer in seconds";
      //   //        default "1";
      //   //        type union {
      //   //          type string {
      //   //            pattern "<.*>|$.*";
      //   //          }
      //   //          type uint32 {
      //   //            range "0 .. 255";
      //   //          }
      //   //        }
      //   //      }
      //   //    }
      //   //  }
      //   //  leaf accept-data {
      //   //    description "Keep receiving traffic even when LACP goes down";
      //   //    type empty;
      //   //  }
      //   //  leaf sync-reset {
      //   //    description "On minimum-link failure notify out of sync to peer";
      //   //    type enumeration {
      //   //      enum "disable" {
      //   //        description "To disable minimum-link failure handling at LACP level";
      //   //      }
      //   //      enum "enable" {
      //   //        description "To enable minimum-link failure handling at LACP level";
      //   //      }
      //   //    }
      //   //  }
      //   //  leaf system-priority {
      //   //    description "Priority of the system (0 ... 65535)";
      //   //    type string;
      //   //  }
      //   //  leaf system-id {
      //   //    description "Node's System ID, encoded as a MAC address";
      //   //    type jt:mac-addr;
      //   //  }
      //   //  leaf admin-key {
      //   //    description "Node's administrative key";
      //   //    type union {
      //   //      type uint16;
      //   //      type string {
      //   //        pattern "<.*>|$.*";
      //   //      }
      //   //    }
      //   //  }
      //   //  container hold-time {
      //   //    description "Hold time for link up and link down for AE link members";
      //   //    leaf up {
      //   //      description "Link up hold time for the AE link members";
      //   //      units "seconds";
      //   //      type union {
      //   //        type string {
      //   //          pattern "<.*>|$.*";
      //   //        }
      //   //        type uint16 {
      //   //          range "1 .. 6000";
      //   //        }
      //   //      }
      //   //    }
      //   //  }
      //   //  leaf aggregate-wait-time {
      //   //    description "Aggregate wait time for the AE";
      //   //    units "seconds";
      //   //    type union {
      //   //      type string {
      //   //        pattern "<.*>|$.*";
      //   //      }
      //   //      type uint16 {
      //   //        range "0 .. 1800";
      //   //      }
      //   //    }
      //   //  }
      //   //  leaf force-up {
      //   //    description "Forceup AE interface with LACP";
      //   //    type empty;
      //   //  }
      //   //  leaf no-peer-loopback-validation {
      //   //    description "Skip MCLAG peer loop back validation for LACP PDUs on Forceup AE interface";
      //   //    type empty;
      //   //  }
      //  }
      //  list link-protection-sub-group {
      //    key name;
      //    ordered-by user;
      //    description "Link Protection subgroup configuration";
      //    leaf name {
      //      description "Name of the subgroup";
      //      type string {
      //        length "2 .. 64";
      //      }
      //    }
      //    // uses apply-advanced;
      //    choice type {
      //      case case_1 {
      //        leaf primary {
      //          description "Primary subgroup for N:N link-protection mode";
      //          type empty;
      //        }
      //      }
      //      case case_2 {
      //        leaf backup {
      //          description "Backup subgroup for N:N link-protection mode";
      //          type empty;
      //        }
      //      }
      //    }
      //  }
      //  container ethernet-switch-profile {
      //    description "Ethernet virtual LAN/media access control-level options";
      //    // uses apply-advanced;
      //    leaf-list tag-protocol-id {
      //      ordered-by user;
      //      description "IEEE 802.1q Tag Protocol Identifier values for VLAN-tagged frames";
      //      type string;
      //    }
      //    container storm-control {
      //      description "Storm control profile name to bind";
      //      // uses apply-advanced;
      //      leaf profile-name {
      //        description "Profile name";
      //        type string;
      //      }
      //    }
      //    leaf mac-learn-enable {
      //      description "Learn MAC addresses dynamically";
      //      type empty;
      //    }
      //  }
      //  container mc-ae {
      //    description "Multi-chassis aggregation (MC-AE) network device configuration";
      //    // uses apply-advanced;
      //    leaf mc-ae-id {
      //      description "MC-AE group id";
      //      type union {
      //        type string {
      //          pattern "<.*>|$.*";
      //        }
      //        type uint16 {
      //          range "1 .. 65535";
      //        }
      //      }
      //    }
      //   //  leaf redundancy-group {
      //   //    description "Redundancy group id";
      //   //    type union {
      //   //      type string {
      //   //        pattern "<.*>|$.*";
      //   //      }
      //   //      type uint32 {
      //   //        range "1 .. 4294967294";
      //   //      }
      //   //    }
      //   //  }
      //   //  leaf chassis-id {
      //   //    description "Chassis id of MC-AE network device";
      //   //    type union {
      //   //      type string {
      //   //        pattern "<.*>|$.*";
      //   //      }
      //   //      type uint16 {
      //   //        range "0 .. 1";
      //   //      }
      //   //    }
      //   //  }
      //   //  leaf mode {
      //   //    description "Mode of the MC-AE";
      //   //    type enumeration {
      //   //      enum "active-standby" {
      //   //        description "MC-AE in active-standby mode";
      //   //      }
      //   //      enum "active-active" {
      //   //        description "MC-AE in active-active mode";
      //   //      }
      //   //    }
      //   //  }
      //   //  leaf status-control {
      //   //    description "Status of the MC-AE chassis";
      //   //    type enumeration {
      //   //      enum "active" {
      //   //        description "Chassis is Active";
      //   //      }
      //   //      enum "standby" {
      //   //        description "Chassis is Standby";
      //   //      }
      //   //    }
      //   //  }
      //   //  leaf switchover-mode {
      //   //    description "Switchover mode";
      //   //    type enumeration {
      //   //      enum "revertive" {
      //   //        description "Switch mcae node when preferred link comes up";
      //   //      }
      //   //      enum "non-revertive" {
      //   //        description "Do not switch mcae node when preferred link comes up";
      //   //      }
      //   //    }
      //   //  }
      //   //  leaf revert-time {
      //   //    description "Wait interval before performing switchover";
      //   //    default "3";
      //   //    units "minute";
      //   //    type union {
      //   //      type string {
      //   //        pattern "<.*>|$.*";
      //   //      }
      //   //      type uint32 {
      //   //        range "1 .. 10";
      //   //      }
      //   //    }
      //   //  }
      //   //  leaf init-delay-time {
      //   //    description "Init delay timer for mcae sm for min traffic loss";
      //   //    units "seconds";
      //   //    type union {
      //   //      type string {
      //   //        pattern "<.*>|$.*";
      //   //      }
      //   //      type uint16 {
      //   //        range "1 .. 6000";
      //   //      }
      //   //    }
      //   //  }
      //   //  leaf recovery-delay-time {
      //   //    description "Delay timer for bringing up ICL, ICCP";
      //   //    units "seconds";
      //   //    type union {
      //   //      type string {
      //   //        pattern "<.*>|$.*";
      //   //      }
      //   //      type uint16 {
      //   //        range "1 .. 6000";
      //   //      }
      //   //    }
      //   //  }
      //   //  leaf enhanced-convergence {
      //   //    description "Optimized convergence time for mcae";
      //   //    type empty;
      //   //  }
      //   //  container events {
      //   //    presence "enable events";
      //   //    description "MCAE related events";
      //   //    // uses apply-advanced;
      //   //    container iccp-peer-down {
      //   //      presence "enable iccp-peer-down";
      //   //      description "Define behavior in the event of ICCP peer down";
      //   //      // uses apply-advanced;
      //   //      leaf force-icl-down {
      //   //        description "Bring down ICL logical interface";
      //   //        type empty;
      //   //      }
      //   //      leaf prefer-status-control-active {
      //   //        description "Keep this node up (recommended only on status-control active)";
      //   //        type empty;
      //   //      }
      //   //    }
      //   //  }
      //  }
      //  leaf share-standby {
      //    description "Share the resources with standby ports, needs FPC reboot to take effect";
      //    type empty;
      //  }
     }
    //  container es-options {
    //    description "ES PIC interface-specific options";
    //    // uses apply-advanced;
    //    leaf backup-interface {
    //      description "Name of backup interface";
    //      type union {
    //        type jt:interface-device;
    //        type string {
    //          pattern "<.*>|$.*";
    //        }
    //      }
    //    }
    //  }
    //  container dsl-options {
    //    description "DSL interface-specific options";
    //    // uses apply-advanced;
    //    leaf operating-mode {
    //      description "DSL operating mode";
    //      type enumeration {
    //        enum "auto" {
    //          description "Autonegotiate mode";
    //        }
    //        enum "ansi-dmt" {
    //          description "ANSI T1.413 Issue II mode";
    //        }
    //        enum "itu-dmt" {
    //          description "ITU G.992.1 mode";
    //        }
    //        enum "etsi" {
    //          description "ETSI TS 101 388 V1.3.1 mode";
    //        }
    //        enum "itu-annexb-ur2" {
    //          description "ITU G.992.1 UR-2 mode";
    //        }
    //        enum "itu-annexb-non-ur2" {
    //          description "ITU G.992.1 Non UR-2 mode";
    //        }
    //        enum "itu-dmt-bis" {
    //          description "ITU G.992.3 mode";
    //        }
    //        enum "adsl2plus" {
    //          description "ITU G.992.5 mode";
    //        }
    //        enum "annexm-itu-dmt-bis" {
    //          description "AnnexM ITU G.992.3 mode";
    //        }
    //        enum "annexm-adsl2plus" {
    //          description "AnnexM ITU G.992.5 mode";
    //        }
    //      }
    //    }
    //  }
    //  container vdsl-options {
    //    description "VDSL interface-specific options";
    //    // uses apply-advanced;
    //    leaf vdsl-profile {
    //      description "VDSL profile";
    //      type enumeration {
    //        enum "auto" {
    //          description "Auto";
    //        }
    //        enum "8a" {
    //          description "Profile 8a";
    //        }
    //        enum "8b" {
    //          description "Profile 8b";
    //        }
    //        enum "8c" {
    //          description "Profile 8c";
    //        }
    //        enum "8d" {
    //          description "Profile 8d";
    //        }
    //        enum "12a" {
    //          description "Profile 12a";
    //        }
    //        enum "12b" {
    //          description "Profile 12b";
    //        }
    //        enum "17a" {
    //          description "Profile 17a";
    //        }
    //      }
    //    }
    //    leaf sra {
    //      description "DSL SRA";
    //      default "disable";
    //      type enumeration {
    //        enum "enable" {
    //          description "Enable SRA";
    //        }
    //        enum "disable" {
    //          description "Disable SRA";
    //        }
    //      }
    //    }
    //    leaf v43 {
    //      description "DSL V43 tones";
    //      default "enable";
    //      type enumeration {
    //        enum "enable" {
    //          description "Enable V43";
    //        }
    //        enum "disable" {
    //          description "Disable V43";
    //        }
    //      }
    //    }
    //    leaf sos {
    //      description "Enable SOS";
    //      type empty;
    //    }
    //  }
    //  container dsl-sfp-options {
    //    description "DSL SFP options";
    //    // uses apply-advanced;
    //    container adsl-options {
    //      description "ADSL options";
    //      // uses apply-advanced;
    //      leaf vpi {
    //        description "Virtual path identifier";
    //        type union {
    //          type string {
    //            pattern "<.*>|$.*";
    //          }
    //          type uint32 {
    //            range "0 .. 255";
    //          }
    //        }
    //      }
    //      leaf vci {
    //        description "Virtual circuit identifier";
    //        type union {
    //          type string {
    //            pattern "<.*>|$.*";
    //          }
    //          type uint32 {
    //            range "32 .. 65535";
    //          }
    //        }
    //      }
    //      leaf encap {
    //        description "Encapsulation";
    //        type enumeration {
    //          enum "bypass" {
    //            description "Bypass";
    //          }
    //          enum "llcsnap-bridged-802dot1q" {
    //            description "LLCSNAP bridged 802.1q";
    //          }
    //          enum "llcsnap-routed-ip" {
    //            description "LLCSNAP routed ip";
    //          }
    //          enum "vc-mux-bridged" {
    //            description "VC MUX bridged";
    //          }
    //          enum "vc-mux-routed-ip" {
    //            description "VC MUX routed ip";
    //          }
    //          enum "generic" {
    //            description "Generic";
    //          }
    //        }
    //      }
    //      leaf annex {
    //        description "Annex type";
    //        type enumeration {
    //          enum "auto" {
    //            description "Annex type auto";
    //          }
    //          enum "annexj-off" {
    //            description "Annex type annexj turn off";
    //          }
    //        }
    //      }
    //    }
    //    container vdsl-options {
    //      description "VDSL options";
    //      // uses apply-advanced;
    //      leaf profile {
    //        description "VDSL profile";
    //        type enumeration {
    //          enum "auto" {
    //            description "Automatic";
    //          }
    //          enum "8a" {
    //            description "Profile 8a";
    //          }
    //          enum "8b" {
    //            description "Profile 8b";
    //          }
    //          enum "8c" {
    //            description "Profile 8c";
    //          }
    //          enum "8d" {
    //            description "Profile 8d";
    //          }
    //          enum "12a" {
    //            description "Profile 12a";
    //          }
    //          enum "12b" {
    //            description "Profile 12b";
    //          }
    //          enum "17a" {
    //            description "Profile 17a";
    //          }
    //          enum "30a" {
    //            description "Profile 30a";
    //          }
    //        }
    //      }
    //      leaf carrier {
    //        description "Carrier setting";
    //        type enumeration {
    //          enum "auto" {
    //            description "Automatic";
    //          }
    //          enum "a43" {
    //            description "Carrier A43";
    //          }
    //          enum "b43" {
    //            description "Carrier B43";
    //          }
    //        }
    //      }
    //    }
    //    container gfast-options {
    //      description "G.fast options";
    //      // uses apply-advanced;
    //      leaf carrier {
    //        description "Carrier setting";
    //        type enumeration {
    //          enum "a43" {
    //            description "Carrier A43";
    //          }
    //          enum "a43c" {
    //            description "Carrier A43C";
    //          }
    //          enum "b43" {
    //            description "Carrier B43";
    //          }
    //          enum "b43c" {
    //            description "Carrier B43C";
    //          }
    //        }
    //      }
    //    }
    //  }
    //  container shdsl-options {
    //    description "SHDSL interface-specific options";
    //    // uses apply-advanced;
    //    leaf annex {
    //      description "Type of SHDSL annex";
    //      default "annex-b";
    //      type enumeration {
    //        enum "annex-a" {
    //          description "Annex-a PIC";
    //        }
    //        enum "annex-b" {
    //          description "Annex-b PIC";
    //        }
    //        enum "annex-f" {
    //          description "Annex-f PIC";
    //        }
    //        enum "annex-g" {
    //          description "Annex-g PIC";
    //        }
    //        enum "annex-auto" {
    //          description "Annex-auto PIC";
    //        }
    //      }
    //    }
    //    leaf line-rate {
    //      description "SHDSL line rate";
    //      type string;
    //    }
    //    leaf loopback {
    //      description "Loopback mode";
    //      type enumeration {
    //        enum "local" {
    //          description "Local loopback";
    //        }
    //        enum "remote" {
    //          description "Remote loopback";
    //        }
    //      }
    //    }
    //    container snr-margin {
    //      presence "enable snr-margin";
    //      description "Signal to noise ratio margin";
    //      // uses apply-advanced;
    //      leaf current {
    //        description "Current signal to noise ratio margin";
    //        units "dB";
    //        type string;
    //      }
    //      leaf snext {
    //        description "SNEXT signal to noise ratio margin";
    //        units "dB";
    //        type string;
    //      }
    //    }
    //  }
    //  container data-input {
    //    description "Configuration for drop-insert data input";
    //    // uses apply-advanced;
    //    choice input-choice {
    //      case case_1 {
    //        leaf system {
    //          description "Data sourced from system";
    //          type empty;
    //        }
    //      }
    //      case case_2 {
    //        leaf interface {
    //          description "Interface that acts as data source";
    //          type union {
    //            type jt:interface-device;
    //            type string {
    //              pattern "<.*>|$.*";
    //            }
    //          }
    //        }
    //      }
    //    }
    //  }
    //  container switch-options {
    //    description "Front end ports configuration";
    //    // uses apply-advanced;
    //    list switch-port {
    //      key name;
    //      leaf name {
    //        description "Front end port number";
    //        type union {
    //          type string {
    //            pattern "<.*>|$.*";
    //          }
    //          type uint32 {
    //            range "0 .. 15";
    //          }
    //        }
    //      }
    //      // uses apply-advanced;
    //      choice auto-negotiation-choice {
    //        leaf auto-negotiation {
    //          description "Enable auto-negotiation";
    //          type empty;
    //        }
    //        leaf no-auto-negotiation {
    //          description "Don't enable auto-negotiation";
    //          type empty;
    //        }
    //      }
    //      leaf link-mode {
    //        description "Link operational mode";
    //        type enumeration {
    //          enum "half-duplex" {
    //            description "Half-duplex operation";
    //          }
    //          enum "full-duplex" {
    //            description "Full-duplex operation";
    //          }
    //        }
    //      }
    //      leaf speed {
    //        description "Link speed";
    //        type enumeration {
    //          enum "10m" {
    //          }
    //          enum "100m" {
    //          }
    //          enum "1g" {
    //          }
    //        }
    //      }
    //      leaf vlan-id {
    //        description "VLAN ID for this port";
    //        type union {
    //          type string {
    //            pattern "<.*>|$.*";
    //          }
    //          type uint32 {
    //            range "0 .. 4094";
    //          }
    //        }
    //      }
    //      leaf cascade-port {
    //        description "Port externally connected to another cascade port";
    //        type empty;
    //      }
    //    }
    //  }
    //  container container-options {
    //    description "Container interface specific options";
    //    // uses apply-advanced;
    //    container container-type {
    //      presence "enable container-type";
    //      description "Protocol type of the container interface";
    //      // uses apply-advanced;
    //      choice container-type-choice {
    //        case case_1 {
    //          container aps {
    //            description "APS options on the container";
    //            presence "enable aps";
    //            uses aps_type;
    //          }
    //        }
    //      }
    //    }
    //    container member-interface-type {
    //      description "Link type of members of container";
    //      // uses apply-advanced;
    //      choice member_interface_type_choice {
    //        case case_1 {
    //          container sonet {
    //            // uses apply-advanced;
    //            leaf member-interface-speed {
    //              description "Link speed of members of container";
    //              type enumeration {
    //                enum "oc3" {
    //                  description "Links are OC-3";
    //                }
    //                enum "oc12" {
    //                  description "Links are OC-12";
    //                }
    //                enum "oc48" {
    //                  description "Links are OC-48";
    //                }
    //                enum "oc192" {
    //                  description "Links are OC-192";
    //                }
    //                enum "oc768" {
    //                  description "Links are OC-768";
    //                }
    //                enum "mixed" {
    //                  description "Links are of different speeds";
    //                }
    //              }
    //            }
    //          }
    //        }
    //        case case_2 {
    //          container atm {
    //            // uses apply-advanced;
    //            leaf member-interface-speed {
    //              description "Link speed of members of container";
    //              type enumeration {
    //                enum "oc3" {
    //                  description "Links are OC-3";
    //                }
    //                enum "oc12" {
    //                  description "Links are OC-12";
    //                }
    //                enum "oc48" {
    //                  description "Links are OC-48";
    //                }
    //              }
    //            }
    //          }
    //        }
    //        case case_3 {
    //          container channelized-sonet {
    //            // uses apply-advanced;
    //            leaf member-interface-speed {
    //              description "Link speed of members of container";
    //              type enumeration {
    //                enum "coc3" {
    //                  description "Links are COC-3";
    //                }
    //                enum "coc12" {
    //                  description "Links are COC-12";
    //                }
    //                enum "coc48" {
    //                  description "Links are COC-48";
    //                }
    //                enum "coc192" {
    //                  description "Links are COC-192";
    //                }
    //                enum "coc768" {
    //                  description "Links are COC-768";
    //                }
    //              }
    //            }
    //          }
    //        }
    //        case case_4 {
    //          container channelized-sdh {
    //            // uses apply-advanced;
    //            leaf member-interface-speed {
    //              description "Link speed of members of container";
    //              type enumeration {
    //                enum "cstm1" {
    //                  description "Links are cstm-1";
    //                }
    //                enum "cstm4" {
    //                  description "Links are cstm-4";
    //                }
    //                enum "cstm16" {
    //                  description "Links are cstm-16";
    //                }
    //                enum "coc64" {
    //                  description "Links are cstm-64";
    //                }
    //                enum "cstm256" {
    //                  description "Links are cstm256";
    //                }
    //              }
    //            }
    //          }
    //        }
    //      }
    //    }
    //    container redundancy {
    //      description "Container interface redundancy options";
    //      // uses apply-advanced;
    //      container hold-time {
    //        description "Hold time for link up and link down";
    //        leaf up {
    //          description "Link up hold time";
    //          units "milliseconds";
    //          type union {
    //            type string {
    //              pattern "<.*>|$.*";
    //            }
    //            type uint32 {
    //              range "0 .. 65534";
    //            }
    //          }
    //        }
    //        leaf down {
    //          description "Link down hold time";
    //          units "milliseconds";
    //          type union {
    //            type string {
    //              pattern "<.*>|$.*";
    //            }
    //            type uint32 {
    //              range "0 .. 65534";
    //            }
    //          }
    //        }
    //      }
    //    }
    //    leaf-list container-list {
    //      ordered-by user;
    //      description "List of container interfaces this member link is associated to";
    //      type union {
    //        type jt:interface-device;
    //        type string {
    //          pattern "<.*>|$.*";
    //        }
    //      }
    //    }
    //    choice redundancy-type {
    //      case case_1 {
    //        choice aps-redundancy {
    //          case case_1 {
    //            leaf primary {
    //              description "This member link is primary interface of the container";
    //              type empty;
    //            }
    //          }
    //          case case_2 {
    //            leaf standby {
    //              description "This member link is standby interface of the container";
    //              type empty;
    //            }
    //          }
    //        }
    //      }
    //    }
    //    leaf fast-aps {
    //      description "Fast APS switch";
    //      type empty;
    //    }
    //    leaf allow-configuration-override {
    //      description "Allow physical configuration of member link to override container configuration";
    //      type empty;
    //    }
    //  }
    //  container layer2-policer {
    //    description "Layer2 policing for interface";
    //    // uses apply-advanced;
    //    choice layer2-input-policer-choice {
    //      case case_1 {
    //        leaf input-policer {
    //          description "Two-color policer for received packets";
    //          type string;
    //        }
    //      }
    //      case case_2 {
    //        leaf input-hierarchical-policer {
    //          description "Hierarchical policer for received packets";
    //          type string;
    //        }
    //      }
    //    }
    //  }
     list unit {
       key name;
       description "Logical interface";
       leaf name {
         type string;
       }
       // uses apply-advanced;
       leaf interface-tag {
         description "Interface tag name";
         type string {
           length "1 .. 64";
         }
       }
      //  container policer-overhead {
      //    description "Policer overhead adjustment for this unit";
      //    // uses apply-advanced;
      //    leaf policer-overhead-value {
      //      description "Policer overhead bytes to be accounted in ingress and egress";
      //      units "bytes";
      //      type union {
      //        type string {
      //          pattern "<.*>|$.*";
      //        }
      //        type int32;
      //      }
      //    }
      //    leaf ingress {
      //      description "Ingress value in bytes";
      //      units "bytes";
      //      type union {
      //        type string {
      //          pattern "<.*>|$.*";
      //        }
      //        type int32 {
      //          range "-64 .. 64";
      //        }
      //      }
      //    }
      //    leaf egress {
      //      description "Egress value in bytes";
      //      units "bytes";
      //      type union {
      //        type string {
      //          pattern "<.*>|$.*";
      //        }
      //        type int32 {
      //          range "-64 .. 64";
      //        }
      //      }
      //    }
      //  }
      //  leaf alias {
      //    description "Interface alias";
      //    type string;
      //  }
      //  leaf enhanced-convergence {
      //    description "Optimize convergence time for L3";
      //    type empty;
      //  }
      //  leaf proxy-macip-advertisement {
      //    description "Proxy advertisement of type 2 MAC+IP route for EVPN";
      //    type empty;
      //  }
      //  leaf virtual-gateway-accept-data {
      //    description "Accept packets destined for virtual gateway address";
      //    type empty;
      //  }
      //  container peer-psd {
      //    presence "enable peer-psd";
      //    description "Peer psd";
      //    leaf psd-name {
      //      description "Peer psd name";
      //      type string;
      //    }
      //  }
      //  container peer-interface {
      //    presence "enable peer-interface";
      //    description "Peer interface";
      //    // uses apply-advanced;
      //    leaf interface-name {
      //      description "Peer interface name";
      //      type union {
      //        type jt:interface-unit;
      //        type string {
      //          pattern "<.*>|$.*";
      //        }
      //      }
      //    }
      //  }
      //  container interface-shared-with {
      //    presence "enable interface-shared-with";
      //    description "Specify which PSD owns this logical interface";
      //    // uses apply-advanced;
      //    leaf psd-name {
      //      description "Name of protected system domain (psd[1-31], ex. psd2)";
      //      type string {
      //      }
      //    }
      //  }
       choice enable-disable {
         case case_1 {
           leaf disable {
             description "Disable this logical interface";
             type empty;
           }
         }
       }
      //  leaf passive-monitor-mode {
      //    description "Use interface to tap packets from another router";
      //    type empty;
      //  }
      //  leaf per-session-scheduler {
      //    description "Enable per-session queuing on an IQ2 interface";
      //    type empty;
      //  }
      //  container account-layer2-overhead {
      //    presence "enable account-layer2-overhead";
      //    description "Account layer2 overhead in IFL byte statistics";
      //    // uses apply-advanced;
      //    leaf overhead-value {
      //      description "Layer2 overhead bytes to be accounted in ingress and egress";
      //      units "bytes";
      //      type union {
      //        type string {
      //          pattern "<.*>|$.*";
      //        }
      //        type int8 {
      //          range "-128 .. 127";
      //        }
      //      }
      //    }
      //    leaf ingress {
      //      description "Layer2 overhead bytes to be accounted in ingress";
      //      units "bytes";
      //      type union {
      //        type string {
      //          pattern "<.*>|$.*";
      //        }
      //        type int8 {
      //          range "-128 .. 127";
      //        }
      //      }
      //    }
      //    leaf egress {
      //      description "Layer2 overhead bytes to be accounted in egress";
      //      units "bytes";
      //      type union {
      //        type string {
      //          pattern "<.*>|$.*";
      //        }
      //        type int8 {
      //          range "-128 .. 127";
      //        }
      //      }
      //    }
      //  }
      //  container forwarding-class-accounting {
      //    presence "enable forwarding-class-accounting";
      //    description "Configure Forwarding-class-accounting parameters for IFL ";
      //    // uses apply-advanced;
      //    leaf direction {
      //      description "Direction of the traffic to be accounted for IFL";
      //      type enumeration {
      //        enum "ingress" {
      //          description "Enable forwarding-class-accounting for ingress traffic";
      //        }
      //        enum "egress" {
      //          description "Enable forwarding-class-accounting for egress traffic";
      //        }
      //        enum "both" {
      //          description "Enable forwarding-class-accounting for both directions";
      //        }
      //      }
      //    }
      //    container enhanced {
      //      presence "enable enhanced";
      //      // uses apply-advanced;
      //      leaf traffic-type {
      //        description "Traffic-type to be accounted for forwarding-class-accounting for IFL";
      //        type enumeration {
      //          enum "unicast-statistics" {
      //            description "Count only unicast traffic for forwarding-class-accounting for IFL ";
      //          }
      //          enum "multicast-statistics" {
      //            description "Count only multicast traffic for forwarding-class-accounting for IFL";
      //          }
      //        }
      //      }
      //      leaf family {
      //        description "Protocol traffic to be accounted for forwarding-class-accounting for IFL";
      //        type enumeration {
      //          enum "inet" {
      //            description "Enable forwarding-class-accounting for IPv4 family only for IFL";
      //          }
      //          enum "inet6" {
      //            description "Enable forwarding-class-accounting for IPv6 family only for IFL";
      //          }
      //          enum "both" {
      //            description "Enable forwarding-class-accounting for both IPv4 and IPv6 family for IFL";
      //          }
      //        }
      //      }
      //      leaf direction {
      //        description "Direction of the traffic to be accounted for forwarding-class-accounting for IFL";
      //        type enumeration {
      //          enum "ingress" {
      //            description "Enable forwarding-class-accounting for ingress traffic for IFL";
      //          }
      //          enum "egress" {
      //            description "Enable forwarding-class-accounting for egress traffic for IFL";
      //          }
      //          enum "both" {
      //            description "Enable forwarding-class-accounting for both ingress and egress traffic for IFL";
      //          }
      //        }
      //      }
      //      leaf overhead-bytes {
      //        description "Per octet overhead bytes to be accounted for forwarding-class-accounting for IFL ";
      //        default "0";
      //        type union {
      //          type string {
      //            pattern "<.*>|$.*";
      //          }
      //          type uint32 {
      //            range "0 .. 255";
      //          }
      //        }
      //      }
      //    }
      //  }
      //  leaf clear-dont-fragment-bit {
      //    description "Clear DF bit in packet (AS PIC and J-series only as well as MIF)";
      //    type empty;
      //  }
      //  leaf packet-inject-enable {
      //    description "Enable packet inject functionality on this IFL";
      //    type empty;
      //  }
      //  leaf reassemble-packets {
      //    description "Do reassembly of fragmented tunnel packets";
      //    type empty;
      //  }
      //  container ip-address-owner {
      //    description "Define the owner for IP addresses hosted on this interface";
      //    choice ip-address-owner-options {
      //      case case_1 {
      //        leaf service-plane {
      //          description "IP address defined on this interface is hosted by service plane";
      //          type empty;
      //        }
      //      }
      //      case case_2 {
      //        leaf routing-engine {
      //          description "IP address defined on this interface is hosted by routing engine";
      //          type empty;
      //        }
      //      }
      //    }
      //  }
      //  container services-options {
      //    description "Services interface-specific options";
      //    // uses apply-advanced;
      //  }
      //  container rpm {
      //    description "Enable RPM service on this interface";
      //    // uses apply-advanced;
      //    choice rpm_or_twamp {
      //      case case_1 {
      //        choice rpm-type {
      //          case case_1 {
      //            leaf client {
      //              description "Client mode";
      //              type empty;
      //            }
      //          }
      //          case case_2 {
      //            leaf server {
      //              description "Server mode";
      //              type empty;
      //            }
      //          }
      //          case case_3 {
      //            leaf client-delegate-probes {
      //              description "Client delegate probe mode";
      //              type empty;
      //            }
      //          }
      //        }
      //      }
      //      case case_2 {
      //        leaf twamp-server {
      //          description "Set TWAMP server mode on this interface";
      //          type empty;
      //        }
      //      }
      //      case case_3 {
      //        leaf twamp-client {
      //          description "Set TWAMP client mode on this interface";
      //          type empty;
      //        }
      //      }
      //    }
      //  }
       leaf description {
         description "Text description of interface";
         type string;
       }
      //  container dial-options {
      //    description "Dial options";
      //    // uses apply-advanced;
      //    choice interface_id_choice {
      //      case case_1 {
      //        leaf l2tp-interface-id {
      //          description "Identifier for group of PPP sessions";
      //          type string {
      //            length "1 .. 63";
      //          }
      //        }
      //      }
      //      case case_2 {
      //        leaf ipsec-interface-id {
      //          description "Identifier for group of dynamic peers";
      //          type string {
      //            length "1 .. 63";
      //          }
      //        }
      //      }
      //    }
      //    choice ifl_type {
      //      case case_1 {
      //        leaf dedicated {
      //          description "Use this unit for only one PPP/IPSec session";
      //          type empty;
      //        }
      //      }
      //      case case_2 {
      //        leaf shared {
      //          description "Share this unit for multiple PPP/IPSec sessions";
      //          type empty;
      //        }
      //      }
      //    }
      //  }
      //  container actual-transit-statistics {
      //    presence "enable actual-transit-statistics";
      //    description "Actual transit statistics";
      //  }
      //  list demux-source {
      //    key name;
      //    ordered-by user;
      //    description "Demux based on source address";
      //    uses demux_options_table;
      //  }
      //  list demux-destination {
      //    key name;
      //    ordered-by user;
      //    description "Demux based on destination address";
      //    uses demux_options_table;
      //  }
      //  container demux {
      //    description "Demux based on source or destination address";
      //    // uses apply-advanced;
      //    container inet {
      //      presence "enable inet";
      //      description "Family inet";
      //      // uses apply-advanced;
      //      leaf address {
      //        description "Address type";
      //        type enumeration {
      //          enum "source" {
      //            description "Demux based on source address";
      //          }
      //          enum "destination" {
      //            description "Demux based on destination address";
      //          }
      //        }
      //      }
      //      container auto-configure {
      //        description "Auto configuration";
      //        uses dynamic_ipv4_type;
      //      }
      //    }
      //    container inet6 {
      //      presence "enable inet6";
      //      description "Family inet6";
      //      // uses apply-advanced;
      //      leaf address {
      //        description "Address type";
      //        type enumeration {
      //          enum "source" {
      //            description "Demux based on source address";
      //          }
      //          enum "destination" {
      //            description "Demux based on destination address";
      //          }
      //        }
      //      }
      //      container auto-configure {
      //        description "Auto configuration";
      //        uses dynamic_ipv6_type;
      //      }
      //    }
      //  }
       leaf encapsulation {
         description "Logical link-layer encapsulation";
         type enumeration {
           enum "atm-nlpid" {
             description "ATM NLPID encapsulation";
           }
           enum "atm-cisco-nlpid" {
             description "Cisco-compatible ATM NLPID encapsulation";
           }
           enum "atm-snap" {
             description "ATM LLC/SNAP encapsulation";
           }
           enum "atm-vc-mux" {
             description "ATM VC multiplexing";
           }
           enum "atm-ccc-vc-mux" {
             description "ATM VC for CCC";
           }
           enum "atm-tcc-vc-mux" {
             description "ATM VC for translational cross-connect";
           }
           enum "atm-tcc-snap" {
             description "ATM LLC/SNAP for translational cross-connect";
           }
           enum "atm-ccc-cell-relay" {
             description "ATM cell relay for CCC";
           }
           enum "vlan-vci-ccc" {
             description "CCC for VLAN Q-in-Q and ATM VPI/VCI interworking";
           }
           enum "ether-over-atm-llc" {
             description "Ethernet over ATM (LLC/SNAP) encapsulation";
           }
           enum "ether-vpls-over-atm-llc" {
             description "Ethernet VPLS over ATM (bridging) encapsulation";
           }
           enum "ppp-over-ether-over-atm-llc" {
             description "PPPoE over ATM (LLC/SNAP) encapsulation";
           }
           enum "ppp-over-ether" {
             description "PPPoE encapsulation";
           }
           enum "atm-ppp-vc-mux" {
             description "ATM PPP over raw AAL5";
           }
           enum "atm-ppp-llc" {
             description "ATM PPP over AAL5/LLC";
           }
           enum "atm-mlppp-llc" {
             description "ATM MLPPP over AAL5/LLC";
           }
           enum "frame-relay-ppp" {
             description "PPP over Frame Relay";
           }
           enum "frame-relay-ccc" {
             description "Frame Relay DLCI for CCC";
           }
           enum "frame-relay" {
             description "Frame Relay DLCI";
           }
           enum "frame-relay-tcc" {
             description "Frame Relay DLCI for translational cross-connect";
           }
           enum "frame-relay-ether-type" {
             description "Cisco-compatible Frame Relay Encapsulation DLCI";
           }
           enum "frame-relay-ether-type-tcc" {
             description "Cisco-compatible Frame Relay Encapsulation DLCI for TCC";
           }
           enum "ether-vpls-fr" {
             description "Ethernet VPLS over Frame Relay (bridging) encapsulation";
           }
           enum "vlan-ccc" {
             description "802.1q tagging for a cross-connect";
           }
           enum "ethernet-ccc" {
             description "Ethernet for a cross-connect";
           }
           enum "vlan-vpls" {
             description "VLAN virtual private LAN service";
           }
           enum "vlan-bridge" {
             description "VLAN layer-2 bridging";
           }
           enum "ethernet-tcc" {
             description "Ethernet translational cross-connect";
           }
           enum "dix" {
             description "Ethernet DIXv2 (RFC 894)";
           }
           enum "ethernet" {
             description "Ethernet II (RFC 894)";
           }
           enum "ethernet-vpls" {
             description "Ethernet II virtual private LAN service";
           }
           enum "ethernet-bridge" {
             description "Ethernet II bridging";
           }
           enum "vlan" {
             description "802.1q-tagged Ethernet";
           }
           enum "vlan-tcc" {
             description "802.1q tagging for a translational cross-connect";
           }
           enum "multilink-ppp" {
             description "Multilink PPP";
           }
           enum "multilink-frame-relay-end-to-end" {
             description "Multilink Frame Relay end-to-end (FRF.15)";
           }
           enum "ppp-ccc" {
             description "Serial PPP device for a cross-connect";
           }
         }
       }
       leaf gre {
         description "Allow GRE packets";
         type empty;
       }
       leaf mtu {
         description "Maximum transmission unit packet size";
         type union {
           type string {
             pattern "<.*>|$.*";
           }
           type uint32;
         }
       }
      //  choice pointedness {
      //    case case_1 {
      //      leaf point-to-point {
      //        description "Point-to-point connection";
      //        type empty;
      //      }
      //    }
      //    case case_2 {
      //      leaf multipoint {
      //        description "Multipoint connection";
      //        type empty;
      //      }
      //    }
      //  }
       leaf bandwidth {
         description "Logical unit bandwidth (informational only)";
         type string;
       }
      //  container radio-router {
      //    description "Parameters for dynamic link cost management";
      //    presence "enable radio-router";
      //    uses dynamic_ifbw_parms_type;
      //  }
      //  choice traps-choice {
      //    leaf traps {
      //      description "Enable SNMP notifications on state changes";
      //      type empty;
      //    }
      //    leaf no-traps {
      //      description "Don't enable SNMP notifications on state changes";
      //      type empty;
      //    }
      //  }
      //  choice routing-services-choice {
      //    leaf routing-services {
      //      description "Enable routing services";
      //      status deprecated;
      //      type empty;
      //    }
      //    leaf no-routing-services {
      //      description "Don't enable routing services";
      //      status deprecated;
      //      type empty;
      //    }
      //  }
      //  container routing-service {
      //    description "Routing Services on this interface";
      //    // uses apply-advanced;
      //    choice enable-disable {
      //      case case_1 {
      //        leaf enable {
      //          description "Enable Routing Service";
      //          type empty;
      //        }
      //      }
      //      case case_2 {
      //        leaf disable {
      //          description "Disable Routing Service";
      //          type empty;
      //        }
      //      }
      //    }
      //  }
      //  container arp-resp {
      //    presence "enable arp-resp";
      //    description "Knob to control ARP response on the interface, default is restricted";
      //    choice arp-response-options {
      //      case case_1 {
      //        leaf unrestricted {
      //          description "Enable unrestricted ARP respone on the interface";
      //          type empty;
      //        }
      //      }
      //      case case_2 {
      //        leaf restricted {
      //          description "Enable restricted proxy ARP response on the interface";
      //          type empty;
      //        }
      //      }
      //    }
      //  }
      //  container proxy-arp {
      //    presence "enable proxy-arp";
      //    description "Enable proxy ARP on the interface, default is unrestricted";
      //    choice proxyarp-options {
      //      case case_1 {
      //        leaf unrestricted {
      //          description "Enable unrestricted proxy ARP on the interface";
      //          type empty;
      //        }
      //      }
      //      case case_2 {
      //        leaf restricted {
      //          description "Enable restricted proxy ARP on the interface";
      //          type empty;
      //        }
      //      }
      //    }
      //  }
       choice vlan_choice {
         case case_1 {
           leaf vlan-id {
             description "Virtual LAN identifier value for 802.1q VLAN tags";
             type string;
           }
         }
         case case_2 {
           leaf vlan-id-range {
             description "Virtual LAN identifier range of form vid1-vid2";
             type jt:vlan-range;
           }
         }
         case case_3 {
           leaf-list inner-vlan-id-swap-ranges {
             description "Inner vlan-id swap range(s) of form vid1-vid2 for dynamic L2 VLANs";
             type jt:vlan-range;
           }
         }
         case case_4 {
           leaf-list vlan-id-list {
             description "List of VLAN identifiers";
             type jt:vlan-range;
           }
         }
         case case_5 {
           leaf-list vlan-tag {
             ordered-by user;
             description "IEEE 802.1q tag list for VLAN tagged frames";
             status deprecated;
             type string;
           }
         }
         case case_6 {
           container vlan-tags {
             presence "enable vlan-tags";
             description "IEEE 802.1q tags";
             leaf outer {
               description "[tpid.]vlan-id, tpid format is 0xNNNN and is optional";
               type string;
             }
             choice inner_choice {
               case case_1 {
                 leaf inner {
                   description "[tpid.]vlan-id, tpid format is 0xNNNN and is optional";
                   type string;
                 }
               }
               case case_2 {
                 leaf inner-range {
                   description "[tpid.]vid1-vid2, tpid format is 0xNNNN and is optional";
                   type string {
                   }
                 }
               }
               case case_3 {
                 leaf-list inner-list {
                   description "List of VLAN identifiers";
                   type jt:vlan-range;
                 }
               }
             }
           }
         }
       }
      //  leaf deep-vlan-qualified-learning {
      //    description "Enable qualified MAC-address learning on the specified vlan tag";
      //    type union {
      //      type string {
      //        pattern "<.*>|$.*";
      //      }
      //      type uint32 {
      //        range 3;
      //      }
      //    }
      //  }
      //  leaf native-inner-vlan-id {
      //    description "Native virtual LAN identifier for singly tagged frames";
      //    type union {
      //      type string {
      //        pattern "<.*>|$.*";
      //      }
      //      type uint32 {
      //        range "0 .. 4094";
      //      }
      //    }
      //  }
      //  container inner-vlan-id-range {
      //    description "Inner vlan-id range start <start-vlan-id> end <end-vlan-id>";
      //    leaf start {
      //      description "Inner vlan-id range's start value";
      //      type union {
      //        type string {
      //          pattern "<.*>|$.*";
      //        }
      //        type uint32 {
      //          range "32 .. 4094";
      //        }
      //      }
      //    }
      //    leaf end {
      //      description "Inner vlan-id range's end value";
      //      type union {
      //        type string {
      //          pattern "<.*>|$.*";
      //        }
      //        type uint32 {
      //          range "32 .. 4094";
      //        }
      //      }
      //    }
      //  }
      //  container accept-source-mac {
      //    description "Remote media access control address to/from which to accept traffic";
      //    // uses apply-advanced;
      //    list mac-address {
      //      key name;
      //      description "Remote MAC address";
      //      uses mac_list;
      //    }
      //  }
      //  container input-vlan-map {
      //    description "VLAN map operation on input";
      //    uses vlan_map;
      //  }
      //  container output-vlan-map {
      //    description "VLAN map operation on output";
      //    uses vlan_map;
      //  }
      //  leaf swap-by-poppush {
      //    description "Pop original vlan tag and then push a new vlan tag";
      //    type empty;
      //  }
      //  leaf receive-lsp {
      //    description "Name of incoming label-switched path";
      //    type string;
      //  }
      //  leaf transmit-lsp {
      //    description "Name of outgoing label-switched path";
      //    type string;
      //  }
      //  leaf dlci {
      //    description "Frame Relay data-link control identifier";
      //    type union {
      //      type string {
      //        pattern "<.*>|$.*";
      //      }
      //      type uint32 {
      //        range "1 .. 1022";
      //      }
      //    }
      //  }
      //  leaf multicast-dlci {
      //    description "Frame Relay data-link control identifier for multicast packets";
      //    type union {
      //      type string {
      //        pattern "<.*>|$.*";
      //      }
      //      type uint32 {
      //        range "1 .. 1022";
      //      }
      //    }
      //  }
      //  choice vci_type {
      //    case case_1 {
      //      leaf vci {
      //        description "ATM point-to-point virtual circuit identifier ([vpi.]vci)";
      //        type jt:atm-vci;
      //      }
      //    }
      //    case case_2 {
      //      leaf allow-any-vci {
      //        description "Allow all VCIs to open in atm-ccc-cell-relay mode";
      //        type empty;
      //      }
      //    }
      //    case case_3 {
      //      leaf vpi {
      //        description "ATM point-to-point virtual path identifier (vpi)";
      //        type union {
      //          type string {
      //            pattern "<.*>|$.*";
      //          }
      //          type uint32 {
      //            range "0 .. 255";
      //          }
      //        }
      //      }
      //    }
      //    case case_4 {
      //      leaf trunk-id {
      //        description "ATM trunk identifier";
      //        type union {
      //          type string {
      //            pattern "<.*>|$.*";
      //          }
      //          type uint32 {
      //            range "0 .. 31";
      //          }
      //        }
      //      }
      //    }
      //  }
      //  leaf no-vpivci-swapping {
      //    description "Do not swap VPI/VCI for Cell Relay";
      //    type empty;
      //  }
      //  choice psn_vci_type {
      //    case case_1 {
      //      leaf psn-vci {
      //        description "PSN VCI";
      //        type jt:atm-vci;
      //      }
      //    }
      //    case case_2 {
      //      leaf psn-vpi {
      //        description "PSN VPI";
      //        type union {
      //          type string {
      //            pattern "<.*>|$.*";
      //          }
      //          type uint32 {
      //            range "0 .. 255";
      //          }
      //        }
      //      }
      //    }
      //  }
      //  container atm-l2circuit-mode {
      //    description "Select ATM Layer 2 circuit transport mode";
      //    choice mode_choice {
      //      case case_1 {
      //        leaf cell {
      //          description "ATM Layer 2 circuit cell mode";
      //          type empty;
      //        }
      //      }
      //      case case_2 {
      //        leaf aal5 {
      //          description "ATM Layer 2 circuit AAL5 mode";
      //          type empty;
      //        }
      //      }
      //    }
      //  }
      //  container vci-range {
      //    description "ATM VCI range start <start-vci> end <end-vci>";
      //    leaf start {
      //      description "ATM VCI range's start value";
      //      type union {
      //        type string {
      //          pattern "<.*>|$.*";
      //        }
      //        type uint16 {
      //          range "32 .. 4094";
      //        }
      //      }
      //    }
      //    leaf end {
      //      description "ATM VCI range's end value";
      //      type union {
      //        type string {
      //          pattern "<.*>|$.*";
      //        }
      //        type uint16 {
      //          range "32 .. 4094";
      //        }
      //      }
      //    }
      //  }
      //  leaf trunk-bandwidth {
      //    description "ATM trunk bandwidth";
      //    units "bits per second";
      //    type string;
      //  }
      //  leaf multicast-vci {
      //    description "ATM virtual circuit identifier for multicast packets";
      //    type jt:atm-vci;
      //  }
      //  container shaping {
      //    description "Virtual circuit traffic-shaping options";
      //    uses dcd_shaping_config;
      //  }
      //  container oam-period {
      //    description "OAM cell period";
      //    choice oam_period_choices {
      //      case case_1 {
      //        leaf oam-period {
      //          description "OAM cell period";
      //          units "seconds";
      //          type union {
      //            type string {
      //              pattern "<.*>|$.*";
      //            }
      //            type uint32 {
      //              range "1 .. 900";
      //            }
      //          }
      //        }
      //      }
      //      case case_2 {
      //        container disable {
      //          presence "enable disable";
      //          description "Disable F5 OAM loopback";
      //        }
      //      }
      //    }
      //  }
      //  container oam-liveness {
      //    description "OAM virtual circuit liveness parameters";
      //    // uses apply-advanced;
      //    leaf up-count {
      //      description "Number of OAM cells to consider VC up";
      //      type union {
      //        type string {
      //          pattern "<.*>|$.*";
      //        }
      //        type uint32 {
      //          range "1 .. 255";
      //        }
      //      }
      //    }
      //    leaf down-count {
      //      description "Number of OAM cells to consider VC down";
      //      type union {
      //        type string {
      //          pattern "<.*>|$.*";
      //        }
      //        type uint32 {
      //          range "1 .. 255";
      //        }
      //      }
      //    }
      //  }
      //  container ppp-options {
      //    description "Point-to-Point Protocol interface-specific options";
      //    uses ppp_options_type;
      //  }
      //  container pppoe-options {
      //    description "PPP over Ethernet interface-specific options";
      //    uses pppoe_options_type;
      //  }
      //  container pppoe-underlying-options {
      //    description "PPP over Ethernet underlying interface-specific options";
      //    uses pppoe_underlying_options_type;
      //  }
      //  container advisory-options {
      //    description "Interface-specific recommendations";
      //    uses advisory_options_type;
      //  }
      //  container auto-configure {
      //    description "Auto configuration";
      //    uses auto_configure_vlan_type;
      //  }
      //  container demux-options {
      //    description "IP demux interface-specific options";
      //    uses demux_options_type;
      //  }
      //  container targeted-distribution {
      //    presence "enable targeted-distribution";
      //    description "Interface participates in targeted-distribution";
      //    // uses apply-advanced;
      //    leaf primary-list {
      //      description "Primary targeted distribution list";
      //      type string {
      //        length "1 .. 20";
      //      }
      //    }
      //    leaf backup-list {
      //      description "Backup targeted distribution list";
      //      type string {
      //        length "1 .. 20";
      //      }
      //    }
      //    leaf standby-list {
      //      description "Standby targeted distribution list";
      //      type string {
      //        length "1 .. 20";
      //      }
      //    }
      //  }
      //  container targeted-options {
      //    presence "enable targeted-options";
      //    description "Targeting specific options";
      //    // uses apply-advanced;
      //    leaf weight {
      //      description "Targeting weight for subscriber";
      //      type string;
      //    }
      //    leaf primary {
      //      description "Primary link for the subscriber";
      //      type union {
      //        type jt:interface-device;
      //        type string {
      //          pattern "<.*>|$.*";
      //        }
      //      }
      //    }
      //    leaf backup {
      //      description "Backup link for the subscriber";
      //      type union {
      //        type jt:interface-device;
      //        type string {
      //          pattern "<.*>|$.*";
      //        }
      //      }
      //    }
      //    leaf group {
      //      description "Group name to which the subscriber is associated";
      //      type string {
      //      }
      //    }
      //  }
      //  choice keepalive_choices {
      //    case case_1 {
      //      container keepalives {
      //        description "Send or demand keepalive messages";
      //        presence "enable keepalives";
      //        uses keepalives_type;
      //      }
      //    }
      //    case case_2 {
      //      leaf no-keepalives {
      //        description "Do not send or demand keepalive messages";
      //        type empty;
      //      }
      //    }
      //  }
      //  leaf inverse-arp {
      //    description "Enable inverse ARP";
      //    type empty;
      //  }
      //  leaf transmit-weight {
      //    description "ATM2 transmit weight for VC under VP tunnel";
      //    type union {
      //      type string {
      //        pattern "<.*>|$.*";
      //      }
      //      type uint16 {
      //        range "1 .. 32767";
      //      }
      //    }
      //  }
      //  container epd-threshold {
      //    description "Early packet discard threshold for ATM2";
      //    uses epd_threshold_config;
      //  }
      //  leaf cell-bundle-size {
      //    description "L2 circuit cell bundle size";
      //    units "cells";
      //    type union {
      //      type string {
      //        pattern "<.*>|$.*";
      //      }
      //      type uint32 {
      //        range "1 .. 176";
      //      }
      //    }
      //  }
      //  leaf cell-bundle-timeout {
      //    description "L2 circuit cell bundle timeout";
      //    units "microseconds";
      //    type union {
      //      type string {
      //        pattern "<.*>|$.*";
      //      }
      //      type uint32 {
      //        range "1 .. 512";
      //      }
      //    }
      //  }
      //  leaf plp-to-clp {
      //    description "Enable ATM2 PLP to CLP copy";
      //    type empty;
      //  }
      //  leaf atm-scheduler-map {
      //    description "Assign ATM2 CoS scheduling map";
      //    type union {
      //      type string {
      //        pattern "default";
      //      }
      //      type string;
      //    }
      //  }
      //  leaf mrru {
      //    description "Maximum received reconstructed unit";
      //    units "bytes";
      //    type union {
      //      type string {
      //        pattern "<.*>|$.*";
      //      }
      //      type uint16 {
      //        range "1500 .. 4500";
      //      }
      //    }
      //  }
      //  leaf short-sequence {
      //    description "Short sequence number header format (MLPPP only)";
      //    type empty;
      //  }
      //  leaf fragment-threshold {
      //    description "Fragmentation threshold";
      //    units "bytes";
      //    type union {
      //      type string {
      //        pattern "<.*>|$.*";
      //      }
      //      type uint32 {
      //        range "64 .. 4500";
      //      }
      //    }
      //  }
      //  leaf drop-timeout {
      //    description "Drop timeout";
      //    units "milliseconds";
      //    type union {
      //      type string {
      //        pattern "<.*>|$.*";
      //      }
      //      type uint16 {
      //        range "0 .. 2000";
      //      }
      //    }
      //  }
      //  leaf disable-mlppp-inner-ppp-pfc {
      //    description "Disable compression for inner PPP header in MLPPP payload";
      //    type empty;
      //  }
       leaf minimum-links {
         description "Minimum number of links to sustain the bundle";
         type union {
           type string {
             pattern "<.*>|$.*";
           }
           type uint16;
         }
       }
      //  leaf multilink-max-classes {
      //    description "Number of multilink classes";
      //    type union {
      //      type string {
      //        pattern "<.*>|$.*";
      //      }
      //      type uint16;
      //    }
      //  }
      //  container compression {
      //    presence "enable compression";
      //    description "Various packet header compressions";
      //    // uses apply-advanced;
      //    container rtp {
      //      presence "enable rtp";
      //      description "Compress and decompress RTP";
      //      // uses apply-advanced;
      //      leaf f-max-period {
      //        description "Maximum number of compressed packets between transmission of full headers";
      //        type union {
      //          type string {
      //            pattern "<.*>|$.*";
      //          }
      //          type uint32 {
      //            range "1 .. 65535";
      //          }
      //        }
      //      }
      //      leaf-list queues {
      //        ordered-by user;
      //        description "Queue holding RTP packets. Default is queue 1";
      //        type enumeration {
      //          enum "q0" {
      //            description "RTP packets assigned to queue 0";
      //          }
      //          enum "q1" {
      //            description "RTP packets assigned to queue 1";
      //          }
      //          enum "q2" {
      //            description "RTP packets assigned to queue 2";
      //          }
      //          enum "q3" {
      //            description "RTP packets assigned to queue 3";
      //          }
      //        }
      //      }
      //      container port {
      //        presence "enable port";
      //        description "UDP destination ports reserved for RTP packets";
      //        leaf minimum {
      //          type union {
      //            type string {
      //              pattern "<.*>|$.*";
      //            }
      //            type uint32 {
      //              range "0 .. 65535";
      //            }
      //          }
      //        }
      //        leaf maximum {
      //          type union {
      //            type string {
      //              pattern "<.*>|$.*";
      //            }
      //            type uint32 {
      //              range "0 .. 65535";
      //            }
      //          }
      //        }
      //      }
      //      container maximum-contexts {
      //        description "Maximum number of simultaneous RTP contexts";
      //        leaf number {
      //          description "Maximum number of simultaneous RTP contexts";
      //          type union {
      //            type string {
      //              pattern "<.*>|$.*";
      //            }
      //            type uint32 {
      //              range "16 .. 2048";
      //            }
      //          }
      //        }
      //      }
      //    }
      //  }
      //  leaf interleave-fragments {
      //    description "Interleave long packets with high priority ones";
      //    type empty;
      //  }
      //  leaf link-layer-overhead {
      //    description "Link layer bit stuffing overhead (0.0 .. 50.0 percent)";
      //    type jt:unsigned-float;
      //  }
      //  leaf accounting-profile {
      //    description "Accounting profile name";
      //    type string;
      //  }
      //  leaf peer-unit {
      //    description "Peer unit number";
      //    type union {
      //      type string {
      //        pattern "<.*>|$.*";
      //      }
      //      type uint32 {
      //        range "0 .. 16385";
      //      }
      //    }
      //  }
       container tunnel {
         description "Tunnel parameters";
         // uses apply-advanced;
         container encapsulation {
           presence "enable encapsulation";
           description "Encapsulation over tunnel";
           container vxlan-gpe {
             presence "enable vxlan-gpe";
             // uses apply-advanced;
             container source {
               // uses apply-advanced;
               leaf address {
                 description "Interface address prefix";
                 type jt:ipv4addr;
               }
               leaf mac-address {
                 description "Interface source mac address";
                 type jt:mac-addr;
               }
               leaf interface {
                 description "Name of the interface";
                 type union {
                   type jt:interface-name;
                   type string {
                     pattern "<.*>|$.*";
                   }
                 }
               }
             }
             container destination {
               // uses apply-advanced;
               leaf address {
                 description "Interface address prefix";
                 type jt:ipv4addr;
               }
               leaf mac-address {
                 description "Interface destination mac address";
                 type jt:mac-addr;
               }
             }
             leaf tunnel-endpoint {
               description "Tunnel end point type";
               type enumeration {
                 enum "vxlan" {
                   description "To configure vxlan tunnel-end-point";
                 }
               }
             }
             container source-udp-port-range {
               description "Value range for source-udp-port";
               leaf min {
                 description "Minimum range value";
                 type union {
                   type string {
                     pattern "<.*>|$.*";
                   }
                   type uint32 {
                     range "1 .. 65535";
                   }
                 }
               }
               leaf max {
                 description "Maximum range value";
                 type union {
                   type string {
                     pattern "<.*>|$.*";
                   }
                   type uint32 {
                     range "1 .. 65535";
                   }
                 }
               }
             }
             leaf destination-udp-port {
               description "Value to write to the destination-udp-port field";
               type union {
                 type string {
                   pattern "<.*>|$.*";
                 }
                 type uint32 {
                   range "1 .. 65535";
                 }
               }
             }
             leaf vni {
               description "Value to write to the vni field";
               type union {
                 type string {
                   pattern "<.*>|$.*";
                 }
                 type uint32 {
                   range "0 .. 16777214";
                 }
               }
             }
           }
           container udp {
             presence "enable udp";
             description "Family for tunnel encapsulation udp";
             // uses apply-advanced;
             container source {
               // uses apply-advanced;
               leaf address {
                 description "Interface address prefix";
                 type jt:ipv4addr;
               }
               leaf interface {
                 description "Name of the interface";
                 type union {
                   type jt:interface-name;
                   type string {
                     pattern "<.*>|$.*";
                   }
                 }
               }
             }
             container destination {
               // uses apply-advanced;
               leaf address {
                 description "Interface address prefix";
                 type jt:ipv4addr;
               }
             }
           }
           container ipip {
             presence "enable ipip";
             description "Family for tunnel encapsulation ipip";
             // uses apply-advanced;
             container source {
               // uses apply-advanced;
               leaf address {
                 description "Interface address prefix";
                 type jt:ipv4addr;
               }
               leaf interface {
                 description "Name of the interface";
                 type union {
                   type jt:interface-name;
                   type string {
                     pattern "<.*>|$.*";
                   }
                 }
               }
             }
             container destination {
               // uses apply-advanced;
               leaf address {
                 description "Interface address prefix";
                 type jt:ipv4addr;
               }
             }
           }
         }
         leaf encap-type {
           description "Tunnel encapsulation type";
           type enumeration {
             enum "ipv4" {
               description "Tunnel IPv4 encapsulation";
             }
             enum "ipv6" {
               description "Tunnel IPv6 encapsulation";
             }
           }
         }
         choice source_type {
           case case_1 {
             leaf source {
               description "Tunnel source address";
               type jt:ipaddr;
             }
           }
           case case_2 {
             leaf source-hostname {
               description "Tunnel source hostname";
               type string;
             }
           }
           case case_3 {
             leaf source-interface {
               description "Tunnel source interface";
               type union {
                 type jt:interface-name;
                 type string {
                   pattern "<.*>|$.*";
                 }
               }
             }
           }
         }
         choice destination_type {
           case case_1 {
             leaf destination {
               description "Tunnel destination address";
               type jt:ipaddr;
             }
           }
           case case_2 {
             leaf destination-hostname {
               description "Tunnel destination hostname";
               type string;
             }
           }
         }
         leaf key {
           description "Tunnel key";
           type union {
             type string {
               pattern "<.*>|$.*";
             }
             type uint32 {
               range "0 .. 4294967295";
             }
           }
         }
         leaf backup-destination {
           description "Backup tunnel destination";
           type jt:ipaddr;
         }
         choice fragmentation {
           case case_1 {
             leaf allow-fragmentation {
               description "Do not set DF bit on packets";
               type empty;
             }
           }
           case case_2 {
             leaf do-not-fragment {
               description "Set DF bit on packets";
               type empty;
             }
           }
         }
         leaf ttl {
           description "Time to live";
           type union {
             type string {
               pattern "<.*>|$.*";
             }
             type uint32 {
               range "1 .. 255";
             }
           }
         }
         leaf traffic-class {
           description "TOS/Traffic class field of IP-header";
           type union {
             type string {
               pattern "<.*>|$.*";
             }
             type uint32 {
               range "0 .. 255";
             }
           }
         }
         leaf flow-label {
           description "Flow label field of IP6-header";
           type union {
             type string {
               pattern "<.*>|$.*";
             }
             type uint32 {
               range "0 .. 1048575";
             }
           }
         }
         choice path-mtu-discovery-choice {
           leaf path-mtu-discovery {
             description "Enable path MTU discovery for tunnels";
             type empty;
           }
           leaf no-path-mtu-discovery {
             description "Don't enable path MTU discovery for tunnels";
             type empty;
           }
         }
         container routing-instance {
           description "Routing instance to which tunnel ends belong";
           // uses apply-advanced;
           leaf destination {
             description "Routing instance of tunnel destination";
             type string {
             }
           }
         }
       }
      //  leaf compression-device {
      //    description "Logical interface used for compression";
      //    type union {
      //      type jt:interface-unit;
      //      type string {
      //        pattern "<.*>|$.*";
      //      }
      //    }
      //  }
      //  container atm-policer {
      //    description "ATM policing for logical interface";
      //    // uses apply-advanced;
      //    leaf input-atm-policer {
      //      description "Input atm policer";
      //      type string;
      //    }
      //  }
      //  container layer2-policer {
      //    description "Layer2 policing for logical interface";
      //    // uses apply-advanced;
      //    choice layer2-input-policer-choice {
      //      case case_1 {
      //        leaf input-policer {
      //          description "Two-color policer for received packets";
      //          type string;
      //        }
      //      }
      //      case case_2 {
      //        leaf input-hierarchical-policer {
      //          description "Hierarchical policer for received packets";
      //          type string;
      //        }
      //      }
      //      case case_3 {
      //        leaf input-three-color {
      //          description "Color-blind three-color policer for received packets";
      //          type string;
      //        }
      //      }
      //    }
      //    choice layer2-output-policer-choice {
      //      case case_1 {
      //        leaf output-policer {
      //          description "Two-color policer for transmitted packets";
      //          type string;
      //        }
      //      }
      //      case case_2 {
      //        leaf output-three-color {
      //          description "Three-color policer for transmitted packets";
      //          type string;
      //        }
      //      }
      //    }
      //  }
       container filter {
         description "Filters to apply to all families configured under this logical interface";
         // uses apply-advanced;
         choice chain_choice {
           case case_1 {
             leaf-list chain {
               ordered-by user;
               description "List of filter modules applied to TAG packets ";
               type string;
               max-elements 6;
             }
           }
         }
         choice input_choice {
           case case_1 {
             container input {
               description "Name of filter to be applied to received packets";
               leaf filter-name {
                 description "Name of the filter";
                 type string;
               }
               leaf shared-name {
                 description "Filter shared-name of instances of interface-shared filter";
                 type string;
               }
               leaf precedence {
                 description "Precedence of the filter";
                 type union {
                   type string {
                     pattern "<.*>|$.*";
                   }
                   type uint32 {
                     range "0 .. 255";
                   }
                 }
               }
             }
           }
         }
         choice output_choice {
           case case_1 {
             container output {
               description "Name of filter to be applied to transmitted packets";
               leaf filter-name {
                 description "Name of the filter";
                 type string;
               }
               leaf shared-name {
                 description "Filter shared-name of instances of interface-shared filter";
                 type string;
               }
               leaf precedence {
                 description "Precedence of the filter";
                 type union {
                   type string {
                     pattern "<.*>|$.*";
                   }
                   type uint32 {
                     range "0 .. 255";
                   }
                 }
               }
             }
           }
         }
       }
      //  list multi-chassis-protection {
      //    key name;
      //    description "Inter-Chassis protection configuration";
      //    uses multi-chassis-protection-group-ifl;
      //  }
      //  leaf statistics {
      //    description "Enable statistics collection in PFE";
      //    type empty;
      //  }
      //  container esi {
      //    presence "enable esi";
      //    description "ESI configuration of logical interface";
      //    // uses apply-advanced;
      //    container auto-derive {
      //      description "Auto-derive ESI value for the interface";
      //      // uses apply-advanced;
      //      choice esitype {
      //        case case_1 {
      //          leaf lacp-pe-system-id-and-admin-key {
      //            description "Auto-derive ESI from lacp";
      //            type empty;
      //          }
      //        }
      //      }
      //    }
      //    leaf identifier {
      //      description "ESI value for the interface";
      //      type jt:esi;
      //    }
      //    choice mode {
      //      case case_1 {
      //        leaf single-active {
      //          description "Single-active mode";
      //          type empty;
      //        }
      //      }
      //      case case_2 {
      //        leaf all-active {
      //          description "All-active mode";
      //          type empty;
      //        }
      //      }
      //    }
      //    container df-election-granularity {
      //      presence "enable df-election-granularity";
      //      description "DF Election Granularity Selection ";
      //      // uses apply-advanced;
      //      choice mode {
      //        case case_1 {
      //          container per-esi {
      //            presence "enable per-esi";
      //            description "DF Election Granularity Per Esi";
      //            // uses apply-advanced;
      //            leaf lacp-oos-on-ndf {
      //              description "Lacp Oos";
      //              type empty;
      //            }
      //          }
      //        }
      //        case case_2 {
      //          leaf per-esi-vlan {
      //            description "Per Esi Vlan";
      //            type empty;
      //          }
      //        }
      //      }
      //    }
      //    container df-election-type {
      //      presence "enable df-election-type";
      //      description "DF Election Type";
      //      // uses apply-advanced;
      //      choice pref_choice {
      //        case case_1 {
      //          container preference {
      //            presence "enable preference";
      //            description "Preference based DF election";
      //            // uses apply-advanced;
      //            leaf value {
      //              description "Preference value for EVPN Multihoming DF election";
      //              default "32767";
      //              type union {
      //                type string {
      //                  pattern "<.*>|$.*";
      //                }
      //                type uint32 {
      //                  range "0 .. 65535";
      //                }
      //              }
      //            }
      //          }
      //        }
      //      }
      //      choice mod_choice {
      //        case case_1 {
      //          container mod {
      //            presence "enable mod";
      //            description "MOD based DF election";
      //          }
      //        }
      //      }
      //    }
      //    leaf source-bmac {
      //      description "Unicast Source B-MAC address per ESI for PBB-EVPN";
      //      type jt:mac-unicast;
      //    }
      //  }
      //  choice virtual-gateway {
      //    case case_1 {
      //      leaf no-auto-virtual-gateway-esi {
      //        description "Disable auto ESI generation for virtual gateway address";
      //        type empty;
      //      }
      //    }
      //    case case_2 {
      //      container virtual-gateway-esi {
      //        description "ESI configuration of virtual gateway";
      //        // uses apply-advanced;
      //        leaf identifier {
      //          description "ESI value for the interface";
      //          type jt:esi;
      //        }
      //        choice mode {
      //          case case_1 {
      //            leaf single-active {
      //              description "Single-active mode";
      //              type empty;
      //            }
      //          }
      //          case case_2 {
      //            leaf all-active {
      //              description "All-active mode";
      //              type empty;
      //            }
      //          }
      //        }
      //      }
      //    }
      //  }
      //  container service {
      //    description "Service operations";
      //    // uses apply-advanced;
      //    list pcef {
      //      key name;
      //      ordered-by user;
      //      description "PCEF configuration";
      //      leaf name {
      //        description "PCEF Profile name";
      //        type string;
      //      }
      //      // uses apply-advanced;
      //      leaf activate-all {
      //        description "Activate all rules and rulebases in the pcef profile";
      //        type empty;
      //      }
      //      list activate {
      //        key name;
      //        ordered-by user;
      //        description "Name of pcef profile rule or rulebase to activate";
      //        leaf name {
      //          description "Name of pcef profile rule or rulebase to activate";
      //          type string;
      //        }
      //        // uses apply-advanced;
      //      }
      //    }
      //  }
      //  choice generate-eui64-choice {
      //    leaf generate-eui64 {
      //      description "To generate Link Local EUI-64 addresses";
      //      type empty;
      //    }
      //    leaf no-generate-eui64 {
      //      description "Don't to generate Link Local EUI-64 addresses";
      //      type empty;
      //    }
      //  }
       container family {
         description "Protocol family";
         container inet {
           presence "enable inet";
           description "IPv4 parameters";
           // uses apply-advanced;
          //  container dhcp {
          //    description "Dynamic Host Configuration Protocol client configuration";
          //    presence "enable dhcp";
          //    uses dhcp-client-type;
          //  }
          //  container targeted-broadcast {
          //    presence "enable targeted-broadcast";
          //    description "Directed broadcast";
          //    // uses apply-advanced;
          //    choice targeted-bcast-choice {
          //      case case_1 {
          //        leaf forward-and-send-to-re {
          //          description "Allow packets to be forwarded and sent to re";
          //          type empty;
          //        }
          //      }
          //      case case_2 {
          //        leaf forward-only {
          //          description "Allow packets only to be forwarded";
          //          type empty;
          //        }
          //      }
          //    }
          //  }
           leaf destination-class-usage {
             description "Enable destination class usage on this interface";
             status deprecated;
             type empty;
           }
           leaf transit-options-packets {
             description "Transit IP options packets (don't send to Routing Engine)";
             status deprecated;
             type empty;
           }
           leaf transit-ttl-exceeded {
             description "Transit IP TTL-exceeded packets (don't send to Routing Engine)";
             status deprecated;
             type empty;
           }
           leaf receive-options-packets {
             description "Receive IP options packets (don't send to Routing Engine)";
             type empty;
           }
           leaf receive-ttl-exceeded {
             description "Receive IP TTL-exceeded packets (don't send to Routing Engine)";
             type empty;
           }
           container accounting {
             description "Configure interface-based accounting options";
             // uses apply-advanced;
             container source-class-usage {
               description "Enable source class usage on this interface";
               // uses apply-advanced;
               leaf input {
                 description "Specify this interface for source-class-usage input";
                 type empty;
               }
               leaf output {
                 description "Specify this interface for source-class-usage output";
                 type empty;
               }
             }
             leaf destination-class-usage {
               description "Enable destination class usage on this interface";
               type empty;
             }
           }
           leaf mac-validate {
             description "Validate source MAC address";
             type enumeration {
               enum "strict" {
                 description "Strict mac-validation";
               }
               enum "loose" {
                 description "Loose mac-validation";
               }
             }
           }
           container rpf-check {
             presence "enable rpf-check";
             description "Enable reverse-path-forwarding checks on this interface";
             // uses apply-advanced;
             leaf fail-filter {
               description "Name of filter applied to packets failing RPF check";
               type string;
             }
             container mode {
               description "Mode for reverse path forwarding";
               leaf loose {
                 description "Reverse-path-forwarding loose mode";
                 type empty;
               }
             }
           }
           leaf mtu {
             description "Protocol family maximum transmission unit";
             type union {
               type uint32;
               type string {
                 pattern "<.*>|$.*";
               }
             }
           }
           leaf arp-max-cache {
             description "Max interface ARP nexthop cache size";
             type union {
               type string {
                 pattern "<.*>|$.*";
               }
               type uint32 {
                 range "1 .. 2000000";
               }
             }
           }
           leaf arp-new-hold-limit {
             description "Max no. of new unresolved nexthops";
             type union {
               type string {
                 pattern "<.*>|$.*";
               }
               type uint32 {
                 range "1 .. 2000000";
               }
             }
           }
           leaf tcp-mss {
             description "Protocol family tcp maximum segment size";
             type union {
               type string {
                 pattern "<.*>|$.*";
               }
               type uint32 {
                 range "1 .. 65535";
               }
             }
           }
           leaf no-redirects {
             description "Do not redirect traffic";
             type empty;
           }
           leaf no-neighbor-learn {
             description "Disable neighbor address learning on interface";
             type empty;
           }
           leaf unconditional-src-learn {
             description "Glean from arp packets even when source cannot be validated";
             type empty;
           }
           leaf multicast-only {
             description "Allow only multicast traffic (tunnels only)";
             type empty;
           }
           leaf primary {
             description "Candidate for primary interface in system";
             type empty;
           }
           leaf ipsec-sa {
             description "Name of security association";
             type string {
               length "1 .. 32";
             }
           }
          //  list demux-source {
          //    key name;
          //    ordered-by user;
          //    description "Demux based on source prefix";
          //    leaf name {
          //      type string;
          //    }
          //    // uses apply-advanced;
          //  }
          //  list demux-destination {
          //    key name;
          //    ordered-by user;
          //    description "Demux based on destination prefix";
          //    leaf name {
          //      type string;
          //    }
          //    // uses apply-advanced;
          //  }
           container filter {
             description "Packet filtering";
             // uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             leaf-list input-chain {
               ordered-by user;
               description "List of filter modules applied to received packets ";
               type string;
             }
             leaf-list output-chain {
               ordered-by user;
               description "List of filter modules applied to transmitted packets ";
               type string;
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               // uses apply-advanced;
               list rule {
                 key name;
                 ordered-by user;
                 description "Set of ADF rules";
                 leaf name {
                   description "Value for a single rule";
                   type string;
                 }
                 // uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32;
               }
             }
           }
           container ingress-queuing-filter {
             description "Protocol family ingress-queuing-filter";
             leaf filter-name {
               description "Name of the ingress-queuing-filter";
               type string;
             }
           }
           container iq-policing-filter {
             description "Protocol family ingress-queuing-policing-filter";
             leaf filter-name {
               description "Name of the ingress-queuing-policing-filter";
               type string;
             }
           }
           container simple-filter {
             description "Filter for doing multifield classification";
             // uses apply-advanced;
             leaf input {
               description "Name of simple filter applied to received packets";
               type string;
             }
           }
           leaf input-hierarchical-policer {
             description "Hierarchical policer for received packets";
             type string;
           }
           container policer {
             description "Interface policing";
             // uses apply-advanced;
             leaf disable-arp-policer {
               description "Disable the arp policer for the interface";
               type empty;
             }
             leaf arp {
               description "Name of policer applied to received ARP packets";
               type string;
             }
             leaf input {
               description "Name of policer applied to received packets";
               type string;
             }
             leaf output {
               description "Name of policer applied to transmitted packets";
               type string;
             }
           }
           container sampling {
             description "Interface sampling";
             // uses apply-advanced;
             leaf input {
               description "Sample all packets input on this interface";
               type empty;
             }
             leaf output {
               description "Sample all packets output on this interface";
               type empty;
             }
           }
           container service {
             description "Service operations";
             // uses apply-advanced;
             container input {
               description "Service sets to consider for received packets";
               // uses apply-advanced;
               list service-set {
                 key name;
                 ordered-by user;
                 description "Service set to consider for received packets";
                 leaf name {
                   description "Name of service set";
                   type string {
                   }
                 }
                 // uses apply-advanced;
                 leaf service-filter {
                   description "Name of service filter";
                   type string;
                 }
               }
               leaf post-service-filter {
                 description "Post-service filter to apply to received packets";
                 type string;
               }
             }
             container output {
               description "Service sets to consider for transmitted packets";
               // uses apply-advanced;
               list service-set {
                 key name;
                 ordered-by user;
                 description "Service set to consider for transmitted packets";
                 leaf name {
                   description "Name of service set";
                   type string {
                   }
                 }
                 // uses apply-advanced;
                 leaf service-filter {
                   description "Name of service filter";
                   type string;
                 }
               }
             }
           }
           list next-hop-tunnel {
             key name;
             ordered-by user;
             description "One or more next-hop tunnel tables";
             leaf name {
               description "Next-hop tunnel gateway address";
               type string;
             }
             // uses apply-advanced;
             leaf ipsec-vpn {
               description "Name of IPSec VPN";
               type string;
             }
           }
           choice tunnel-termination-status {
             case case_1 {
               leaf tunnel-termination {
                 description "Tunnel termination";
                 type empty;
               }
             }
             case case_2 {
               leaf no-tunnel-termination {
                 description "No Tunnel termination";
                 type empty;
               }
             }
           }
           leaf tunnel-loopback {
             description "Allows tunnel packet processing on IRB underlay using the loopback path";
             type empty;
           }
           list address {
             key name;
             ordered-by user;
             description "Interface address/destination prefix";
             leaf name {
               description "Interface address/destination prefix";
               type jt:ipv4prefix;
             }
             // uses apply-advanced;
             leaf destination {
               description "Destination address";
               type jt:ipv4addr;
             }
             leaf destination-profile {
               description "Profile to use for destination address";
               type string;
             }
             leaf broadcast {
               description "Broadcast address";
               type jt:ipv4addr;
             }
             leaf primary {
               description "Candidate for primary address in system";
               type empty;
             }
             leaf preferred {
               description "Preferred address on interface";
               type empty;
             }
             leaf master-only {
               description "Master management IP address for router";
               type empty;
             }
             list multipoint-destination {
               key name;
               ordered-by user;
               description "Multipoint NBMA destination";
               leaf name {
                 description "Destination address";
                 type jt:ipv4addr;
               }
               // uses apply-advanced;
               choice link-address {
                 case case_1 {
                   leaf dlci {
                     description "Frame Relay data-link control identifier";
                     type union {
                       type string {
                         pattern "<.*>|$.*";
                       }
                       type uint32 {
                         range "1 .. 1022";
                       }
                     }
                   }
                 }
                 case case_2 {
                   leaf vci {
                     description "ATM virtual circuit identifier ([vpi.]vci)";
                     type jt:atm-vci;
                   }
                 }
               }
              //  container shaping {
              //    description "Virtual circuit traffic-shaping options";
              //    uses dcd_shaping_config;
              //  }
              //  container oam-period {
              //    description "OAM cell period";
              //    choice oam_period_choices {
              //      case case_1 {
              //        leaf oam_period {
              //          description "OAM cell period";
              //          units "seconds";
              //          type union {
              //            type string {
              //              pattern "<.*>|$.*";
              //            }
              //            type uint32 {
              //              range "1 .. 900";
              //            }
              //          }
              //        }
              //      }
              //      case case_2 {
              //        container disable {
              //          presence "enable disable";
              //          description "Disable OAM loopback";
              //        }
              //      }
              //    }
              //  }
              //  container oam-liveness {
              //    description "OAM virtual circuit liveness parameters";
              //    // uses apply-advanced;
              //    leaf up-count {
              //      description "Number of OAM cells to consider VC up";
              //      type union {
              //        type string {
              //          pattern "<.*>|$.*";
              //        }
              //        type uint32 {
              //          range "1 .. 255";
              //        }
              //      }
              //    }
              //    leaf down-count {
              //      description "Number of OAM cells to consider VC down";
              //      type union {
              //        type string {
              //          pattern "<.*>|$.*";
              //        }
              //        type uint32 {
              //          range "1 .. 255";
              //        }
              //      }
              //    }
              //  }
              //  leaf inverse-arp {
              //    description "Enable inverse ARP reply messages";
              //    type empty;
              //  }
              //  leaf transmit-weight {
              //    description "ATM2 transmit weight for VC under VP tunnel";
              //    type union {
              //      type string {
              //        pattern "<.*>|$.*";
              //      }
              //      type uint16 {
              //        range "1 .. 32767";
              //      }
              //    }
              //  }
              //  container epd-threshold {
              //    description "Early packet discard threshold for ATM2";
              //    uses epd_threshold_config;
              //  }
             }
             list arp {
               key name;
               ordered-by user;
               description "Static Address Resolution Protocol entries";
               leaf name {
                 description "Destination IP address";
                 type jt:ipv4addr;
               }
               leaf l2-interface {
                 description "Layer 2 interface name for ARP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to ARP requests for this entry";
                 type empty;
               }
               leaf flood-as-unknown-unicast {
                 description "Broadcast the packet with unicast MAC";
                 type empty;
               }
             }
            //  container web-authentication {
            //    description "Parameters for web-based firewall-user authentication";
            //    // uses apply-advanced;
            //    leaf http {
            //      description "Enable authentication via HTTP";
            //      type empty;
            //    }
            //    leaf https {
            //      description "Enable authentication via HTTPS";
            //      type empty;
            //    }
            //    leaf redirect-to-https {
            //      description "Web authentication redirect to HTTPS";
            //      type empty;
            //    }
            //  }
             list vrrp-group {
               key name;
               ordered-by user;
               description "VRRP group";
               uses vrrp-group;
             }
             leaf virtual-gateway-address {
               description "Virtual Gateway IP address";
               type jt:ipv4addr;
             }
           }
           container unnumbered-address {
             description "Unnumbered interface address/destination prefix";
             leaf source {
               description "Interface from which to take local address";
               type union {
                 type jt:interface-unit;
                 type string {
                   pattern "<.*>|$.*";
                 }
               }
             }
             leaf preferred-source-address {
               description "Preferred address on the donor interface";
               type string;
             }
             leaf destination {
               description "Destination address";
               type jt:ipv4addr;
             }
             leaf destination-profile {
               description "Profile to use for destination address";
               type string;
             }
           }
           leaf negotiate-address {
             description "Negotiate address with remote";
             type empty;
           }
           leaf destination-udp-port {
             description "Choose destination UDP port number";
             type union {
               type string {
                 pattern "<.*>|$.*";
               }
               type uint32 {
                 range "10000 .. 10009";
               }
             }
           }
          //  container auto-configure {
          //    description "Auto configuration";
          //    uses dynamic_ipv4_type;
          //  }
          //  leaf clear-dont-fragment-bit {
          //    description "Clear DF bit in packet (AS PIC and J-series only as well as MIF)";
          //    type empty;
          //  }
         }
         container iso {
           presence "enable iso";
           description "OSI ISO protocol parameters";
           // uses apply-advanced;
           list address {
             key name;
             ordered-by user;
             description "Interface address";
             leaf name {
               description "Interface address";
               type jt:isoaddr;
             }
             // uses apply-advanced;
           }
           leaf mtu {
             description "Protocol family maximum transmission unit";
             type union {
               type uint32;
               type string {
                 pattern "<.*>|$.*";
               }
             }
           }
           leaf destination-udp-port {
             description "Choose destination UDP port number";
             type union {
               type string {
                 pattern "<.*>|$.*";
               }
               type uint32 {
                 range "10030 .. 10039";
               }
             }
           }
         }
         container inet6 {
           presence "enable inet6";
           description "IPv6 protocol parameters";
           // uses apply-advanced;
           container dhcpv6-client {
             description "Dynamic Host Configuration Protocol DHCPv6 client configuration";
             // uses apply-advanced;
             leaf client-type {
               description "DHCPv6 client type";
               type enumeration {
                 enum "stateful" {
                   description "Stateful client type for address assignment.";
                 }
                 enum "autoconfig" {
                   description "Autoconfig  client type for router-advertisement";
                 }
               }
             }
             list client-ia-type {
               key name;
               ordered-by user;
               description "DHCPv6 client identity association type";
               leaf name {
                 type enumeration {
                   enum "ia-na" {
                     description "Identity Association-Non-temporary Address";
                   }
                   enum "ia-pd" {
                     description "Identity Association-Prefix Address";
                   }
                 }
               }
               // uses apply-advanced;
             }
             container rapid-commit {
               presence "enable rapid-commit";
               description "Option is used to signal the use of the two message exchange for address assignment";
             }
             leaf interface-identifier {
               description "Identifier for this interface";
               type jt:ipv6addr;
             }
             leaf use-ra-prefix {
               description "Assign interface IP from RA prefix when ia-na address not received";
               type empty;
             }
             container prefix-delegating {
               description "Prefix delegating parameters";
               // uses apply-advanced;
               leaf preferred-prefix-length {
                 description "Client preferred prefix length";
                 type union {
                   type string {
                     pattern "<.*>|$.*";
                   }
                   type uint32 {
                     range "0 .. 64";
                   }
                 }
               }
               leaf sub-prefix-length {
                 description "The sub prefix length for LAN interfaces";
                 type union {
                   type string {
                     pattern "<.*>|$.*";
                   }
                   type uint32 {
                     range "1 .. 127";
                   }
                 }
               }
             }
             container client-identifier {
               description "DHCP Server identifies a client by client-identifier value ";
               leaf duid-type {
                 description "DUID identifying a client";
                 type enumeration {
                   enum "duid-llt" {
                     description "Link-layer address plus time";
                   }
                   enum "vendor" {
                     description "Vendor-assigned unique ID based on Enterprise Number";
                   }
                   enum "duid-ll" {
                     description "Link-layer address";
                   }
                 }
               }
             }
             leaf vendor-id {
               description "Vendor class id for the dhcpv6 client";
               type string {
                 length "1 .. 60";
               }
             }
             list req-option {
               key name;
               ordered-by user;
               description "DHCPV6 client requested option configuration";
               leaf name {
                 type enumeration {
                   enum "dns-server" {
                     description "Dns-server option";
                   }
                   enum "domain" {
                     description "Dns-server option";
                   }
                   enum "ntp-server" {
                     description "Ntp-server option";
                   }
                   enum "time-zone" {
                     description "Time-zone option";
                   }
                   enum "sip-server" {
                     description "Sip-server option";
                   }
                   enum "sip-domain" {
                     description "Sip-domain option";
                   }
                   enum "nis-server" {
                     description "Nis-server option";
                   }
                   enum "nis-domain" {
                     description "Nis-domain option";
                   }
                   enum "fqdn" {
                     description "Fully-qualified-domain option";
                   }
                   enum "vendor-spec" {
                     description "Vendor-spec option";
                   }
                   enum "zero-touch-redirect" {
                     description "Zero-touch-redirect";
                   }
                   enum "bootfile-url" {
                     description "Bootfile url";
                   }
                   enum "bootfile-param" {
                     description "Bootfile param";
                   }
                 }
               }
               // uses apply-advanced;
             }
             container options {
               description "DHCP options";
               // uses apply-advanced;
               list number {
                 key name;
                 description "DHCP option code";
                 leaf name {
                   description "DHCP option identifier code";
                   type union {
                     type string {
                       pattern "<.*>|$.*";
                     }
                     type uint32 {
                       range "1 .. 254";
                     }
                   }
                 }
                 choice option-type-choice {
                   case case_1 {
                     leaf hex-string {
                       description "Hexadecimal string";
                       type string {
                         length "1 .. 510";
                       }
                     }
                   }
                 }
               }
             }
             leaf retransmission-attempt {
               description "Number of attempts to retransmit the DHCPV6 client protocol packet";
               default "9";
               type union {
                 type string {
                   pattern "<.*>|$.*";
                 }
                 type uint32 {
                   range "0 .. 50000";
                 }
               }
             }
             container no-dns-install {
               presence "enable no-dns-install";
               description "Not propagate DNS to kernel";
             }
             container update-router-advertisement {
               description "Dhcpv6 client update rpd for prefix delegation";
               // uses apply-advanced;
               list interface {
                 key name;
                 ordered-by user;
                 description "Interfaces on which to delegate prefix";
                 max-elements 3;
                 leaf name {
                   description "Interfaces-name on which to delegate prefix";
                   type union {
                     type jt:interface-name;
                     type string {
                       pattern "<.*>|$.*";
                     }
                   }
                 }
                 // uses apply-advanced;
                 leaf interface-identifier {
                   description "Identifier for this interface";
                   type jt:ipv6addr;
                 }
                 leaf prefix-identifier {
                   description "Prefix identifier for prefix used in this interface";
                   type jt:ipv6addr;
                 }
                 choice managed-configuration-choice {
                   leaf managed-configuration {
                     description "Set managed address configuration";
                     type empty;
                   }
                   leaf no-managed-configuration {
                     description "Don't set managed address configuration";
                     type empty;
                   }
                 }
                 choice other-stateful-configuration-choice {
                   leaf other-stateful-configuration {
                     description "Set other stateful configuration";
                     type empty;
                   }
                   leaf no-other-stateful-configuration {
                     description "Don't set other stateful configuration";
                     type empty;
                   }
                 }
                 leaf max-advertisement-interval {
                   description "Maximum advertisement interval";
                   units "seconds";
                   type union {
                     type string {
                       pattern "<.*>|$.*";
                     }
                     type uint32 {
                       range "4 .. 1800";
                     }
                   }
                 }
                 leaf min-advertisement-interval {
                   description "Minimum advertisement interval";
                   units "seconds";
                   type union {
                     type string {
                       pattern "<.*>|$.*";
                     }
                     type uint32 {
                       range "3 .. 1350";
                     }
                   }
                 }
                 choice enable-recursive-dns-server-option-choice {
                   leaf enable-recursive-dns-server-option {
                     description "Enables the recursive DNS server option";
                     type empty;
                   }
                   leaf no-enable-recursive-dns-server-option {
                     description "Don't enables the recursive DNS server option";
                     type empty;
                   }
                 }
               }
             }
             leaf update-server {
               description "Propagate TCP/IP settings to DHCP server";
               type empty;
             }
           }
           container rpf-check {
             presence "enable rpf-check";
             description "Enable reverse-path-forwarding checks on this interface";
             // uses apply-advanced;
             leaf fail-filter {
               description "Name of filter applied to packets failing RPF check";
               type string;
             }
             container mode {
               description "Mode for reverse path forwarding";
               leaf loose {
                 description "Reverse-path-forwarding loose mode";
                 type empty;
               }
             }
           }
           container accounting {
             description "Interface-based accounting options";
             // uses apply-advanced;
             container source-class-usage {
               // uses apply-advanced;
               leaf input {
                 description "Interface for source-class-usage input";
                 type empty;
               }
               leaf output {
                 description "Interface for source-class-usage output";
                 type empty;
               }
             }
             leaf destination-class-usage {
               description "Enable destination class usage on this interface";
               type empty;
             }
           }
           leaf mtu {
             description "Protocol family maximum transmission unit";
             type union {
               type uint32;
               type string {
                 pattern "<.*>|$.*";
               }
             }
           }
           leaf tcp-mss {
             description "Protocol family tcp maximum segment size";
             type union {
               type string {
                 pattern "<.*>|$.*";
               }
               type uint32 {
                 range "1 .. 65535";
               }
             }
           }
           leaf nd6-stale-time {
             description "Stale time to reconfirm reachability with inet6 neighbour";
             units "seconds";
             type union {
               type string {
                 pattern "<.*>|$.*";
               }
               type uint32 {
                 range "1 .. 18000";
               }
             }
           }
           leaf no-neighbor-learn {
             description "Disable neighbor address learning on interface";
             type empty;
           }
          //  leaf slaac-enable {
          //    description "Enable slaac on management interface";
          //    type empty;
          //  }
          //  container ndp-proxy {
          //    description "Enable ndp proxy on interface";
          //    // uses apply-advanced;
          //    leaf interface-restricted {
          //      description "Enable ndp interface proxy restricted to interface";
          //      type empty;
          //    }
          //    leaf interface-unrestricted {
          //      description "Enable ndp interface proxy unrestricted to interface";
          //      type empty;
          //    }
          //  }
          //  container dad-proxy {
          //    description "DAD proxy on interface";
          //    // uses apply-advanced;
          //    leaf interface-restricted {
          //      description "Enable DAD interface proxy restricted to interface";
          //      type empty;
          //    }
          //    leaf interface-unrestricted {
          //      description "Enable DAD interface proxy unrestricted to interface";
          //      type empty;
          //    }
          //  }
          //  leaf nd6-max-cache {
          //    description "Max interface ND nexthop cache size";
          //    type union {
          //      type string {
          //        pattern "<.*>|$.*";
          //      }
          //      type uint32 {
          //        range "1 .. 2000000";
          //      }
          //    }
          //  }
          //  leaf nd6-new-hold-limit {
          //    description "Max no. of new unresolved nexthops";
          //    type union {
          //      type string {
          //        pattern "<.*>|$.*";
          //      }
          //      type uint32 {
          //        range "1 .. 2000000";
          //      }
          //    }
          //  }
           leaf no-redirects {
             description "Do not redirect traffic";
             type empty;
           }
           container filter {
             description "Packet filtering";
             // uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             leaf-list input-chain {
               ordered-by user;
               description "List of filter modules applied to received packets ";
               type string;
             }
             leaf-list output-chain {
               ordered-by user;
               description "List of filter modules applied to transmitted packets ";
               type string;
             }
             container adf {
               description "Ascend Data Filter definition";
               // uses apply-advanced;
               list rule {
                 key name;
                 ordered-by user;
                 description "Set of ADF rules";
                 leaf name {
                   description "Value for a single rule";
                   type string;
                 }
                 // uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32;
               }
             }
           }
           container ingress-queuing-filter {
             description "Protocol family ingress-queuing-filter";
             leaf filter-name {
               description "Name of the ingress-queuing-filter";
               type string;
             }
           }
           leaf input-hierarchical-policer {
             description "Hierarchical policer for received packets";
             type string;
           }
           container policer {
             description "Interface policing";
             // uses apply-advanced;
             leaf input {
               description "Name of policer applied to received packets";
               type string;
             }
             leaf output {
               description "Name of policer applied to transmitted packets";
               type string;
             }
           }
          //  container sampling {
          //    description "Interface sampling";
          //    // uses apply-advanced;
          //    leaf input {
          //      description "Sample all packets input on this interface";
          //      type empty;
          //    }
          //    leaf output {
          //      description "Sample all packets output on this interface";
          //      type empty;
          //    }
          //  }
          //  container service {
          //    description "Service operations";
          //    // uses apply-advanced;
          //    container input {
          //      description "Service sets to consider for received packets";
          //      // uses apply-advanced;
          //      list service-set {
          //        key name;
          //        ordered-by user;
          //        description "Service set to consider for received packets";
          //        leaf name {
          //          description "Name of service set";
          //          type string {
          //          }
          //        }
          //        // uses apply-advanced;
          //        leaf service-filter {
          //          description "Name of service filter";
          //          type string;
          //        }
          //      }
          //      leaf post-service-filter {
          //        description "Post-service filter to apply to received packets";
          //        type string;
          //      }
          //    }
          //    container output {
          //      description "Service sets to consider for transmitted packets";
          //      // uses apply-advanced;
          //      list service-set {
          //        key name;
          //        ordered-by user;
          //        description "Service set to consider for transmitted packets";
          //        leaf name {
          //          description "Name of service set";
          //          type string {
          //          }
          //        }
          //        // uses apply-advanced;
          //        leaf service-filter {
          //          description "Name of service filter";
          //          type string;
          //        }
          //      }
          //    }
          //  }
          //  choice tunnel-termination-status {
          //    case case_1 {
          //      leaf tunnel-termination {
          //        description "Tunnel termination";
          //        type empty;
          //      }
          //    }
          //    case case_2 {
          //      leaf no-tunnel-termination {
          //        description "No Tunnel termination";
          //        type empty;
          //      }
          //    }
          //  }
           list address {
             key name;
             ordered-by user;
             description "Interface address or destination prefix";
             leaf name {
               description "Interface address or destination prefix";
               type jt:ipv6prefix;
             }
             // uses apply-advanced;
             leaf destination {
               description "Destination address";
               type jt:ipv6addr;
             }
             leaf eui-64 {
               description "Generate EUI-64 interface ID";
               type empty;
             }
             leaf primary {
               description "Candidate for primary address in system";
               type empty;
             }
             leaf preferred {
               description "Preferred address on interface";
               type empty;
             }
             leaf master-only {
               description "Master management IP address for router";
               type empty;
             }
             list ndp {
               key name;
               ordered-by user;
               description "Static Neighbor Discovery Protocol  entries";
               leaf name {
                 description "Destination IP address";
                 type jt:ipv6addr;
               }
               leaf l2-interface {
                 description "Layer 2 interface name for NDP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to NDP requests for this entry";
                 type empty;
               }
             }
             list vrrp-inet6-group {
               key name;
               ordered-by user;
               description "VRRP group";
               uses vrrp-group;
             }
             container web-authentication {
               description "Parameters for web-based firewall-user authentication";
               // uses apply-advanced;
               leaf http {
                 description "Enable authentication via HTTP";
                 type empty;
               }
               leaf https {
                 description "Enable authentication via HTTPS";
                 type empty;
               }
               leaf redirect-to-https {
                 description "Web authentication redirect to HTTPS";
                 type empty;
               }
             }
             leaf virtual-gateway-address {
               description "Virtual Gateway IP address";
               type jt:ipv6addr;
             }
             leaf subnet-router-anycast {
               description "Create a subnet roter anycast address for this address.";
               type empty;
             }
           }
           list demux-source {
             key name;
             ordered-by user;
             description "Demux based on source prefix";
             leaf name {
               type string;
             }
             // uses apply-advanced;
           }
           list demux-destination {
             key name;
             ordered-by user;
             description "Demux based on destination prefix";
             leaf name {
               type string;
             }
             // uses apply-advanced;
           }
           container unnumbered-address {
             description "Unnumbered interface address/destination prefix";
             leaf source {
               description "Interface from which to take local address";
               type union {
                 type jt:interface-unit;
                 type string {
                   pattern "<.*>|$.*";
                 }
               }
             }
             leaf preferred-source-address {
               description "Preferred address on the donor interface";
               type string;
             }
           }
           choice dad-disable-choice {
             leaf dad-disable {
               description "Disable duplicate-address-detection";
               type empty;
             }
             leaf no-dad-disable {
               description "Don't disable duplicate-address-detection";
               type empty;
             }
           }
           leaf destination-udp-port {
             description "Choose destination UDP port number";
             type union {
               type string {
                 pattern "<.*>|$.*";
               }
               type uint32 {
                 range "10010 .. 10019";
               }
             }
           }
          //  container auto-configure {
          //    description "Auto configuration";
          //    uses dynamic_ipv6_type;
          //  }
         }
         container mpls {
           presence "enable mpls";
           description "MPLS protocol parameters";
           // uses apply-advanced;
           leaf mtu {
             description "Protocol family maximum transmission unit";
             type union {
               type uint32;
               type string {
                 pattern "<.*>|$.*";
               }
             }
           }
           leaf maximum-labels {
             description "Protocol family maximum number of labels";
             type union {
               type string {
                 pattern "<.*>|$.*";
               }
               type uint32;
             }
           }
           container filter {
             description "Packet filtering";
             // uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
           }
           container ingress-queuing-filter {
             description "Protocol family ingress-queuing-filter";
             leaf filter-name {
               description "Name of the ingress-queuing-filter";
               type string;
             }
           }
           leaf input-hierarchical-policer {
             description "Hierarchical policer for received packets";
             type string;
           }
           container policer {
             description "Interface policing";
             // uses apply-advanced;
             leaf input {
               description "Name of policer applied to received packets";
               type string;
             }
             leaf output {
               description "Name of policer applied to transmitted packets";
               type string;
             }
           }
           leaf destination-udp-port {
             description "Choose destination UDP port number";
             type union {
               type string {
                 pattern "<.*>|$.*";
               }
               type uint32 {
                 range "10020 .. 10029";
               }
             }
           }
         }
        //  container mlppp {
        //    description "Multilink PPP protocol parameters";
        //    // uses apply-advanced;
        //    leaf bundle {
        //      description "Logical interface name this link will join";
        //      type string;
        //    }
        //    choice anchor-points {
        //      case case_1 {
        //        leaf service-interface {
        //          description "Services interface to use";
        //          type union {
        //            type jt:interface-device;
        //            type string {
        //              pattern "<.*>|$.*";
        //            }
        //          }
        //        }
        //      }
        //      case case_2 {
        //        leaf service-device-pool {
        //          description "Service interface pool name to use";
        //          type string {
        //            length "1 .. 63";
        //          }
        //        }
        //      }
        //    }
        //    leaf dynamic-profile {
        //      description " dynamic profile for interface to use";
        //      type string {
        //        length "1 .. 80";
        //      }
        //    }
        //  }
        //  container mlfr-end-to-end {
        //    presence "enable mlfr-end-to-end";
        //    description "Multilink Frame Relay end-to-end protocol parameters";
        //    // uses apply-advanced;
        //    leaf bundle {
        //      description "Logical interface name this link will join";
        //      type union {
        //        type jt:interface-unit;
        //        type string {
        //          pattern "<.*>|$.*";
        //        }
        //      }
        //    }
        //  }
        //  container mlfr-uni-nni {
        //    presence "enable mlfr-uni-nni";
        //    description "Multilink Frame Relay UNI NNI protocol parameters";
        //    // uses apply-advanced;
        //    leaf bundle {
        //      description "Logical interface name this link will join";
        //      type union {
        //        type jt:interface-unit;
        //        type string {
        //          pattern "<.*>|$.*";
        //        }
        //      }
        //    }
        //  }
        //  container ccc {
        //    presence "enable ccc";
        //    description "Circuit cross-connect parameters";
        //    // uses apply-advanced;
        //    leaf mtu {
        //      description "Protocol family maximum transmission unit";
        //      type union {
        //        type uint32;
        //        type string {
        //          pattern "<.*>|$.*";
        //        }
        //      }
        //    }
        //    container filter {
        //      description "Packet filtering";
        //      // uses apply-advanced;
        //      choice input_choice {
        //        case case_1 {
        //          leaf input {
        //            description "Name of filter applied to received packets";
        //            type string;
        //          }
        //        }
        //        case case_2 {
        //          leaf-list input-list {
        //            ordered-by user;
        //            description "List of filter modules applied to received packets ";
        //            type string;
        //          }
        //        }
        //      }
        //      leaf-list input-chain {
        //        ordered-by user;
        //        description "List of filter modules applied to received packets ";
        //        type string;
        //      }
        //      choice output_choice {
        //        case case_1 {
        //          leaf output {
        //            description "Name of filter applied to transmitted packets";
        //            type string;
        //          }
        //        }
        //        case case_2 {
        //          leaf-list output-list {
        //            ordered-by user;
        //            description "List of filter modules applied to transmitted packets ";
        //            type string;
        //          }
        //        }
        //      }
        //      leaf-list output-chain {
        //        ordered-by user;
        //        description "List of filter modules applied to transmitted packets ";
        //        type string;
        //      }
        //      leaf group {
        //        description "Interface group to which interface belongs";
        //        type union {
        //          type string {
        //            pattern "<.*>|$.*";
        //          }
        //          type uint32 {
        //            range "1 .. 255";
        //          }
        //        }
        //      }
        //    }
        //    container ingress-queuing-filter {
        //      description "Protocol family ingress-queuing-filter";
        //      leaf filter-name {
        //        description "Name of the ingress-queuing-filter";
        //        type string;
        //      }
        //    }
        //    container policer {
        //      description "Interface policing";
        //      // uses apply-advanced;
        //      leaf input {
        //        description "Name of policer applied to received packets";
        //        type string;
        //      }
        //      leaf output {
        //        description "Name of policer applied to transmitted packets";
        //        type string;
        //      }
        //    }
        //    leaf translate-fecn-and-becn {
        //      description "Translate FECN and BECN bits";
        //      type empty;
        //    }
        //    choice de-or-plp {
        //      case case_1 {
        //        leaf translate-discard-eligible {
        //          description "Translate DE bit";
        //          type empty;
        //        }
        //      }
        //      case case_2 {
        //        leaf translate-plp-control-word-de {
        //          description "Translate PLP to/from Martini Control DE bit";
        //          type empty;
        //        }
        //      }
        //    }
        //    leaf keep-address-and-control {
        //      description "Don't strip PPP address and control bytes";
        //      type empty;
        //    }
        //  }
        //  container tcc {
        //    presence "enable tcc";
        //    description "Translational cross-connect parameters";
        //    // uses apply-advanced;
        //    container policer {
        //      description "Interface policing";
        //      // uses apply-advanced;
        //      leaf input {
        //        description "Name of policer applied to received packets";
        //        type string;
        //      }
        //      leaf output {
        //        description "Name of policer applied to transmitted packets";
        //        type string;
        //      }
        //    }
        //    container proxy {
        //      presence "enable proxy";
        //      // uses apply-advanced;
        //      leaf inet-address {
        //        description "Remote host address on non-Ethernet side of Ethernet TCC";
        //        type jt:ipv4addr;
        //      }
        //    }
        //    container remote {
        //      presence "enable remote";
        //      // uses apply-advanced;
        //      leaf inet-address {
        //        description "Remote host address on Ethernet side of Ethernet TCC";
        //        type jt:ipv4addr;
        //      }
        //      leaf mac-address {
        //        description "Remote host MAC address on Ethernet side of Ethernet TCC";
        //        type jt:mac-addr;
        //      }
        //    }
        //    leaf-list protocols {
        //      ordered-by user;
        //      description "Protocols supported on TCC interface";
        //      type enumeration {
        //        enum "mpls" {
        //          description "Multiprotocol Label Switching";
        //        }
        //        enum "inet" {
        //          description "IP version 4";
        //        }
        //        enum "iso" {
        //          description "International Organization for Standardization";
        //        }
        //        enum "inet6" {
        //          description "IP version 6";
        //        }
        //      }
        //    }
        //  }
        //  container vpls {
        //    presence "enable vpls";
        //    description "Virtual private LAN service parameters";
        //    // uses apply-advanced;
        //    leaf core-facing {
        //      description "Interface is core facing";
        //      type empty;
        //    }
        //    container filter {
        //      description "Packet filtering";
        //      // uses apply-advanced;
        //      choice input_choice {
        //        case case_1 {
        //          container input {
        //            description "Filter to be applied to received packets";
        //            leaf filter-name {
        //              description "Name of the filter";
        //              type string;
        //            }
        //            leaf shared-name {
        //              description "Filter shared-name of instances of interface-shared filter";
        //              type string;
        //            }
        //            leaf precedence {
        //              description "Precedence of the filter";
        //              type union {
        //                type string {
        //                  pattern "<.*>|$.*";
        //                }
        //                type uint32 {
        //                  range "0 .. 255";
        //                }
        //              }
        //            }
        //          }
        //        }
        //        case case_2 {
        //          leaf-list input-list {
        //            ordered-by user;
        //            description "List of filter modules applied to received packets ";
        //            type string;
        //          }
        //        }
        //      }
        //      leaf-list input-chain {
        //        ordered-by user;
        //        description "List of filter modules applied to received packets ";
        //        type string;
        //      }
        //      leaf-list output-chain {
        //        ordered-by user;
        //        description "List of filter modules applied to transmitted packets ";
        //        type string;
        //      }
        //      choice output_choice {
        //        case case_1 {
        //          container output {
        //            description "Filter to be applied to transmitted packets";
        //            leaf filter-name {
        //              description "Name of the filter";
        //              type string;
        //            }
        //            leaf shared-name {
        //              description "Filter shared-name of instances of interface-shared filter";
        //              type string;
        //            }
        //            leaf precedence {
        //              description "Precedence of the filter";
        //              type union {
        //                type string {
        //                  pattern "<.*>|$.*";
        //                }
        //                type uint32 {
        //                  range "0 .. 255";
        //                }
        //              }
        //            }
        //          }
        //        }
        //        case case_2 {
        //          leaf-list output-list {
        //            ordered-by user;
        //            description "List of filter modules applied to transmitted packets ";
        //            type string;
        //          }
        //        }
        //      }
        //      container adf {
        //        description "Ascend Data Filter definition";
        //        // uses apply-advanced;
        //        list rule {
        //          key name;
        //          ordered-by user;
        //          description "Set of ADF rules";
        //          leaf name {
        //            description "Value for a single rule";
        //            type string;
        //          }
        //          // uses apply-advanced;
        //        }
        //        leaf counter {
        //          description "Add a counter to each rule";
        //          type empty;
        //        }
        //        leaf input-precedence {
        //          description "Precedence of the input rules";
        //          type union {
        //            type string {
        //              pattern "<.*>|$.*";
        //            }
        //            type uint32 {
        //              range "0 .. 255";
        //            }
        //          }
        //        }
        //        leaf not-mandatory {
        //          description "No errors will be reported if no rules are present";
        //          type empty;
        //        }
        //        leaf output-precedence {
        //          description "Precedence of the output rules";
        //          type union {
        //            type string {
        //              pattern "<.*>|$.*";
        //            }
        //            type uint32 {
        //              range "0 .. 255";
        //            }
        //          }
        //        }
        //      }
        //      leaf group {
        //        description "Group to which interface belongs";
        //        type union {
        //          type string {
        //            pattern "<.*>|$.*";
        //          }
        //          type uint32 {
        //            range "1 .. 255";
        //          }
        //        }
        //      }
        //    }
        //    container ingress-queuing-filter {
        //      description "Protocol family ingress-queuing-filter";
        //      leaf filter-name {
        //        description "Name of the ingress-queuing-filter";
        //        type string;
        //      }
        //    }
        //    container iq-policing-filter {
        //      description "Protocol family ingress-queuing-policing-filter";
        //      leaf filter-name {
        //        description "Name of the ingress-queuing-policing-filter";
        //        type string;
        //      }
        //    }
        //    container policer {
        //      description "Interface policing";
        //      // uses apply-advanced;
        //      leaf input {
        //        description "Name of policer applied to received packets";
        //        type string;
        //      }
        //      leaf output {
        //        description "Name of policer applied to transmitted packets";
        //        type string;
        //      }
        //    }
        //    container sampling {
        //      description "Interface sampling";
        //      // uses apply-advanced;
        //      leaf input {
        //        description "Sample all packets input on this interface";
        //        type empty;
        //      }
        //      leaf output {
        //        description "Sample all packets output on this interface";
        //        type empty;
        //      }
        //    }
        //  }
         container bridge {
           presence "enable bridge";
           description "Layer-2 bridging parameters";
           // uses apply-advanced;
           leaf core-facing {
             description "Interface is core facing";
             type empty;
           }
           container filter {
             description "Packet filtering";
             // uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             leaf-list input-chain {
               ordered-by user;
               description "List of filter modules applied to received packets ";
               type string;
             }
             leaf-list output-chain {
               ordered-by user;
               description "List of filter modules applied to transmitted packets ";
               type string;
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               // uses apply-advanced;
               list rule {
                 key name;
                 ordered-by user;
                 description "Set of ADF rules";
                 leaf name {
                   description "Value for a single rule";
                   type string;
                 }
                 // uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container ingress-queuing-filter {
             description "Protocol family ingress-queuing-filter";
             leaf filter-name {
               description "Name of the ingress-queuing-filter";
               type string;
             }
           }
           container iq-policing-filter {
             description "Protocol family ingress-queuing-policing-filter";
             leaf filter-name {
               description "Name of the ingress-queuing-policing-filter";
               type string;
             }
           }
           container policer {
             description "Interface policing";
             // uses apply-advanced;
             leaf input {
               description "Name of policer applied to received packets";
               type string;
             }
             leaf output {
               description "Name of policer applied to transmitted packets";
               type string;
             }
           }
           leaf interface-mode {
             description "Interface mode (access or trunk)";
             type enumeration {
               enum "access" {
                 description "Interface mode is access";
               }
               enum "trunk" {
                 description "Interface mode is trunk";
               }
             }
           }
           leaf vlan-auto-sense {
             description "Enable VLAN auto sense on this interface";
             type empty;
           }
           leaf bridge-domain-type {
             description "Bridge domain type (svlan or bvlan)";
             type enumeration {
               enum "svlan" {
                 description "Bridge domain type svlan";
               }
               enum "bvlan" {
                 description "Bridge domain type bvlan";
               }
             }
           }
           leaf inter-switch-link {
             description "PVLAN inter switch link";
             type empty;
           }
           choice vlan_list {
             case case_1 {
               leaf vlan-id {
                 description "Access mode and trunk mode VLAN membership";
                 type union {
                   type string {
                     pattern "<.*>|$.*";
                   }
                   type uint32 {
                     range "1 .. 4094";
                   }
                 }
               }
             }
             case case_2 {
               leaf-list vlan-id-list {
                 description "Trunk mode VLAN membership for this interface";
                 type jt:vlan-range;
               }
             }
             case case_3 {
               leaf-list inner-vlan-id-list {
                 description "Trunk mode VLAN membership for this interface based on inner VLAN tag";
                 type jt:vlan-range;
               }
             }
           }
           container vlan-rewrite {
             description "Specify vlan translation";
             // uses apply-advanced;
             list translate {
               key name;
               ordered-by user;
               description "Translate incoming VLAN tag";
               leaf name {
                 description "Specify the incoming VLAN tag";
                 type union {
                   type string {
                     pattern "<.*>|$.*";
                   }
                   type uint32 {
                     range "1 .. 4094";
                   }
                 }
               }
               leaf to-vlan-id {
                 description "Specify the bridge-domain VLAN-ID";
                 type union {
                   type string {
                     pattern "<.*>|$.*";
                   }
                   type uint32 {
                     range "1 .. 4094";
                   }
                 }
               }
             }
           }
          //  choice isid_list {
          //    case case_1 {
          //      leaf isid-list {
          //        description "Specify the ISID list";
          //        type enumeration {
          //          enum "all-service-groups" {
          //            description "Map all ISIDs specified under the service-groups";
          //          }
          //          enum "all" {
          //            description "Map all ISIDs";
          //          }
          //        }
          //      }
          //    }
          //  }
          //  container storm-control {
          //    description "Storm control profile name to bind";
          //    // uses apply-advanced;
          //    leaf profile-name {
          //      description "Profile name";
          //      type string;
          //    }
          //  }
          //  container recovery-timeout {
          //    description "Recovery timeout for this interface";
          //    leaf time-in-seconds {
          //      units "seconds";
          //      type union {
          //        type string {
          //          pattern "<.*>|$.*";
          //        }
          //        type uint32 {
          //          range "10 .. 3600";
          //        }
          //      }
          //    }
          //  }
          //  container sampling {
          //    description "Interface sampling";
          //    // uses apply-advanced;
          //    leaf input {
          //      description "Sample all packets input on this interface";
          //      type empty;
          //    }
          //    leaf output {
          //      description "Sample all packets output on this interface";
          //      type empty;
          //    }
          //  }
         }
        //  container ethernet-switching {
        //    description "Ethernet switching parameters";
        //    presence "enable ethernet-switching";
        //    uses ethernet-switching-type;
        //  }
        //  container fibre-channel {
        //    description "Fibre channel switching parameters";
        //    presence "enable fibre-channel";
        //    uses fibre-channel-type;
        //  }
        //  container pppoe {
        //    description "PPP over Ethernet underlying interface-specific options";
        //    presence "enable pppoe";
        //    uses pppoe_underlying_options_type;
        //  }
         container any {
           presence "enable any";
           description "Parameters for 'any' family";
           // uses apply-advanced;
           container filter {
             description "Layer 2 packet filtering";
             // uses apply-advanced;
             leaf input {
               description "Name of filter applied to received packets";
               type string {
               }
             }
             leaf group {
               description "Group to which interface belongs";
               type union {
                 type string {
                   pattern "<.*>|$.*";
                 }
                 type uint32 {
                   range "1 .. 255";
                 }
               }
             }
           }
         }
       }
      //  leaf service-domain {
      //    description "Service domain to which interface belongs";
      //    type enumeration {
      //      enum "inside" {
      //        description "Inside network";
      //      }
      //      enum "outside" {
      //        description "Outside network";
      //      }
      //    }
      //  }
      //  leaf copy-tos-to-outer-ip-header {
      //    description "Copy IP payload header's ToS field to GRE delivery header";
      //    type empty;
      //  }
      //  leaf copy-tos-to-outer-ip-header-transit {
      //    description "Copy IP ToS field to GRE header for transit packets";
      //    type empty;
      //  }
      //  leaf force-control-packets-on-transit-path {
      //    description "Force control packets to follow transit path";
      //    type empty;
      //  }
      //  container load-balancing-options {
      //    description "AMS subunit load balancing options";
      //    // uses apply-advanced;
      //    leaf preferred-active {
      //      description "Preferred active Interface name";
      //      type union {
      //        type jt:interface-device;
      //        type string {
      //          pattern "<.*>|$.*";
      //        }
      //      }
      //    }
      //    leaf disable-hash {
      //      description "Hash based distribution is not needed for this subunit";
      //      type empty;
      //    }
      //    leaf modulo-key {
      //      description "Modulo based distribution";
      //      type enumeration {
      //        enum "source-ip" {
      //          description "Source Ip Address";
      //        }
      //        enum "destination-ip" {
      //          description "Destination Ip Address";
      //        }
      //      }
      //    }
      //    container hash-keys {
      //      // uses apply-advanced;
      //      leaf-list ingress-key {
      //        ordered-by user;
      //        description "Hash Key for the ingress direction";
      //        type enumeration {
      //          enum "source-ip" {
      //            description "Source Ip Address";
      //          }
      //          enum "destination-ip" {
      //            description "Destination Ip Address";
      //          }
      //          enum "protocol" {
      //            description "Protocol";
      //          }
      //          enum "iif" {
      //            description "Incoming Interface";
      //          }
      //        }
      //      }
      //      leaf-list egress-key {
      //        ordered-by user;
      //        description "Hash Key for the egress direction";
      //        status deprecated;
      //        type enumeration {
      //          enum "source-ip" {
      //            description "Source Ip Address";
      //            status deprecated;
      //          }
      //          enum "destination-ip" {
      //            description "Destination Ip Address";
      //            status deprecated;
      //          }
      //          enum "protocol" {
      //            description "Protocol";
      //            status deprecated;
      //          }
      //          enum "oif" {
      //            description "Outgoing Interface";
      //            status deprecated;
      //          }
      //        }
      //      }
      //      leaf ipv6-source-prefix-length {
      //        description "IPv6 source prefix length for hash computation";
      //        type enumeration {
      //          enum "56" {
      //            description "56 bit IPv6 address prefix";
      //          }
      //          enum "64" {
      //            description "64 bit IPv6 address prefix";
      //          }
      //          enum "96" {
      //            description "96 bit IPv6 address prefix";
      //          }
      //          enum "128" {
      //            description "Complete 128 bit IPv6 address";
      //          }
      //        }
      //      }
      //    }
      //  }
      //  container interface-state {
      //    description "IRB interface state computation";
      //    // uses apply-advanced;
      //    choice state {
      //      case case_1 {
      //        leaf local {
      //          description "IRB State computation based on local interface state";
      //          type empty;
      //        }
      //      }
      //      case case_2 {
      //        leaf remote {
      //          description "IRB State computation based on remote reachability";
      //          type empty;
      //        }
      //      }
      //      case case_3 {
      //        leaf local-remote {
      //          description "IRB State computation based on local or remote reachability";
      //          type empty;
      //        }
      //      }
      //      case case_4 {
      //        leaf local-interface {
      //          description "IRB State computation based on loopback AE port state";
      //          type union {
      //            type jt:interface-name;
      //            type string {
      //              pattern "<.*>|$.*";
      //            }
      //          }
      //        }
      //      }
      //    }
      //    leaf local-count {
      //      description "Minimum number of local layer2 link in up state to consider IRB up";
      //      type union {
      //        type uint16;
      //        type string {
      //          pattern "<.*>|$.*";
      //        }
      //      }
      //    }
      //    leaf vtep-count {
      //      description "Minimum number of VTEP link in up state to consider IRB up";
      //      type union {
      //        type uint16;
      //        type string {
      //          pattern "<.*>|$.*";
      //        }
      //      }
      //    }
      //    container hold-time {
      //      description "Delay before marking interface up or down for defect";
      //      // uses apply-advanced;
      //      leaf up {
      //        description "Delay in seconds before marking IRB interface up";
      //        units "seconds";
      //        type union {
      //          type uint32;
      //          type string {
      //            pattern "<.*>|$.*";
      //          }
      //        }
      //      }
      //      leaf down {
      //        description "Delay in seconds before marking IRB interface down";
      //        units "seconds";
      //        type union {
      //          type uint32;
      //          type string {
      //            pattern "<.*>|$.*";
      //          }
      //        }
      //      }
      //    }
      //  }
      //  leaf mac {
      //    description "Configure logical interface MAC address";
      //    type jt:mac-unicast;
      //  }
      //  leaf virtual-gateway-v4-mac {
      //    description "Configure virtual gateway IPV4 virtual MAC address";
      //    type jt:mac-unicast;
      //  }
      //  leaf virtual-gateway-v6-mac {
      //    description "Configure virtual gateway IPV6 virtual MAC address";
      //    type jt:mac-unicast;
      //  }
      //  leaf no-dhcp-flood {
      //    description "Disable dhcp flooding";
      //    type empty;
      //  }
      //  container forwarding-options {
      //    description "Aggregated Ethernet interface forwarding-options";
      //    // uses apply-advanced;
      //    container load-balance-stateful {
      //      description "Stateful load balancing";
      //      // uses apply-advanced;
      //      leaf per-flow {
      //        description "Enable feature";
      //        type empty;
      //      }
      //      leaf rebalance {
      //        description "Rebalancing interval";
      //        units "per minute";
      //        type union {
      //          type string {
      //            pattern "<.*>|$.*";
      //          }
      //          type uint32 {
      //            range "1 .. 1000";
      //          }
      //        }
      //      }
      //      leaf load-type {
      //        description "Load - defines the flows";
      //        type enumeration {
      //          enum "high" {
      //            description "If the no of flows on this aggregate is large(1000-10000 flows) ";
      //          }
      //          enum "medium" {
      //            description "If the no of flows on this aggregate is moderate(100-1000 flows)";
      //          }
      //          enum "low" {
      //            description "If the no of flows on this aggregate is less(1-100)";
      //          }
      //        }
      //      }
      //    }
      //  }
      //  leaf etree-ac-role {
      //    description "ETREE attachment circuit role";
      //    type enumeration {
      //      enum "root" {
      //        description "ETREE root interface";
      //      }
      //      enum "leaf" {
      //        description "ETREE leaf interface";
      //      }
      //    }
      //  }
      //  container load-balance {
      //    description "Load-balance weight per subscriber interface";
      //    // uses apply-advanced;
      //    leaf weight {
      //      description "Load-balance weight";
      //      type union {
      //        type string {
      //          pattern "<.*>|$.*";
      //        }
      //        type uint32 {
      //          range "1 .. 1000";
      //        }
      //      }
      //    }
      //  }
     }
    //  container no-partition {
    //    description "Use channelizable interface as clear channel";
    //    leaf interface-type {
    //      description "Interface type";
    //      type enumeration {
    //        enum "e1" {
    //          description "E1 interface";
    //        }
    //        enum "t1" {
    //          description "T1 interface";
    //        }
    //        enum "at" {
    //          description "ATM interface";
    //        }
    //        enum "t3" {
    //          description "T3 interface";
    //        }
    //        enum "e3" {
    //          description "E3 interface";
    //        }
    //        enum "ct3" {
    //          description "Channelized T3 interface";
    //        }
    //        enum "so" {
    //          description "SONET interface";
    //        }
    //        enum "cau4" {
    //          description "CAU4 interface";
    //        }
    //      }
    //    }
    //  }
    //  list partition {
    //    key name;
    //    ordered-by user;
    //    description "Channelized interface partition";
    //    leaf name {
    //      description "Sublevel interface partition index (for example, 1, 3-4)";
    //      type string;
    //    }
    //    leaf oc-slice {
    //      description "Range of SONET/SDH slices (for example, 1, 7-9)";
    //      type string;
    //    }
    //    leaf timeslots {
    //      description "Timeslots [(1..24) for T1, (1..31) for E1]; for example, 1-3,4,9,22-24 (no spaces)";
    //      type string;
    //    }
    //    leaf interface-type {
    //      description "Sublevel interface type";
    //      type enumeration {
    //        enum "ds" {
    //          description "DS0 interface";
    //        }
    //        enum "e1" {
    //          description "E1 interface";
    //        }
    //        enum "t1" {
    //          description "T1 interface";
    //        }
    //        enum "at" {
    //          description "ATM interface";
    //        }
    //        enum "ct1" {
    //          description "Channelized T1 interface";
    //        }
    //        enum "ce1" {
    //          description "Channelized E1 interface";
    //        }
    //        enum "t3" {
    //          description "T3 interface";
    //        }
    //        enum "ct3" {
    //          description "Channelized T3 interface";
    //        }
    //        enum "e3" {
    //          description "E3 interface";
    //        }
    //        enum "so" {
    //          description "SONET interface";
    //        }
    //        enum "coc1" {
    //          description "Channelized OC1 interface";
    //        }
    //        enum "cau4" {
    //          description "Channelized AU4 interface";
    //        }
    //        enum "dc" {
    //          description "D channel interface";
    //        }
    //        enum "bc" {
    //          description "B channel interface";
    //        }
    //      }
    //    }
    //  }
    //  container radius-options {
    //    description "Interface RADIUS Options";
    //    uses radius_options_vlan_type;
    //  }
    //  leaf rpf-stats {
    //    description "Enable Reverse path forwarding stats for this interface";
    //    type empty;
    //  }
   }
  //  grouping keepalives_type {
  //    // uses apply-advanced;
  //    leaf interval {
  //      description "Keepalive period";
  //      units "seconds";
  //      type union {
  //        type string {
  //          pattern "<.*>|$.*";
  //        }
  //        type uint16 {
  //          range "1 .. 32767";
  //        }
  //      }
  //    }
  //    leaf up-count {
  //      description "Keepalive received to bring link up";
  //      type union {
  //        type string {
  //          pattern "<.*>|$.*";
  //        }
  //        type uint16 {
  //          range "1 .. 255";
  //        }
  //      }
  //    }
  //    leaf down-count {
  //      description "Keepalive missed to bring link down";
  //      type union {
  //        type string {
  //          pattern "<.*>|$.*";
  //        }
  //        type uint16 {
  //          range "1 .. 255";
  //        }
  //      }
  //    }
  //  }
  //  grouping log-object {
  //    description "Configure auditable security logs";
  //    // uses apply-advanced;
  //    list exclude {
  //      key name;
  //      ordered-by user;
  //      description "List of security log criteria to exclude from the audit log";
  //      status deprecated;
  //      leaf name {
  //        description "Exclude criteria name";
  //        type string;
  //      }
  //      // uses apply-advanced;
  //      leaf destination-address {
  //        description "Destination address";
  //        type jt:ipaddr;
  //      }
  //      leaf destination-port {
  //        description "Destination port";
  //        type union {
  //          type uint32;
  //          type string {
  //            pattern "<.*>|$.*";
  //          }
  //        }
  //      }
  //      leaf event-id {
  //        description "Event ID filter";
  //        type string;
  //      }
  //      leaf failure {
  //        description "Event was a failure";
  //        type empty;
  //      }
  //      leaf interface-name {
  //        description "Name of interface";
  //        type string;
  //      }
  //      leaf policy-name {
  //        description "Policy name filter";
  //        type string;
  //      }
  //      leaf process {
  //        description "Process that generated the event";
  //        type string;
  //      }
  //      leaf protocol {
  //        description "Protocol filter";
  //        type string;
  //      }
  //      leaf source-address {
  //        description "Source address";
  //        type jt:ipaddr;
  //      }
  //      leaf source-port {
  //        description "Source port";
  //        type union {
  //          type uint32;
  //          type string {
  //            pattern "<.*>|$.*";
  //          }
  //        }
  //      }
  //      leaf success {
  //        description "Event was successful";
  //        type empty;
  //      }
  //      leaf username {
  //        description "Username filter";
  //        type string;
  //      }
  //    }
  //    leaf limit {
  //      description "Limit number of security log entries to keep in memory";
  //      status deprecated;
  //      default "10000";
  //      type union {
  //        type uint32;
  //        type string {
  //          pattern "<.*>|$.*";
  //        }
  //      }
  //    }
  //    container cache {
  //      presence "enable cache";
  //      description "Cache security log events in the audit log buffer";
  //      // uses apply-advanced;
  //      list exclude {
  //        key name;
  //        ordered-by user;
  //        description "List of security log criteria to exclude from the audit log";
  //        leaf name {
  //          description "Exclude criteria name";
  //          type string;
  //        }
  //        // uses apply-advanced;
  //        leaf destination-address {
  //          description "Destination address";
  //          type jt:ipaddr;
  //        }
  //        leaf destination-port {
  //          description "Destination port";
  //          type union {
  //            type uint32;
  //            type string {
  //              pattern "<.*>|$.*";
  //            }
  //          }
  //        }
  //        leaf event-id {
  //          description "Event ID filter";
  //          type string;
  //        }
  //        leaf failure {
  //          description "Event was a failure";
  //          type empty;
  //        }
  //        leaf interface-name {
  //          description "Name of interface";
  //          type string;
  //        }
  //        leaf policy-name {
  //          description "Policy name filter";
  //          type string;
  //        }
  //        leaf process {
  //          description "Process that generated the event";
  //          type string;
  //        }
  //        leaf protocol {
  //          description "Protocol filter";
  //          type string;
  //        }
  //        leaf source-address {
  //          description "Source address";
  //          type jt:ipaddr;
  //        }
  //        leaf source-port {
  //          description "Source port";
  //          type union {
  //            type uint32;
  //            type string {
  //              pattern "<.*>|$.*";
  //            }
  //          }
  //        }
  //        leaf success {
  //          description "Event was successful";
  //          type empty;
  //        }
  //        leaf username {
  //          description "Username filter";
  //          type string;
  //        }
  //      }
  //      leaf limit {
  //        description "Limit number of security log entries to keep in memory";
  //        default "10000";
  //        type union {
  //          type uint32;
  //          type string {
  //            pattern "<.*>|$.*";
  //          }
  //        }
  //      }
  //    }
  //    list host {
  //      key name;
  //      ordered-by user;
  //      max-elements 10;
  //      leaf name {
  //        description "Name of host to notify";
  //        type string {
  //        }
  //      }
  //      // uses apply-advanced;
  //      list contents {
  //        key name;
  //        leaf name {
  //          description "Facility type";
  //          type enumeration {
  //            enum "services" {
  //              description "Adaptive Services PIC";
  //            }
  //          }
  //        }
  //        choice level {
  //          case case_1 {
  //            leaf any {
  //              description "All levels";
  //              type empty;
  //            }
  //          }
  //          case case_2 {
  //            leaf emergency {
  //              description "Panic conditions";
  //              type empty;
  //            }
  //          }
  //          case case_3 {
  //            leaf alert {
  //              description "Conditions that should be corrected immediately";
  //              type empty;
  //            }
  //          }
  //          case case_4 {
  //            leaf critical {
  //              description "Critical conditions";
  //              type empty;
  //            }
  //          }
  //          case case_5 {
  //            leaf error {
  //              description "Error conditions";
  //              type empty;
  //            }
  //          }
  //          case case_6 {
  //            leaf warning {
  //              description "Warning messages";
  //              type empty;
  //            }
  //          }
  //          case case_7 {
  //            leaf notice {
  //              description "Conditions that should be handled specially";
  //              type empty;
  //            }
  //          }
  //          case case_8 {
  //            leaf info {
  //              description "Informational messages";
  //              type empty;
  //            }
  //          }
  //          case case_9 {
  //            leaf none {
  //              description "No messages";
  //              type empty;
  //            }
  //          }
  //        }
  //      }
  //      leaf facility-override {
  //        description "Alternate facility for logging to remote host";
  //        type enumeration {
  //          enum "authorization" {
  //            description "Authorization system";
  //          }
  //          enum "daemon" {
  //            description "Various system processes";
  //          }
  //          enum "ftp" {
  //            description "FTP process";
  //          }
  //          enum "kernel" {
  //            description "Kernel";
  //          }
  //          enum "user" {
  //            description "User processes";
  //          }
  //          enum "local0" {
  //            description "Local logging option number 0";
  //          }
  //          enum "local1" {
  //            description "Local logging option number 1";
  //          }
  //          enum "local2" {
  //            description "Local logging option number 2";
  //          }
  //          enum "local3" {
  //            description "Local logging option number 3";
  //          }
  //          enum "local4" {
  //            description "Local logging option number 4";
  //          }
  //          enum "local5" {
  //            description "Local logging option number 5";
  //          }
  //          enum "local6" {
  //            description "Local logging option number 6";
  //          }
  //          enum "local7" {
  //            description "Local logging option number 7";
  //          }
  //        }
  //      }
  //      leaf log-prefix {
  //        description "Prefix for all logging to this host";
  //        type string {
  //        }
  //      }
  //      leaf port {
  //        description "UDP port for syslogd on the host";
  //        type union {
  //          type string {
  //            pattern "<.*>|$.*";
  //          }
  //          type uint16 {
  //            range "1 .. 65535";
  //          }
  //        }
  //      }
  //      container class {
  //        description "Syslog messages classes";
  //        // uses apply-advanced;
  //        container session-logs {
  //          presence "enable session-logs";
  //          description "Allow syslog messages for session events";
  //          // uses apply-advanced;
  //          container open {
  //            presence "enable open";
  //            description "Allow syslog messages for session open events";
  //          }
  //          container close {
  //            presence "enable close";
  //            description "Allow syslog messages for session close events";
  //          }
  //        }
  //        container packet-logs {
  //          presence "enable packet-logs";
  //          description "Allow syslog messages for packet related events";
  //        }
  //        container stateful-firewall-logs {
  //          presence "enable stateful-firewall-logs";
  //          description "Allow syslog messages for stateful firewall events";
  //        }
  //        container alg-logs {
  //          presence "enable alg-logs";
  //          description "Allow syslog messages for ALG events";
  //        }
  //        container nat-logs {
  //          presence "enable nat-logs";
  //          description "Allow syslog messages for NAT events";
  //          // uses apply-advanced;
  //          container deterministic-nat-configuration-log {
  //            presence "enable deterministic-nat-configuration-log";
  //            description "Allow syslog messages for Determinisitic NAT config events";
  //          }
  //        }
  //        container ids-logs {
  //          presence "enable ids-logs";
  //          description "Allow syslog messages for IDS events";
  //        }
  //        container pcp-logs {
  //          presence "enable pcp-logs";
  //          description "PCP logs";
  //          container map {
  //            presence "enable map";
  //            description "Allow syslog messages for PCP";
  //          }
  //          container debug {
  //            presence "enable debug";
  //            description "Allow PCP debug syslogs";
  //          }
  //        }
  //        container ha-logs {
  //          description "Stateful high availability logs";
  //          // uses apply-advanced;
  //          container open-synchronized {
  //            presence "enable open-synchronized";
  //            description "Allow syslog message for session open events";
  //          }
  //          container close-synchronized {
  //            presence "enable close-synchronized";
  //            description "Allow syslog message for session close events";
  //          }
  //        }
  //        container urlf-logs {
  //          presence "enable urlf-logs";
  //          description "Allow syslog messages for URLF events";
  //        }
  //      }
  //      leaf source-address {
  //        description "Use specified address as source address";
  //        type jt:ipv4addr;
  //      }
  //      container tcp-log {
  //        presence "enable tcp-log";
  //        description "Enable tcp log for this service-set";
  //        // uses apply-advanced;
  //        leaf source-address {
  //          description "Source address for tcp logging";
  //          type jt:ipaddr;
  //        }
  //        leaf vrf-name {
  //          description "Routing instance name for tcp logging";
  //          type string;
  //        }
  //        leaf ssl-profile {
  //          description "SSL profile name for tcp logging";
  //          type string {
  //            length "1 .. 63";
  //          }
  //        }
  //      }
  //    }
  //    leaf message-rate-limit {
  //      description "Maximum syslog messages per second allowed from this interface. Applies per member if set at aggregate level";
  //      units "messages per second";
  //      type union {
  //        type string {
  //          pattern "<.*>|$.*";
  //        }
  //        type uint32 {
  //          range "0 .. 2147483647";
  //        }
  //      }
  //    }
  //  }
  //  grouping mac_list {
  //    description "MAC address";
  //    leaf name {
  //      type jt:mac-addr;
  //    }
  //    // uses apply-advanced;
  //    container policer {
  //      description "MAC policing";
  //      // uses apply-advanced;
  //      leaf input {
  //        description "Name of policer applied to received packets";
  //        type string;
  //      }
  //      leaf output {
  //        description "Name of policer applied to transmitted packets";
  //        type string;
  //      }
  //    }
  //  }
  //  grouping macro-data-type {
  //    leaf name {
  //      description "Keyword part of the keyword-value pair";
  //      type string;
  //    }
  //    leaf value {
  //      description "Value part of the keyword-value pair";
  //      type string;
  //    }
  //  }
   grouping mpls_ifd_options {
     // uses apply-advanced;
     container pop-all-labels {
       presence "enable pop-all-labels";
       description "Pop all MPLS labels off incoming packets";
       // uses apply-advanced;
       leaf-list required-depth {
         ordered-by user;
         description "Required label depth of packet to pop all labels";
         type enumeration {
           enum "all" {
             description "Takes effect only in Stoli based FPCs, in all other FPCs equivalent to '[1 2]'";
           }
           enum "1" {
             description "Required label depth of packet to pop labels";
           }
           enum "2" {
             description "Required label depth of packet to pop labels";
           }
         }
       }
     }
   }
  //  grouping multi-chassis-protection-group {
  //    leaf name {
  //      description "IP address for this peer";
  //      type jt:ipv4addr;
  //    }
  //    // uses apply-advanced;
  //    leaf interface {
  //      description "Inter-Chassis protection link";
  //      type string {
  //        length "1 .. 40";
  //      }
  //    }
  //    leaf icl-down-delay {
  //      description "Time in seconds between ICL down and MCAEs moving to standby";
  //      default "1";
  //      units "seconds";
  //      type union {
  //        type string {
  //          pattern "<.*>|$.*";
  //        }
  //        type int32 {
  //          range "1 .. 6000";
  //        }
  //      }
  //    }
  //  }
  //  grouping multi-chassis-protection-group-ifl {
  //    leaf name {
  //      description "IP address for this peer";
  //      type jt:ipv4addr;
  //    }
  //    // uses apply-advanced;
  //    leaf interface {
  //      description "Inter-Chassis protection link";
  //      type string {
  //        length "1 .. 40";
  //      }
  //    }
  //    leaf icl-down-delay {
  //      description "Time in seconds between ICL down and MCAEs moving to standby";
  //      default "1";
  //      units "seconds";
  //      type union {
  //        type string {
  //          pattern "<.*>|$.*";
  //        }
  //        type int32 {
  //          range "1 .. 6000";
  //        }
  //      }
  //    }
  //  }
  //  grouping och-attributes {
  //    description "Optical channel configuration attributes";
  //    // uses apply-advanced;
  //    leaf rate {
  //      description "Data rate of the OCH payload";
  //      type enumeration {
  //        enum "100g" {
  //          description "100Gbit OCH data rate";
  //        }
  //      }
  //    }
  //    leaf modulation {
  //      description "Optical modulation format";
  //      type enumeration {
  //        enum "qpsk" {
  //          description "QPSK Modulation Format";
  //        }
  //      }
  //    }
  //    leaf encoding {
  //      description "Optical encoding";
  //      type enumeration {
  //        enum "differential" {
  //          description "Differential encoding";
  //        }
  //      }
  //    }
  //    choice channel-number {
  //      case case_1 {
  //        leaf wavelength {
  //          description "Optical channel wavelength in nanometers";
  //          type enumeration {
  //            enum "1568.77" {
  //              description "1568.77 nm/191.1003 THz 50/100Ghz spacing";
  //            }
  //            enum "1568.36" {
  //              description "1568.36 nm/191.15000 THz 6.25/12.5/50GHz spacing";
  //            }
  //            enum "1568.31" {
  //              description "1568.31 nm/191.15625 THz 6.25GHz spacing";
  //            }
  //            enum "1568.26" {
  //              description "1568.26 nm/191.16250 THz 6.25/12.5GHz spacing";
  //            }
  //            enum "1568.21" {
  //              description "1568.21 nm/191.16875 THz 6.25GHz spacing";
  //            }
  //            enum "1568.16" {
  //              description "1568.16 nm/191.17500 THz 6.25/12.5GHz spacing";
  //            }
  //            enum "1568.11" {
  //              description "1568.11 nm/191.18125 THz 6.25GHz spacing";
  //            }
  //            enum "1568.05" {
  //              description "1568.05 nm/191.18750 THz 6.25/12.5GHz spacing";
  //            }
  //            enum "1568.00" {
  //              description "1568.00 nm/191.19375 THz 6.25GHz spacing";
  //            }
  //            enum "1567.95" {
  //              description "1567.95 nm/191.20000 THz 6.25/12.5/50/100GHz spacing";
  //            }
  //            enum "1567.90" {
  //              description "1567.90 nm/191.20625 THz 6.25GHz spacing";
  //            }
  //            enum "1567.85" {
  //              description "1567.85 nm/191.21250 THz 6.25/12.5GHz spacing";
  //            }
  //            enum "1567.80" {
  //              description "1567.80 nm/191.21875 THz 6.25GHz spacing";
  //            }
  //            enum "1567.75" {
  //              description "1567.75 nm/191.22500 THz 6.25/12.5GHz spacing";
  //            }
  //            enum "1567.70" {
  //              description "1567.70 nm/191.23125 THz 6.25GHz spacing";
  //            }
  //            enum "1567.64" {
  //              description "1567.64 nm/191.23750 THz 6.25/12.5GHz spacing";
  //            }
  //            enum "1567.59" {
  //              description "1567.59 nm/191.24375 THz 6.25GHz spacing";
  //            }
  //            enum "1567.54" {
  //              description "1567.54 nm/191.25000 THz 6.25/12.5/50GHz spacing";
  //            }
  //            enum "1567.49" {
  //              description "1567.49 nm/191.25625 THz 6.25GHz spacing";
  //            }
  //            enum "1567.44" {
  //              description "1567.44 nm/191.26250 THz 6.25/12.5GHz spacing";
  //            }
  //            enum "1567.39" {
  //              description "1567.39 nm/191.26875 THz 6.25GHz spacing";
  //            }
  //            enum "1567.34" {
  //              description "1567.34 nm/191.27500 THz 6.25/12.5GHz spacing";
  //            }
  //            enum "1567.29" {
  //              description "1567.29 nm/191.28125 THz 6.25GHz spacing";
  //            }
  //            enum "1567.23" {
  //              description "1567.23 nm/191.28750 THz 6.25/12.5GHz spacing";
  //            }
  //            enum "1567.18" {
  //              description "1567.18 nm/191.29375 THz 6.25GHz spacing";
  //            }
  //            enum "1567.13" {
  //              description "1567.13 nm/191.30000 THz 6.25/12.5/50/100GHz spacing";
  //            }
  //            enum "1567.08" {
  //              description "1567.08 nm/191.30625 THz 6.25GHz spacing";
  //            }
  //            enum "1567.03" {
  //              description "1567.03 nm/191.31250 THz 6.25/12.5GHz spacing";
  //            }
  //            enum "1566.98" {
  //              description "1566.98 nm/191.31875 THz 6.25GHz spacing";
  //            }
  //            enum "1566.93" {
  //              description "1566.93 nm/191.32500 THz 6.25/12.5GHz spacing";
  //            }
  //            enum "1566.88" {
  //              description "1566.88 nm/191.33125 THz 6.25GHz spacing";
  //            }
  //            enum "1566.83" {
  //              description "1566.83 nm/191.33750 THz 6.25/12.5GHz spacing";
  //            }
  //            enum "1566.77" {
  //              description "1566.77 nm/191.34375 THz 6.25GHz spacing";
  //            }
  //            enum "1566.72" {
  //              description "1566.72 nm/191.35000 THz 6.25/12.5/50GHz spacing";
  //            }
  //            enum "1566.67" {
  //              description "1566.67 nm/191.35625 THz 6.25GHz spacing";
  //            }
  //            enum "1566.62" {
  //              description "1566.62 nm/191.36250 THz 6.25/12.5GHz spacing";
  //            }
  //            enum "1566.57" {
  //              description "1566.57 nm/191.36875 THz 6.25GHz spacing";
  //            }
  //            enum "1566.52" {
  //              description "1566.52 nm/191.37500 THz 6.25/12.5/75GHz spacing";
  //            }
  //            enum "1566.47" {
  //              description "1566.47 nm/191.38125 THz 6.25GHz spacing";
  //            }
  //            enum "1566.42" {
  //              description "1566.42 nm/191.38750 THz 6.25/12.5GHz spacing";
  //            }
  //            enum "1566.36" {
  //              description "1566.36 nm/191.39375 THz 6.25GHz spacing";
  //            }
  //            enum "1566.31" {
  //              description "1566.31 nm/191.40000 THz 6.25/12.5/50/100GHz spacing";
  //            }
  //            enum "1566.26" {
  //              description "1566.26 nm/191.40625 THz 6.25GHz spacing";
  //            }
  //            enum "1566.21" {
  //              description "1566.21 nm/191.41250 THz 6.25/12.5GHz spacing";
  //            }
  //            enum "1566.16" {
  //              description "1566.16 nm/191.41875 THz 6.25GHz spacing";
  //            }
  //            enum "1566.11" {
  //              description "1566.11 nm/191.42500 THz 6.25/12.5GHz spacing";
  //            }
  //            enum "1566.06" {
  //              description "1566.06 nm/191.43125 THz 6.25GHz spacing";
  //            }
  //            enum "1566.01" {
  //              description "1566.01 nm/191.43750 THz 6.25/12.5GHz spacing";
  //            }
  //            enum "1565.96" {
  //              description "1565.96 nm/191.44375 THz 6.25GHz spacing";
  //            }
  //            enum "1565.90" {
  //              description "1565.90 nm/191.45000 THz 6.25/12.5/50/75GHz spacing";
  //            }
  //            enum "1565.85" {
  //              description "1565.85 nm/191.45625 THz 6.25GHz spacing";
  //            }
  //            enum "1565.80" {
  //              description "1565.80 nm/191.46250 THz 6.25/12.5GHz spacing";
  //            }
  //            enum "1565.75" {
  //              description "1565.75 nm/191.46875 THz 6.25GHz spacing";
  //            }
  //            enum "1565.70" {
  //              description "1565.70 nm/191.47500 THz 6.25/12.5GHz spacing";
  //            }
  //            enum "1565.65" {
  //              description "1565.65 nm/191.48125 THz 6.25GHz spacing";
  //            }
  //            enum "1565.60" {
  //              description "1565.60 nm/191.48750 THz 6.25/12.5GHz spacing";
  //            }
  //            enum "1565.55" {
  //              description "1565.55 nm/191.49375 THz 6.25GHz spacing";
  //            }
  //            enum "1565.50" {
  //              description "1565.50 nm/191.50000 THz 6.25/12.5/50/100GHz spacing";
  //            }
  //            enum "1565.44" {
  //              description "1565.44 nm/191.50625 THz 6.25GHz spacing";
  //            }
  //            enum "1565.39" {
  //              description "1565.39 nm/191.51250 THz 6.25/12.5GHz spacing";
  //            }
  //            enum "1565.34" {
  //              description "1565.34 nm/191.51875 THz 6.25GHz spacing";
  //            }
  //            enum "1565.29" {
  //              description "1565.29 nm/191.52500 THz 6.25/12.5/75GHz spacing";
  //            }
  //            enum "1565.24" {
  //              description "1565.24 nm/191.53125 THz 6.25GHz spacing";
  //            }
  //            enum "1565.19" {
  //              description "1565.19 nm/191.53750 THz 6.25/12.5GHz spacing";
  //            }
  //            enum "1565.14" {
  //              description "1565.14 nm/191.54375 THz 6.25GHz spacing";
  //            }
  //            enum "1565.09" {
  //              description "1565.09 nm/191.55000 THz 6.25/12.5/50GHz spacing";
  //            }
  //            enum "1565.04" {
  //              description "1565.04 nm/191.55625 THz 6.25GHz spacing";
  //            }
  //            enum "1564.99" {
  //              description "1564.99 nm/191.56250 THz 6.25/12.5GHz spacing";
  //            }
  //            enum "1564.93" {
  //              description "1564.93 nm/191.56875 THz 6.25GHz spacing";
  //            }
  //            enum "1564.88" {
  //              description "1564.88 nm/191.57500 THz 6.25/12.5GHz spacing";
  //            }
  //            enum "1564.83" {
  //              description "1564.83 nm/191.58125 THz 6.25GHz spacing";
  //            }
  //            enum "1564.78" {
  //              description "1564.78 nm/191.58750 THz 6.25/12.5GHz spacing";
  //            }
  //            enum "1564.73" {
  //              description "1564.73 nm/191.59375 THz 6.25GHz spacing";
  //            }
  //            enum "1564.68" {
  //              description "1564.68 nm/191.60000 THz 6.25/12.5/50/75/100GHz spacing";
  //            }
  //            enum "1564.63" {
  //              description "1564.63 nm/191.60625 THz 6.25GHz spacing";
  //            }
  //            enum "1564.58" {
  //              description "1564.58 nm/191.61250 THz 6.25/12.5GHz spacing";
  //            }
  //            enum "1564.53" {
  //              description "1564.53 nm/191.61875 THz 6.25GHz spacing";
  //            }
  //            enum "1564.47" {
  //              description "1564.47 nm/191.62500 THz 6.25/12.5GHz spacing";
  //            }
  //            enum "1564.42" {
  //              description "1564.42 nm/191.63125 THz 6.25GHz spacing";
  //            }
  //            enum "1564.37" {
  //              description "1564.37 nm/191.63750 THz 6.25/12.5GHz spacing";
  //            }
  //            enum "1564.32" {
  //              description "1564.32 nm/191.64375 THz 6.25GHz spacing";
  //            }
  //            enum "1564.27" {
  //              description "1564.27 nm/191.65000 THz 6.25/12.5/50GHz spacing";
  //            }
  //            enum "1564.22" {
  //              description "1564.22 nm/191.65625 THz 6.25GHz spacing";
  //            }
  //            enum "1564.17" {
  //              description "1564.17 nm/191.66250 THz 6.25/12.5GHz spacing";
  //            }
  //            enum "1564.12" {
  //              description "1564.12 nm/191.66875 THz 6.25GHz spacing";
  //            }
  //            enum "1564.07" {
  //              description "1564.07 nm/191.67500 THz 6.25/12.5/75GHz spacing";
  //            }
  //            enum "1564.02" {
  //              description "1564.02 nm/191.68125 THz 6.25GHz spacing";
  //            }
  //            enum "1563.96" {
  //              description "1563.96 nm/191.68750 THz 6.25/12.5GHz spacing";
  //            }
  //            enum "1563.91" {
  //              description "1563.91 nm/191.69375 THz 6.25GHz spacing";
  //            }
  //            enum "1563.86" {
  //              description "1563.86 nm/191.70000 THz 6.25/12.5/50/100GHz spacing";
  //            }
  //            enum "1563.81" {
  //              description "1563.81 nm/191.70625 THz 6.25GHz spacing";
  //            }
  //            enum "1563.76" {
  //              description "1563.76 nm/191.71250 THz 6.25/12.5GHz spacing";
  //            }
  //            enum "1563.71" {
  //              description "1563.71 nm/191.71875 THz 6.25GHz spacing";
  //            }
  //            enum "1563.66" {
  //              description "1563.66 nm/191.72500 THz 6.25/12.5GHz spacing";
  //            }
  //            enum "1563.61" {
  //              description "1563.61 nm/191.73125 THz 6.25GHz spacing";
  //            }
  //            enum "1563.56" {
  //              description "1563.56 nm/191.73750 THz 6.25/12.5GHz spacing";
  //            }
  //            enum "1563.51" {
  //              description "1563.51 nm/191.74375 THz 6.25GHz spacing";
  //            }
  //            enum "1563.45" {
  //              description "1563.45 nm/191.75000 THz 6.25/12.5/50/75GHz spacing";
  //            }
  //            enum "1563.40" {
  //              description "1563.40 nm/191.75625 THz 6.25GHz spacing";
  //            }
  //            enum "1563.35" {
  //              description "1563.35 nm/191.76250 THz 6.25/12.5GHz spacing";
  //            }
  //            enum "1563.30" {
  //              description "1563.30 nm/191.76875 THz 6.25GHz spacing";
  //            }
  //            enum "1563.25" {
  //              description "1563.25 nm/191.77500 THz 6.25/12.5GHz spacing";
  //            }
  //            enum "1563.20" {
  //              description "1563.20 nm/191.78125 THz 6.25GHz spacing";
  //            }
  //            enum "1563.15" {
  //              description "1563.15 nm/191.78750 THz 6.25/12.5GHz spacing";
  //            }
  //            enum "1563.10" {
  //              description "1563.10 nm/191.79375 THz 6.25GHz spacing";
  //            }
  //            enum "1563.05" {
  //              description "1563.05 nm/191.80000 THz 6.25/12.5/50/100GHz spacing";
  //            }
  //            enum "1563.00" {
  //              description "1563.00 nm/191.80625 THz 6.25GHz spacing";
  //            }
  //            enum "1562.95" {
  //              description "1562.95 nm/191.81250 THz 6.25/12.5GHz spacing";
  //            }
  //            enum "1562.89" {
  //              description "1562.89 nm/191.81875 THz 6.25GHz spacing";
  //            }
  //            enum "1562.84" {
  //              description "1562.84 nm/191.82500 THz 6.25/12.5/75GHz spacing";
  //            }
  //            enum "1562.79" {
  //              description "1562.79 nm/191.83125 THz 6.25GHz spacing";
  //            }
  //            enum "1562.74" {
  //              description "1562.74 nm/191.83750 THz 6.25/12.5GHz spacing";
  //            }
  //            enum "1562.69" {
  //              description "1562.69 nm/191.84375 THz 6.25GHz spacing";
  //            }
  //            enum "1562.64" {
  //              description "1562.64 nm/191.85000 THz 6.25/12.5/50GHz spacing";
  //            }
  //            enum "1562.59" {
  //              description "1562.59 nm/191.85625 THz 6.25GHz spacing";
  //            }
  //            enum "1562.54" {
  //              description "1562.54 nm/191.86250 THz 6.25/12.5GHz spacing";
  //            }
  //            enum "1562.49" {
  //              description "1562.49 nm/191.86875 THz 6.25GHz spacing";
  //            }
  //            enum "1562.44" {
  //              description "1562.44 nm/191.87500 THz 6.25/12.5GHz spacing";
  //            }
  //            enum "1562.39" {
  //              description "1562.39 nm/191.88125 THz 6.25GHz spacing";
  //            }
  //            enum "1562.33" {
  //              description "1562.33 nm/191.88750 THz 6.25/12.5GHz spacing";
  //            }
  //            enum "1562.28" {
  //              description "1562.28 nm/191.89375 THz 6.25GHz spacing";
  //            }
  //            enum "1562.23" {
  //              description "1562.23 nm/191.90000 THz 6.25/12.5/50/75/100GHz spacing";
  //            }
  //            enum "1562.18" {
  //              description "1562.18 nm/191.90625 THz 6.25GHz spacing";
  //            }
  //            enum "1562.13" {
  //              description "1562.13 nm/191.91250 THz 6.25/12.5GHz spacing";
  //            }
  //            enum "1562.08" {
  //              description "1562.08 nm/191.91875 THz 6.25GHz spacing";
  //            }
  //            enum "1562.03" {
  //              description "1562.03 nm/191.92500 THz 6.25/12.5GHz spacing";
  //            }
  //            enum "1561.98" {
  //              description "1561.98 nm/191.93125 THz 6.25GHz spacing";
  //            }
  //            enum "1561.93" {
  //              description "1561.93 nm/191.93750 THz 6.25/12.5GHz spacing";
  //            }
  //            enum "1561.88" {
  //              description "1561.88 nm/191.94375 THz 6.25GHz spacing";
  //            }
  //            enum "1561.83" {
  //              description "1561.83 nm/191.95000 THz 6.25/12.5/50GHz spacing";
  //            }
  //            enum "1561.77" {
  //              description "1561.77 nm/191.95625 THz 6.25GHz spacing";
  //            }
  //            enum "1561.72" {
  //              description "1561.72 nm/191.96250 THz 6.25/12.5GHz spacing";
  //            }
  //            enum "1561.67" {
  //              description "1561.67 nm/191.96875 THz 6.25GHz spacing";
  //            }
  //            enum "1561.62" {
  //              description "1561.62 nm/191.97500 THz 6.25/12.5/75GHz spacing";
  //            }
  //            enum "1561.57" {
  //              description "1561.57 nm/191.98125 THz 6.25GHz spacing";
  //            }
  //            enum "1561.52" {
  //              description "1561.52 nm/191.98750 THz 6.25/12.5GHz spacing";
  //            }
  //            enum "1561.47" {
  //              description "1561.47 nm/191.99375 THz 6.25GHz spacing";
  //            }
  //            enum "1561.42" {
  //              description "1561.42 nm/192.00000 THz 6.25/12.5/50/100GHz spacing";
  //            }
  //            enum "1561.37" {
  //              description "1561.37 nm/192.00625 THz 6.25GHz spacing";
  //            }
  //            enum "1561.32" {
  //              description "1561.32 nm/192.01250 THz 6.25/12.5GHz spacing";
  //            }
  //            enum "1561.27" {
  //              description "1561.27 nm/192.01875 THz 6.25GHz spacing";
  //            }
  //            enum "1561.22" {
  //              description "1561.22 nm/192.02500 THz 6.25/12.5GHz spacing";
  //            }
  //            enum "1561.16" {
  //              description "1561.16 nm/192.03125 THz 6.25GHz spacing";
  //            }
  //            enum "1561.11" {
  //              description "1561.11 nm/192.03750 THz 6.25/12.5GHz spacing";
  //            }
  //            enum "1561.06" {
  //              description "1561.06 nm/192.04375 THz 6.25GHz spacing";
  //            }
  //            enum "1561.01" {
  //              description "1561.01 nm/192.05000 THz 6.25/12.5/50G/75Hz spacing";
  //            }
  //            enum "1560.96" {
  //              description "1560.96 nm/192.05625 THz 6.25GHz spacing";
  //            }
  //            enum "1560.91" {
  //              description "1560.91 nm/192.06250 THz 6.25/12.5GHz spacing";
  //            }
  //            enum "1560.86" {
  //              description "1560.86 nm/192.06875 THz 6.25GHz spacing";
  //            }
  //            enum "1560.81" {
  //              description "1560.81 nm/192.07500 THz 6.25/12.5GHz spacing";
  //            }
  //            enum "1560.76" {
  //              description "1560.76 nm/192.08125 THz 6.25GHz spacing";
  //            }
  //            enum "1560.71" {
  //              description "1560.71 nm/192.08750 THz 6.25/12.5GHz spacing";
  //            }
  //            enum "1560.66" {
  //              description "1560.66 nm/192.09375 THz 6.25GHz spacing";
  //            }
  //            enum "1560.61" {
  //              description "1560.61 nm/192.10000 THz 6.25/12.5/50/100GHz spacing";
  //            }
  //            enum "1560.56" {
  //              description "1560.56 nm/192.10625 THz 6.25GHz spacing";
  //            }
  //            enum "1560.50" {
  //              description "1560.50 nm/192.11250 THz 6.25/12.5GHz spacing";
  //            }
  //            enum "1560.45" {
  //              description "1560.45 nm/192.11875 THz 6.25GHz spacing";
  //            }
  //            enum "1560.40" {
  //              description "1560.40 nm/192.12500 THz 6.25/12.5/75GHz spacing";
  //            }
  //            enum "1560.35" {
  //              description "1560.35 nm/192.13125 THz 6.25GHz spacing";
  //            }
  //            enum "1560.30" {
  //              description "1560.30 nm/192.13750 THz 6.25/12.5GHz spacing";
  //            }
  //            enum "1560.25" {
  //              description "1560.25 nm/192.14375 THz 6.25GHz spacing";
  //            }
  //            enum "1560.20" {
  //              description "1560.20 nm/192.15000 THz 6.25/12.5/50GHz spacing";
  //            }
  //            enum "1560.15" {
  //              description "1560.15 nm/192.15625 THz 6.25GHz spacing";
  //            }
  //            enum "1560.10" {
  //              description "1560.10 nm/192.16250 THz 6.25/12.5GHz spacing";
  //            }
  //            enum "1560.05" {
  //              description "1560.05 nm/192.16875 THz 6.25GHz spacing";
  //            }
  //            enum "1560.00" {
  //              description "1560.00 nm/192.17500 THz 6.25/12.5GHz spacing";
  //            }
  //            enum "1559.95" {
  //              description "1559.95 nm/192.18125 THz 6.25GHz spacing";
  //            }
  //            enum "1559.90" {
  //              description "1559.90 nm/192.18750 THz 6.25/12.5GHz spacing";
  //            }
  //            enum "1559.84" {
  //              description "1559.84 nm/192.19375 THz 6.25GHz spacing";
  //            }
  //            enum "1559.79" {
  //              description "1559.79 nm/192.20000 THz 6.25/12.5/50/75/100GHz spacing";
  //            }
  //            enum "1559.74" {
  //              description "1559.74 nm/192.20625 THz 6.25GHz spacing";
  //            }
  //            enum "1559.69" {
  //              description "1559.69 nm/192.21250 THz 6.25/12.5GHz spacing";
  //            }
  //            enum "1559.64" {
  //              description "1559.64 nm/192.21875 THz 6.25GHz spacing";
  //            }
  //            enum "1559.59" {
  //              description "1559.59 nm/192.22500 THz 6.25/12.5GHz spacing";
  //            }
  //            enum "1559.54" {
  //              description "1559.54 nm/192.23125 THz 6.25GHz spacing";
  //            }
  //            enum "1559.49" {
  //              description "1559.49 nm/192.23750 THz 6.25/12.5GHz spacing";
  //            }
  //            enum "1559.44" {
  //              description "1559.44 nm/192.24375 THz 6.25GHz spacing";
  //            }
  //            enum "1559.39" {
  //              description "1559.39 nm/192.25000 THz 6.25/12.5/50GHz spacing";
  //            }
  //            enum "1559.34" {
  //              description "1559.34 nm/192.25625 THz 6.25GHz spacing";
  //            }
  //            enum "1559.29" {
  //              description "1559.29 nm/192.26250 THz 6.25/12.5GHz spacing";
  //            }
  //            enum "1559.24" {
  //              description "1559.24 nm/192.26875 THz 6.25GHz spacing";
  //            }
  //            enum "1559.19" {
  //              description "1559.19 nm/192.27500 THz 6.25/12.5/75GHz spacing";
  //            }
  //            enum "1559.14" {
  //              description "1559.14 nm/192.28125 THz 6.25GHz spacing";
  //            }
  //            enum "1559.08" {
  //              description "1559.08 nm/192.28750 THz 6.25/12.5GHz spacing";
  //            }
  //            enum "1559.03" {
  //              description "1559.03 nm/192.29375 THz 6.25GHz spacing";
  //            }
  //            enum "1558.98" {
  //              description "1558.98 nm/192.30000 THz 6.25/12.5/50/100GHz spacing";
  //            }
  //            enum "1558.93" {
  //              description "1558.93 nm/192.30625 THz 6.25GHz spacing";
  //            }
  //            enum "1558.88" {
  //              description "1558.88 nm/192.31250 THz 6.25/12.5GHz spacing";
  //            }
  //            enum "1558.83" {
  //              description "1558.83 nm/192.31875 THz 6.25GHz spacing";
  //            }
  //            enum "1558.78" {
  //              description "1558.78 nm/192.32500 THz 6.25/12.5GHz spacing";
  //            }
  //            enum "1558.73" {
  //              description "1558.73 nm/192.33125 THz 6.25GHz spacing";
  //            }
  //            enum "1558.68" {
  //              description "1558.68 nm/192.33750 THz 6.25/12.5GHz spacing";
  //            }
  //            enum "1558.63" {
  //              description "1558.63 nm/192.34375 THz 6.25GHz spacing";
  //            }
  //            enum "1558.58" {
  //              description "1558.58 nm/192.35000 THz 6.25/12.5/50/75GHz spacing";
  //            }
  //            enum "1558.53" {
  //              description "1558.53 nm/192.35625 THz 6.25GHz spacing";
  //            }
  //            enum "1558.48" {
  //              description "1558.48 nm/192.36250 THz 6.25/12.5GHz spacing";
  //            }
  //            enum "1558.43" {
  //              description "1558.43 nm/192.36875 THz 6.25GHz spacing";
  //            }
  //            enum "1558.38" {
  //              description "1558.38 nm/192.37500 THz 6.25/12.5GHz spacing";
  //            }
  //            enum "1558.32" {
  //              description "1558.32 nm/192.38125 THz 6.25GHz spacing";
  //            }
  //            enum "1558.27" {
  //              description "1558.27 nm/192.38750 THz 6.25/12.5GHz spacing";
  //            }
  //            enum "1558.22" {
  //              description "1558.22 nm/192.39375 THz 6.25GHz spacing";
  //            }
  //            enum "1558.17" {
  //              description "1558.17 nm/192.40000 THz 6.25/12.5/50/100GHz spacing";
  //            }
  //            enum "1558.12" {
  //              description "1558.12 nm/192.40625 THz 6.25GHz spacing";
  //            }
  //            enum "1558.07" {
  //              description "1558.07 nm/192.41250 THz 6.25/12.5GHz spacing";
  //            }
  //            enum "1558.02" {
  //              description "1558.02 nm/192.41875 THz 6.25GHz spacing";
  //            }
  //            enum "1557.97" {
  //              description "1557.97 nm/192.42500 THz 6.25/12.5/75GHz spacing";
  //            }
  //            enum "1557.92" {
  //              description "1557.92 nm/192.43125 THz 6.25GHz spacing";
  //            }
  //            enum "1557.87" {
  //              description "1557.87 nm/192.43750 THz 6.25/12.5GHz spacing";
  //            }
  //            enum "1557.82" {
  //              description "1557.82 nm/192.44375 THz 6.25GHz spacing";
  //            }
  //            enum "1557.77" {
  //              description "1557.77 nm/192.45000 THz 6.25/12.5/50GHz spacing";
  //            }
  //            enum "1557.72" {
  //              description "1557.72 nm/192.45625 THz 6.25GHz spacing";
  //            }
  //            enum "1557.67" {
  //              description "1557.67 nm/192.46250 THz 6.25/12.5GHz spacing";
  //            }
  //            enum "1557.62" {
  //              description "1557.62 nm/192.46875 THz 6.25GHz spacing";
  //            }
  //            enum "1557.57" {
  //              description "1557.57 nm/192.47500 THz 6.25/12.5GHz spacing";
  //            }
  //            enum "1557.52" {
  //              description "1557.52 nm/192.48125 THz 6.25GHz spacing";
  //            }
  //            enum "1557.46" {
  //              description "1557.46 nm/192.48750 THz 6.25/12.5GHz spacing";
  //            }
  //            enum "1557.41" {
  //              description "1557.41 nm/192.49375 THz 6.25GHz spacing";
  //            }
  //            enum "1557.36" {
  //              description "1557.36 nm/192.50000 THz 6.25/12.5/50/75/100GHz spacing";
  //            }
  //            enum "1557.31" {
  //              description "1557.31 nm/192.50625 THz 6.25GHz spacing";
  //            }
  //            enum "1557.26" {
  //              description "1557.26 nm/192.51250 THz 6.25/12.5GHz spacing";
  //            }
  //            enum "1557.21" {
  //              description "1557.21 nm/192.51875 THz 6.25GHz spacing";
  //            }
  //            enum "1557.16" {
  //              description "1557.16 nm/192.52500 THz 6.25/12.5GHz spacing";
  //            }
  //            enum "1557.11" {
  //              description "1557.11 nm/192.53125 THz 6.25GHz spacing";
  //            }
  //            enum "1557.06" {
  //              description "1557.06 nm/192.53750 THz 6.25/12.5GHz spacing";
  //            }
  //            enum "1557.01" {
  //              description "1557.01 nm/192.54375 THz 6.25GHz spacing";
  //            }
  //            enum "1556.96" {
  //              description "1556.96 nm/192.55000 THz 6.25/12.5/50GHz spacing";
  //            }
  //            enum "1556.91" {
  //              description "1556.91 nm/192.55625 THz 6.25GHz spacing";
  //            }
  //            enum "1556.86" {
  //              description "1556.86 nm/192.56250 THz 6.25/12.5GHz spacing";
  //            }
  //            enum "1556.81" {
  //              description "1556.81 nm/192.56875 THz 6.25GHz spacing";
  //            }
  //            enum "1556.76" {
  //              description "1556.76 nm/192.57500 THz 6.25/12.5/75GHz spacing";
  //            }
  //            enum "1556.71" {
  //              description "1556.71 nm/192.58125 THz 6.25GHz spacing";
  //            }
  //            enum "1556.66" {
  //              description "1556.66 nm/192.58750 THz 6.25/12.5GHz spacing";
  //            }
  //            enum "1556.61" {
  //              description "1556.61 nm/192.59375 THz 6.25GHz spacing";
  //            }
  //            enum "1556.55" {
  //              description "1556.55 nm/192.60000 THz 6.25/12.5/50/100GHz spacing";
  //            }
  //            enum "1556.50" {
  //              description "1556.50 nm/192.60625 THz 6.25GHz spacing";
  //            }
  //            enum "1556.45" {
  //              description "1556.45 nm/192.61250 THz 6.25/12.5GHz spacing";
  //            }
  //            enum "1556.40" {
  //              description "1556.40 nm/192.61875 THz 6.25GHz spacing";
  //            }
  //            enum "1556.35" {
  //              description "1556.35 nm/192.62500 THz 6.25/12.5GHz spacing";
  //            }
  //            enum "1556.30" {
  //              description "1556.30 nm/192.63125 THz 6.25GHz spacing";
  //            }
  //            enum "1556.25" {
  //              description "1556.25 nm/192.63750 THz 6.25/12.5GHz spacing";
  //            }
  //            enum "1556.20" {
  //              description "1556.20 nm/192.64375 THz 6.25GHz spacing";
  //            }
  //            enum "1556.15" {
  //              description "1556.15 nm/192.65000 THz 6.25/12.5/50/75GHz spacing";
  //            }
  //            enum "1556.10" {
  //              description "1556.10 nm/192.65625 THz 6.25GHz spacing";
  //            }
  //            enum "1556.05" {
  //              description "1556.05 nm/192.66250 THz 6.25/12.5GHz spacing";
  //            }
  //            enum "1556.00" {
  //              description "1556.00 nm/192.66875 THz 6.25GHz spacing";
  //            }
  //            enum "1555.95" {
  //              description "1555.95 nm/192.67500 THz 6.25/12.5GHz spacing";
  //            }
  //            enum "1555.90" {
  //              description "1555.90 nm/192.68125 THz 6.25GHz spacing";
  //            }
  //            enum "1555.85" {
  //              description "1555.85 nm/192.68750 THz 6.25/12.5GHz spacing";
  //            }
  //            enum "1555.80" {
  //              description "1555.80 nm/192.69375 THz 6.25GHz spacing";
  //            }
  //            enum "1555.75" {
  //              description "1555.75 nm/192.70000 THz 6.25/12.5/50/100GHz spacing";
  //            }
  //            enum "1555.70" {
  //              description "1555.70 nm/192.70625 THz 6.25GHz spacing";
  //            }
  //            enum "1555.65" {
  //              description "1555.65 nm/192.71250 THz 6.25/12.5GHz spacing";
  //            }
  //            enum "1555.60" {
  //              description "1555.60 nm/192.71875 THz 6.25GHz spacing";
  //            }
  //            enum "1555.55" {
  //              description "1555.55 nm/192.72500 THz 6.25/12.5/75GHz spacing";
  //            }
  //            enum "1555.49" {
  //              description "1555.49 nm/192.73125 THz 6.25GHz spacing";
  //            }
  //            enum "1555.44" {
  //              description "1555.44 nm/192.73750 THz 6.25/12.5GHz spacing";
  //            }
  //            enum "1555.39" {
  //              description "1555.39 nm/192.74375 THz 6.25GHz spacing";
  //            }
  //            enum "1555.34" {
  //              description "1555.34 nm/192.75000 THz 6.25/12.5/50GHz spacing";
  //            }
  //            enum "1555.29" {
  //              description "1555.29 nm/192.75625 THz 6.25GHz spacing";
  //            }
  //            enum "1555.24" {
  //              description "1555.24 nm/192.76250 THz 6.25/12.5GHz spacing";
  //            }
  //            enum "1555.19" {
  //              description "1555.19 nm/192.76875 THz 6.25GHz spacing";
  //            }
  //            enum "1555.14" {
  //              description "1555.14 nm/192.77500 THz 6.25/12.5GHz spacing";
  //            }
  //            enum "1555.09" {
  //              description "1555.09 nm/192.78125 THz 6.25GHz spacing";
  //            }
  //            enum "1555.04" {
  //              description "1555.04 nm/192.78750 THz 6.25/12.5GHz spacing";
  //            }
  //            enum "1554.99" {
  //              description "1554.99 nm/192.79375 THz 6.25GHz spacing";
  //            }
  //            enum "1554.94" {
  //              description "1554.94 nm/192.80000 THz 6.25/12.5/50/75/100GHz spacing";
  //            }
  //            enum "1554.89" {
  //              description "1554.89 nm/192.80625 THz 6.25GHz spacing";
  //            }
  //            enum "1554.84" {
  //              description "1554.84 nm/192.81250 THz 6.25/12.5GHz spacing";
  //            }
  //            enum "1554.79" {
  //              description "1554.79 nm/192.81875 THz 6.25GHz spacing";
  //            }
  //            enum "1554.74" {
  //              description "1554.74 nm/192.82500 THz 6.25/12.5GHz spacing";
  //            }
  //            enum "1554.69" {
  //              description "1554.69 nm/192.83125 THz 6.25GHz spacing";
  //            }
  //            enum "1554.64" {
  //              description "1554.64 nm/192.83750 THz 6.25/12.5GHz spacing";
  //            }
  //            enum "1554.59" {
  //              description "1554.59 nm/192.84375 THz 6.25GHz spacing";
  //            }
  //            enum "1554.54" {
  //              description "1554.54 nm/192.85000 THz 6.25/12.5/50GHz spacing";
  //            }
  //            enum "1554.49" {
  //              description "1554.49 nm/192.85625 THz 6.25GHz spacing";
  //            }
  //            enum "1554.44" {
  //              description "1554.44 nm/192.86250 THz 6.25/12.5GHz spacing";
  //            }
  //            enum "1554.39" {
  //              description "1554.39 nm/192.86875 THz 6.25GHz spacing";
  //            }
  //            enum "1554.34" {
  //              description "1554.34 nm/192.87500 THz 6.25/12.5/75GHz spacing";
  //            }
  //            enum "1554.29" {
  //              description "1554.29 nm/192.88125 THz 6.25GHz spacing";
  //            }
  //            enum "1554.23" {
  //              description "1554.23 nm/192.88750 THz 6.25/12.5GHz spacing";
  //            }
  //            enum "1554.18" {
  //              description "1554.18 nm/192.89375 THz 6.25GHz spacing";
  //            }
  //            enum "1554.13" {
  //              description "1554.13 nm/192.90000 THz 6.25/12.5/50/100GHz spacing";
  //            }
  //            enum "1554.08" {
  //              description "1554.08 nm/192.90625 THz 6.25GHz spacing";
  //            }
  //            enum "1554.03" {
  //              description "1554.03 nm/192.91250 THz 6.25/12.5GHz spacing";
  //            }
  //            enum "1553.98" {
  //              description "1553.98 nm/192.91875 THz 6.25GHz spacing";
  //            }
  //            enum "1553.93" {
  //              description "1553.93 nm/192.92500 THz 6.25/12.5GHz spacing";
  //            }
  //            enum "1553.88" {
  //              description "1553.88 nm/192.93125 THz 6.25GHz spacing";
  //            }
  //            enum "1553.83" {
  //              description "1553.83 nm/192.93750 THz 6.25/12.5GHz spacing";
  //            }
  //            enum "1553.78" {
  //              description "1553.78 nm/192.94375 THz 6.25GHz spacing";
  //            }
  //            enum "1553.73" {
  //              description "1553.73 nm/192.95000 THz 6.25/12.5/50/75GHz spacing";
  //            }
  //            enum "1553.68" {
  //              description "1553.68 nm/192.95625 THz 6.25GHz spacing";
  //            }
  //            enum "1553.63" {
  //              description "1553.63 nm/192.96250 THz 6.25/12.5GHz spacing";
  //            }
  //            enum "1553.58" {
  //              description "1553.58 nm/192.96875 THz 6.25GHz spacing";
  //            }
  //            enum "1553.53" {
  //              description "1553.53 nm/192.97500 THz 6.25/12.5GHz spacing";
  //            }
  //            enum "1553.48" {
  //              description "1553.48 nm/192.98125 THz 6.25GHz spacing";
  //            }
  //            enum "1553.43" {
  //              description "1553.43 nm/192.98750 THz 6.25/12.5GHz spacing";
  //            }
  //            enum "1553.38" {
  //              description "1553.38 nm/192.99375 THz 6.25GHz spacing";
  //            }
  //            enum "1553.33" {
  //              description "1553.33 nm/193.00000 THz 6.25/12.5/50/100GHz spacing";
  //            }
  //            enum "1553.28" {
  //              description "1553.28 nm/193.00625 THz 6.25GHz spacing";
  //            }
  //            enum "1553.23" {
  //              description "1553.23 nm/193.01250 THz 6.25/12.5GHz spacing";
  //            }
  //            enum "1553.18" {
  //              description "1553.18 nm/193.01875 THz 6.25GHz spacing";
  //            }
  //            enum "1553.13" {
  //              description "1553.13 nm/193.02500 THz 6.25/12.5/75GHz spacing";
  //            }
  //            enum "1553.08" {
  //              description "1553.08 nm/193.03125 THz 6.25GHz spacing";
  //            }
  //            enum "1553.03" {
  //              description "1553.03 nm/193.03750 THz 6.25/12.5GHz spacing";
  //            }
  //            enum "1552.98" {
  //              description "1552.98 nm/193.04375 THz 6.25GHz spacing";
  //            }
  //            enum "1552.93" {
  //              description "1552.93 nm/193.05000 THz 6.25/12.5/50GHz spacing";
  //            }
  //            enum "1552.88" {
  //              description "1552.88 nm/193.05625 THz 6.25GHz spacing";
  //            }
  //            enum "1552.83" {
  //              description "1552.83 nm/193.06250 THz 6.25/12.5GHz spacing";
  //            }
  //            enum "1552.78" {
  //              description "1552.78 nm/193.06875 THz 6.25GHz spacing";
  //            }
  //            enum "1552.73" {
  //              description "1552.73 nm/193.07500 THz 6.25/12.5GHz spacing";
  //            }
  //            enum "1552.68" {
  //              description "1552.68 nm/193.08125 THz 6.25GHz spacing";
  //            }
  //            enum "1552.62" {
  //              description "1552.62 nm/193.08750 THz 6.25/12.5GHz spacing";
  //            }
  //            enum "1552.57" {
  //              description "1552.57 nm/193.09375 THz 6.25GHz spacing";
  //            }
  //            enum "1552.52" {
  //              description "1552.52 nm/193.10000 THz 6.25/12.5/50/75/100GHz spacing";
  //            }
  //            enum "1552.47" {
  //              description "1552.47 nm/193.10625 THz 6.25GHz spacing";
  //            }
  //            enum "1552.42" {
  //              description "1552.42 nm/193.11250 THz 6.25/12.5GHz spacing";
  //            }
  //            enum "1552.37" {
  //              description "1552.37 nm/193.11875 THz 6.25GHz spacing";
  //            }
  //            enum "1552.32" {
  //              description "1552.32 nm/193.12500 THz 6.25/12.5GHz spacing";
  //            }
  //            enum "1552.27" {
  //              description "1552.27 nm/193.13125 THz 6.25GHz spacing";
  //            }
  //            enum "1552.22" {
  //              description "1552.22 nm/193.13750 THz 6.25/12.5GHz spacing";
  //            }
  //            enum "1552.17" {
  //              description "1552.17 nm/193.14375 THz 6.25GHz spacing";
  //            }
  //            enum "1552.12" {
  //              description "1552.12 nm/193.15000 THz 6.25/12.5/50GHz spacing";
  //            }
  //            enum "1552.07" {
  //              description "1552.07 nm/193.15625 THz 6.25GHz spacing";
  //            }
  //            enum "1552.02" {
  //              description "1552.02 nm/193.16250 THz 6.25/12.5GHz spacing";
  //            }
  //            enum "1551.97" {
  //              description "1551.97 nm/193.16875 THz 6.25GHz spacing";
  //            }
  //            enum "1551.92" {
  //              description "1551.92 nm/193.17500 THz 6.25/12.5/75GHz spacing";
  //            }
  //            enum "1551.87" {
  //              description "1551.87 nm/193.18125 THz 6.25GHz spacing";
  //            }
  //            enum "1551.82" {
  //              description "1551.82 nm/193.18750 THz 6.25/12.5GHz spacing";
  //            }
  //            enum "1551.77" {
  //              description "1551.77 nm/193.19375 THz 6.25GHz spacing";
  //            }
  //            enum "1551.72" {
  //              description "1551.72 nm/193.20000 THz 6.25/12.5/50/100GHz spacing";
  //            }
  //            enum "1551.67" {
  //              description "1551.67 nm/193.20625 THz 6.25GHz spacing";
  //            }
  //            enum "1551.62" {
  //              description "1551.62 nm/193.21250 THz 6.25/12.5GHz spacing";
  //            }
  //            enum "1551.57" {
  //              description "1551.57 nm/193.21875 THz 6.25GHz spacing";
  //            }
  //            enum "1551.52" {
  //              description "1551.52 nm/193.22500 THz 6.25/12.5GHz spacing";
  //            }
  //            enum "1551.47" {
  //              description "1551.47 nm/193.23125 THz 6.25GHz spacing";
  //            }
  //            enum "1551.42" {
  //              description "1551.42 nm/193.23750 THz 6.25/12.5GHz spacing";
  //            }
  //            enum "1551.37" {
  //              description "1551.37 nm/193.24375 THz 6.25GHz spacing";
  //            }
  //            enum "1551.32" {
  //              description "1551.32 nm/193.25000 THz 6.25/12.5/50/75GHz spacing";
  //            }
  //            enum "1551.27" {
  //              description "1551.27 nm/193.25625 THz 6.25GHz spacing";
  //            }
  //            enum "1551.22" {
  //              description "1551.22 nm/193.26250 THz 6.25/12.5GHz spacing";
  //            }
  //            enum "1551.17" {
  //              description "1551.17 nm/193.26875 THz 6.25GHz spacing";
  //            }
  //            enum "1551.12" {
  //              description "1551.12 nm/193.27500 THz 6.25/12.5GHz spacing";
  //            }
  //            enum "1551.07" {
  //              description "1551.07 nm/193.28125 THz 6.25GHz spacing";
  //            }
  //            enum "1551.02" {
  //              description "1551.02 nm/193.28750 THz 6.25/12.5GHz spacing";
  //            }
  //            enum "1550.97" {
  //              description "1550.97 nm/193.29375 THz 6.25GHz spacing";
  //            }
  //            enum "1550.92" {
  //              description "1550.92 nm/193.30000 THz 6.25/12.5/50/100GHz spacing";
  //            }
  //            enum "1550.87" {
  //              description "1550.87 nm/193.30625 THz 6.25GHz spacing";
  //            }
  //            enum "1550.82" {
  //              description "1550.82 nm/193.31250 THz 6.25/12.5GHz spacing";
  //            }
  //            enum "1550.77" {
  //              description "1550.77 nm/193.31875 THz 6.25GHz spacing";
  //            }
  //            enum "1550.72" {
  //              description "1550.72 nm/193.32500 THz 6.25/12.5/75GHz spacing";
  //            }
  //            enum "1550.67" {
  //              description "1550.67 nm/193.33125 THz 6.25GHz spacing";
  //            }
  //            enum "1550.62" {
  //              description "1550.62 nm/193.33750 THz 6.25/12.5GHz spacing";
  //            }
  //            enum "1550.57" {
  //              description "1550.57 nm/193.34375 THz 6.25GHz spacing";
  //            }
  //            enum "1550.52" {
  //              description "1550.52 nm/193.35000 THz 6.25/12.5/50GHz spacing";
  //            }
  //            enum "1550.47" {
  //              description "1550.47 nm/193.35625 THz 6.25GHz spacing";
  //            }
  //            enum "1550.42" {
  //              description "1550.42 nm/193.36250 THz 6.25/12.5GHz spacing";
  //            }
  //            enum "1550.37" {
  //              description "1550.37 nm/193.36875 THz 6.25GHz spacing";
  //            }
  //            enum "1550.32" {
  //              description "1550.32 nm/193.37500 THz 6.25/12.5GHz spacing";
  //            }
  //            enum "1550.27" {
  //              description "1550.27 nm/193.38125 THz 6.25GHz spacing";
  //            }
  //            enum "1550.22" {
  //              description "1550.22 nm/193.38750 THz 6.25/12.5GHz spacing";
  //            }
  //            enum "1550.17" {
  //              description "1550.17 nm/193.39375 THz 6.25GHz spacing";
  //            }
  //            enum "1550.12" {
  //              description "1550.12 nm/193.40000 THz 6.25/12.5/50/75/100GHz spacing";
  //            }
  //            enum "1550.07" {
  //              description "1550.07 nm/193.40625 THz 6.25GHz spacing";
  //            }
  //            enum "1550.02" {
  //              description "1550.02 nm/193.41250 THz 6.25/12.5GHz spacing";
  //            }
  //            enum "1549.97" {
  //              description "1549.97 nm/193.41875 THz 6.25GHz spacing";
  //            }
  //            enum "1549.92" {
  //              description "1549.92 nm/193.42500 THz 6.25/12.5GHz spacing";
  //            }
  //            enum "1549.87" {
  //              description "1549.87 nm/193.43125 THz 6.25GHz spacing";
  //            }
  //            enum "1549.82" {
  //              description "1549.82 nm/193.43750 THz 6.25/12.5GHz spacing";
  //            }
  //            enum "1549.77" {
  //              description "1549.77 nm/193.44375 THz 6.25GHz spacing";
  //            }
  //            enum "1549.72" {
  //              description "1549.72 nm/193.45000 THz 6.25/12.5/50GHz spacing";
  //            }
  //            enum "1549.67" {
  //              description "1549.67 nm/193.45625 THz 6.25GHz spacing";
  //            }
  //            enum "1549.62" {
  //              description "1549.62 nm/193.46250 THz 6.25/12.5GHz spacing";
  //            }
  //            enum "1549.57" {
  //              description "1549.57 nm/193.46875 THz 6.25GHz spacing";
  //            }
  //            enum "1549.52" {
  //              description "1549.52 nm/193.47500 THz 6.25/12.5/75GHz spacing";
  //            }
  //            enum "1549.47" {
  //              description "1549.47 nm/193.48125 THz 6.25GHz spacing";
  //            }
  //            enum "1549.42" {
  //              description "1549.42 nm/193.48750 THz 6.25/12.5GHz spacing";
  //            }
  //            enum "1549.37" {
  //              description "1549.37 nm/193.49375 THz 6.25GHz spacing";
  //            }
  //            enum "1549.32" {
  //              description "1549.32 nm/193.50000 THz 6.25/12.5/50/100GHz spacing";
  //            }
  //            enum "1549.26" {
  //              description "1549.26 nm/193.50625 THz 6.25GHz spacing";
  //            }
  //            enum "1549.21" {
  //              description "1549.21 nm/193.51250 THz 6.25/12.5GHz spacing";
  //            }
  //            enum "1549.16" {
  //              description "1549.16 nm/193.51875 THz 6.25GHz spacing";
  //            }
  //            enum "1549.11" {
  //              description "1549.11 nm/193.52500 THz 6.25/12.5GHz spacing";
  //            }
  //            enum "1549.06" {
  //              description "1549.06 nm/193.53125 THz 6.25GHz spacing";
  //            }
  //            enum "1549.01" {
  //              description "1549.01 nm/193.53750 THz 6.25/12.5GHz spacing";
  //            }
  //            enum "1548.96" {
  //              description "1548.96 nm/193.54375 THz 6.25GHz spacing";
  //            }
  //            enum "1548.91" {
  //              description "1548.91 nm/193.55000 THz 6.25/12.5/50G/75Hz spacing";
  //            }
  //            enum "1548.86" {
  //              description "1548.86 nm/193.55625 THz 6.25GHz spacing";
  //            }
  //            enum "1548.81" {
  //              description "1548.81 nm/193.56250 THz 6.25/12.5GHz spacing";
  //            }
  //            enum "1548.76" {
  //              description "1548.76 nm/193.56875 THz 6.25GHz spacing";
  //            }
  //            enum "1548.71" {
  //              description "1548.71 nm/193.57500 THz 6.25/12.5GHz spacing";
  //            }
  //            enum "1548.66" {
  //              description "1548.66 nm/193.58125 THz 6.25GHz spacing";
  //            }
  //            enum "1548.61" {
  //              description "1548.61 nm/193.58750 THz 6.25/12.5GHz spacing";
  //            }
  //            enum "1548.56" {
  //              description "1548.56 nm/193.59375 THz 6.25GHz spacing";
  //            }
  //            enum "1548.51" {
  //              description "1548.51 nm/193.60000 THz 6.25/12.5/50/100GHz spacing";
  //            }
  //            enum "1548.46" {
  //              description "1548.46 nm/193.60625 THz 6.25GHz spacing";
  //            }
  //            enum "1548.41" {
  //              description "1548.41 nm/193.61250 THz 6.25/12.5GHz spacing";
  //            }
  //            enum "1548.36" {
  //              description "1548.36 nm/193.61875 THz 6.25GHz spacing";
  //            }
  //            enum "1548.31" {
  //              description "1548.31 nm/193.62500 THz 6.25/12.5/75GHz spacing";
  //            }
  //            enum "1548.26" {
  //              description "1548.26 nm/193.63125 THz 6.25GHz spacing";
  //            }
  //            enum "1548.21" {
  //              description "1548.21 nm/193.63750 THz 6.25/12.5GHz spacing";
  //            }
  //            enum "1548.16" {
  //              description "1548.16 nm/193.64375 THz 6.25GHz spacing";
  //            }
  //            enum "1548.11" {
  //              description "1548.11 nm/193.65000 THz 6.25/12.5/50GHz spacing";
  //            }
  //            enum "1548.06" {
  //              description "1548.06 nm/193.65625 THz 6.25GHz spacing";
  //            }
  //            enum "1548.02" {
  //              description "1548.02 nm/193.66250 THz 6.25/12.5GHz spacing";
  //            }
  //            enum "1547.97" {
  //              description "1547.97 nm/193.66875 THz 6.25GHz spacing";
  //            }
  //            enum "1547.92" {
  //              description "1547.92 nm/193.67500 THz 6.25/12.5GHz spacing";
  //            }
  //            enum "1547.87" {
  //              description "1547.87 nm/193.68125 THz 6.25GHz spacing";
  //            }
  //            enum "1547.82" {
  //              description "1547.82 nm/193.68750 THz 6.25/12.5GHz spacing";
  //            }
  //            enum "1547.77" {
  //              description "1547.77 nm/193.69375 THz 6.25GHz spacing";
  //            }
  //            enum "1547.72" {
  //              description "1547.72 nm/193.70000 THz 6.25/12.5/50/75/100GHz spacing";
  //            }
  //            enum "1547.67" {
  //              description "1547.67 nm/193.70625 THz 6.25GHz spacing";
  //            }
  //            enum "1547.62" {
  //              description "1547.62 nm/193.71250 THz 6.25/12.5GHz spacing";
  //            }
  //            enum "1547.57" {
  //              description "1547.57 nm/193.71875 THz 6.25GHz spacing";
  //            }
  //            enum "1547.52" {
  //              description "1547.52 nm/193.72500 THz 6.25/12.5GHz spacing";
  //            }
  //            enum "1547.47" {
  //              description "1547.47 nm/193.73125 THz 6.25GHz spacing";
  //            }
  //            enum "1547.42" {
  //              description "1547.42 nm/193.73750 THz 6.25/12.5GHz spacing";
  //            }
  //            enum "1547.37" {
  //              description "1547.37 nm/193.74375 THz 6.25GHz spacing";
  //            }
  //            enum "1547.32" {
  //              description "1547.32 nm/193.75000 THz 6.25/12.5/50GHz spacing";
  //            }
  //            enum "1547.27" {
  //              description "1547.27 nm/193.75625 THz 6.25GHz spacing";
  //            }
  //            enum "1547.22" {
  //              description "1547.22 nm/193.76250 THz 6.25/12.5GHz spacing";
  //            }
  //            enum "1547.17" {
  //              description "1547.17 nm/193.76875 THz 6.25GHz spacing";
  //            }
  //            enum "1547.12" {
  //              description "1547.12 nm/193.77500 THz 6.25/12.5/75GHz spacing";
  //            }
  //            enum "1547.07" {
  //              description "1547.07 nm/193.78125 THz 6.25GHz spacing";
  //            }
  //            enum "1547.02" {
  //              description "1547.02 nm/193.78750 THz 6.25/12.5GHz spacing";
  //            }
  //            enum "1546.97" {
  //              description "1546.97 nm/193.79375 THz 6.25GHz spacing";
  //            }
  //            enum "1546.92" {
  //              description "1546.92 nm/193.80000 THz 6.25/12.5/50/100GHz spacing";
  //            }
  //            enum "1546.87" {
  //              description "1546.87 nm/193.80625 THz 6.25GHz spacing";
  //            }
  //            enum "1546.82" {
  //              description "1546.82 nm/193.81250 THz 6.25/12.5GHz spacing";
  //            }
  //            enum "1546.77" {
  //              description "1546.77 nm/193.81875 THz 6.25GHz spacing";
  //            }
  //            enum "1546.72" {
  //              description "1546.72 nm/193.82500 THz 6.25/12.5GHz spacing";
  //            }
  //            enum "1546.67" {
  //              description "1546.67 nm/193.83125 THz 6.25GHz spacing";
  //            }
  //            enum "1546.62" {
  //              description "1546.62 nm/193.83750 THz 6.25/12.5GHz spacing";
  //            }
  //            enum "1546.57" {
  //              description "1546.57 nm/193.84375 THz 6.25GHz spacing";
  //            }
  //            enum "1546.52" {
  //              description "1546.52 nm/193.85000 THz 6.25/12.5/50/75GHz spacing";
  //            }
  //            enum "1546.47" {
  //              description "1546.47 nm/193.85625 THz 6.25GHz spacing";
  //            }
  //            enum "1546.42" {
  //              description "1546.42 nm/193.86250 THz 6.25/12.5GHz spacing";
  //            }
  //            enum "1546.37" {
  //              description "1546.37 nm/193.86875 THz 6.25GHz spacing";
  //            }
  //            enum "1546.32" {
  //              description "1546.32 nm/193.87500 THz 6.25/12.5GHz spacing";
  //            }
  //            enum "1546.27" {
  //              description "1546.27 nm/193.88125 THz 6.25GHz spacing";
  //            }
  //            enum "1546.22" {
  //              description "1546.22 nm/193.88750 THz 6.25/12.5GHz spacing";
  //            }
  //            enum "1546.17" {
  //              description "1546.17 nm/193.89375 THz 6.25GHz spacing";
  //            }
  //            enum "1546.12" {
  //              description "1546.12 nm/193.90000 THz 6.25/12.5/50/100GHz spacing";
  //            }
  //            enum "1546.07" {
  //              description "1546.07 nm/193.90625 THz 6.25GHz spacing";
  //            }
  //            enum "1546.02" {
  //              description "1546.02 nm/193.91250 THz 6.25/12.5GHz spacing";
  //            }
  //            enum "1545.97" {
  //              description "1545.97 nm/193.91875 THz 6.25GHz spacing";
  //            }
  //            enum "1545.92" {
  //              description "1545.92 nm/193.92500 THz 6.25/12.5/75GHz spacing";
  //            }
  //            enum "1545.87" {
  //              description "1545.87 nm/193.93125 THz 6.25GHz spacing";
  //            }
  //            enum "1545.82" {
  //              description "1545.82 nm/193.93750 THz 6.25/12.5GHz spacing";
  //            }
  //            enum "1545.77" {
  //              description "1545.77 nm/193.94375 THz 6.25GHz spacing";
  //            }
  //            enum "1545.72" {
  //              description "1545.72 nm/193.95000 THz 6.25/12.5/50GHz spacing";
  //            }
  //            enum "1545.67" {
  //              description "1545.67 nm/193.95625 THz 6.25GHz spacing";
  //            }
  //            enum "1545.62" {
  //              description "1545.62 nm/193.96250 THz 6.25/12.5GHz spacing";
  //            }
  //            enum "1545.57" {
  //              description "1545.57 nm/193.96875 THz 6.25GHz spacing";
  //            }
  //            enum "1545.52" {
  //              description "1545.52 nm/193.97500 THz 6.25/12.5GHz spacing";
  //            }
  //            enum "1545.47" {
  //              description "1545.47 nm/193.98125 THz 6.25GHz spacing";
  //            }
  //            enum "1545.42" {
  //              description "1545.42 nm/193.98750 THz 6.25/12.5GHz spacing";
  //            }
  //            enum "1545.37" {
  //              description "1545.37 nm/193.99375 THz 6.25GHz spacing";
  //            }
  //            enum "1545.32" {
  //              description "1545.32 nm/194.00000 THz 6.25/12.5/50/75/100GHz spacing";
  //            }
  //            enum "1545.27" {
  //              description "1545.27 nm/194.00625 THz 6.25GHz spacing";
  //            }
  //            enum "1545.22" {
  //              description "1545.22 nm/194.01250 THz 6.25/12.5GHz spacing";
  //            }
  //            enum "1545.17" {
  //              description "1545.17 nm/194.01875 THz 6.25GHz spacing";
  //            }
  //            enum "1545.12" {
  //              description "1545.12 nm/194.02500 THz 6.25/12.5GHz spacing";
  //            }
  //            enum "1545.07" {
  //              description "1545.07 nm/194.03125 THz 6.25GHz spacing";
  //            }
  //            enum "1545.02" {
  //              description "1545.02 nm/194.03750 THz 6.25/12.5GHz spacing";
  //            }
  //            enum "1544.97" {
  //              description "1544.97 nm/194.04375 THz 6.25GHz spacing";
  //            }
  //            enum "1544.92" {
  //              description "1544.92 nm/194.05000 THz 6.25/12.5/50GHz spacing";
  //            }
  //            enum "1544.87" {
  //              description "1544.87 nm/194.05625 THz 6.25GHz spacing";
  //            }
  //            enum "1544.82" {
  //              description "1544.82 nm/194.06250 THz 6.25/12.5GHz spacing";
  //            }
  //            enum "1544.77" {
  //              description "1544.77 nm/194.06875 THz 6.25GHz spacing";
  //            }
  //            enum "1544.72" {
  //              description "1544.72 nm/194.07500 THz 6.25/12.5/75GHz spacing";
  //            }
  //            enum "1544.68" {
  //              description "1544.68 nm/194.08125 THz 6.25GHz spacing";
  //            }
  //            enum "1544.63" {
  //              description "1544.63 nm/194.08750 THz 6.25/12.5GHz spacing";
  //            }
  //            enum "1544.58" {
  //              description "1544.58 nm/194.09375 THz 6.25GHz spacing";
  //            }
  //            enum "1544.53" {
  //              description "1544.53 nm/194.10000 THz 6.25/12.5/50/100GHz spacing";
  //            }
  //            enum "1544.48" {
  //              description "1544.48 nm/194.10625 THz 6.25GHz spacing";
  //            }
  //            enum "1544.43" {
  //              description "1544.43 nm/194.11250 THz 6.25/12.5GHz spacing";
  //            }
  //            enum "1544.38" {
  //              description "1544.38 nm/194.11875 THz 6.25GHz spacing";
  //            }
  //            enum "1544.33" {
  //              description "1544.33 nm/194.12500 THz 6.25/12.5GHz spacing";
  //            }
  //            enum "1544.28" {
  //              description "1544.28 nm/194.13125 THz 6.25GHz spacing";
  //            }
  //            enum "1544.23" {
  //              description "1544.23 nm/194.13750 THz 6.25/12.5GHz spacing";
  //            }
  //            enum "1544.18" {
  //              description "1544.18 nm/194.14375 THz 6.25GHz spacing";
  //            }
  //            enum "1544.13" {
  //              description "1544.13 nm/194.15000 THz 6.25/12.5/50/75GHz spacing";
  //            }
  //            enum "1544.08" {
  //              description "1544.08 nm/194.15625 THz 6.25GHz spacing";
  //            }
  //            enum "1544.03" {
  //              description "1544.03 nm/194.16250 THz 6.25/12.5GHz spacing";
  //            }
  //            enum "1543.98" {
  //              description "1543.98 nm/194.16875 THz 6.25GHz spacing";
  //            }
  //            enum "1543.93" {
  //              description "1543.93 nm/194.17500 THz 6.25/12.5GHz spacing";
  //            }
  //            enum "1543.88" {
  //              description "1543.88 nm/194.18125 THz 6.25GHz spacing";
  //            }
  //            enum "1543.83" {
  //              description "1543.83 nm/194.18750 THz 6.25/12.5GHz spacing";
  //            }
  //            enum "1543.78" {
  //              description "1543.78 nm/194.19375 THz 6.25GHz spacing";
  //            }
  //            enum "1543.73" {
  //              description "1543.73 nm/194.20000 THz 6.25/12.5/50/100GHz spacing";
  //            }
  //            enum "1543.68" {
  //              description "1543.68 nm/194.20625 THz 6.25GHz spacing";
  //            }
  //            enum "1543.63" {
  //              description "1543.63 nm/194.21250 THz 6.25/12.5GHz spacing";
  //            }
  //            enum "1543.58" {
  //              description "1543.58 nm/194.21875 THz 6.25GHz spacing";
  //            }
  //            enum "1543.53" {
  //              description "1543.53 nm/194.22500 THz 6.25/12.5/75GHz spacing";
  //            }
  //            enum "1543.48" {
  //              description "1543.48 nm/194.23125 THz 6.25GHz spacing";
  //            }
  //            enum "1543.43" {
  //              description "1543.43 nm/194.23750 THz 6.25/12.5GHz spacing";
  //            }
  //            enum "1543.38" {
  //              description "1543.38 nm/194.24375 THz 6.25GHz spacing";
  //            }
  //            enum "1543.33" {
  //              description "1543.33 nm/194.25000 THz 6.25/12.5/50GHz spacing";
  //            }
  //            enum "1543.28" {
  //              description "1543.28 nm/194.25625 THz 6.25GHz spacing";
  //            }
  //            enum "1543.23" {
  //              description "1543.23 nm/194.26250 THz 6.25/12.5GHz spacing";
  //            }
  //            enum "1543.18" {
  //              description "1543.18 nm/194.26875 THz 6.25GHz spacing";
  //            }
  //            enum "1543.13" {
  //              description "1543.13 nm/194.27500 THz 6.25/12.5GHz spacing";
  //            }
  //            enum "1543.08" {
  //              description "1543.08 nm/194.28125 THz 6.25GHz spacing";
  //            }
  //            enum "1543.04" {
  //              description "1543.04 nm/194.28750 THz 6.25/12.5GHz spacing";
  //            }
  //            enum "1542.99" {
  //              description "1542.99 nm/194.29375 THz 6.25GHz spacing";
  //            }
  //            enum "1542.94" {
  //              description "1542.94 nm/194.30000 THz 6.25/12.5/50/75/100GHz spacing";
  //            }
  //            enum "1542.89" {
  //              description "1542.89 nm/194.30625 THz 6.25GHz spacing";
  //            }
  //            enum "1542.84" {
  //              description "1542.84 nm/194.31250 THz 6.25/12.5GHz spacing";
  //            }
  //            enum "1542.79" {
  //              description "1542.79 nm/194.31875 THz 6.25GHz spacing";
  //            }
  //            enum "1542.74" {
  //              description "1542.74 nm/194.32500 THz 6.25/12.5GHz spacing";
  //            }
  //            enum "1542.69" {
  //              description "1542.69 nm/194.33125 THz 6.25GHz spacing";
  //            }
  //            enum "1542.64" {
  //              description "1542.64 nm/194.33750 THz 6.25/12.5GHz spacing";
  //            }
  //            enum "1542.59" {
  //              description "1542.59 nm/194.34375 THz 6.25GHz spacing";
  //            }
  //            enum "1542.54" {
  //              description "1542.54 nm/194.35000 THz 6.25/12.5/50GHz spacing";
  //            }
  //            enum "1542.49" {
  //              description "1542.49 nm/194.35625 THz 6.25GHz spacing";
  //            }
  //            enum "1542.44" {
  //              description "1542.44 nm/194.36250 THz 6.25/12.5GHz spacing";
  //            }
  //            enum "1542.39" {
  //              description "1542.39 nm/194.36875 THz 6.25GHz spacing";
  //            }
  //            enum "1542.34" {
  //              description "1542.34 nm/194.37500 THz 6.25/12.5/75GHz spacing";
  //            }
  //            enum "1542.29" {
  //              description "1542.29 nm/194.38125 THz 6.25GHz spacing";
  //            }
  //            enum "1542.24" {
  //              description "1542.24 nm/194.38750 THz 6.25/12.5GHz spacing";
  //            }
  //            enum "1542.19" {
  //              description "1542.19 nm/194.39375 THz 6.25GHz spacing";
  //            }
  //            enum "1542.14" {
  //              description "1542.14 nm/194.40000 THz 6.25/12.5/50/100GHz spacing";
  //            }
  //            enum "1542.09" {
  //              description "1542.09 nm/194.40625 THz 6.25GHz spacing";
  //            }
  //            enum "1542.04" {
  //              description "1542.04 nm/194.41250 THz 6.25/12.5GHz spacing";
  //            }
  //            enum "1541.99" {
  //              description "1541.99 nm/194.41875 THz 6.25GHz spacing";
  //            }
  //            enum "1541.94" {
  //              description "1541.94 nm/194.42500 THz 6.25/12.5GHz spacing";
  //            }
  //            enum "1541.89" {
  //              description "1541.89 nm/194.43125 THz 6.25GHz spacing";
  //            }
  //            enum "1541.84" {
  //              description "1541.84 nm/194.43750 THz 6.25/12.5GHz spacing";
  //            }
  //            enum "1541.80" {
  //              description "1541.80 nm/194.44375 THz 6.25GHz spacing";
  //            }
  //            enum "1541.75" {
  //              description "1541.75 nm/194.45000 THz 6.25/12.5/50/75GHz spacing";
  //            }
  //            enum "1541.70" {
  //              description "1541.70 nm/194.45625 THz 6.25GHz spacing";
  //            }
  //            enum "1541.65" {
  //              description "1541.65 nm/194.46250 THz 6.25/12.5GHz spacing";
  //            }
  //            enum "1541.60" {
  //              description "1541.60 nm/194.46875 THz 6.25GHz spacing";
  //            }
  //            enum "1541.55" {
  //              description "1541.55 nm/194.47500 THz 6.25/12.5GHz spacing";
  //            }
  //            enum "1541.50" {
  //              description "1541.50 nm/194.48125 THz 6.25GHz spacing";
  //            }
  //            enum "1541.45" {
  //              description "1541.45 nm/194.48750 THz 6.25/12.5GHz spacing";
  //            }
  //            enum "1541.40" {
  //              description "1541.40 nm/194.49375 THz 6.25GHz spacing";
  //            }
  //            enum "1541.35" {
  //              description "1541.35 nm/194.50000 THz 6.25/12.5/50/100GHz spacing";
  //            }
  //            enum "1541.30" {
  //              description "1541.30 nm/194.50625 THz 6.25GHz spacing";
  //            }
  //            enum "1541.25" {
  //              description "1541.25 nm/194.51250 THz 6.25/12.5GHz spacing";
  //            }
  //            enum "1541.20" {
  //              description "1541.20 nm/194.51875 THz 6.25GHz spacing";
  //            }
  //            enum "1541.15" {
  //              description "1541.15 nm/194.52500 THz 6.25/12.5/75GHz spacing";
  //            }
  //            enum "1541.10" {
  //              description "1541.10 nm/194.53125 THz 6.25GHz spacing";
  //            }
  //            enum "1541.05" {
  //              description "1541.05 nm/194.53750 THz 6.25/12.5GHz spacing";
  //            }
  //            enum "1541.00" {
  //              description "1541.00 nm/194.54375 THz 6.25GHz spacing";
  //            }
  //            enum "1540.95" {
  //              description "1540.95 nm/194.55000 THz 6.25/12.5/50GHz spacing";
  //            }
  //            enum "1540.90" {
  //              description "1540.90 nm/194.55625 THz 6.25GHz spacing";
  //            }
  //            enum "1540.85" {
  //              description "1540.85 nm/194.56250 THz 6.25/12.5GHz spacing";
  //            }
  //            enum "1540.80" {
  //              description "1540.80 nm/194.56875 THz 6.25GHz spacing";
  //            }
  //            enum "1540.76" {
  //              description "1540.76 nm/194.57500 THz 6.25/12.5GHz spacing";
  //            }
  //            enum "1540.71" {
  //              description "1540.71 nm/194.58125 THz 6.25GHz spacing";
  //            }
  //            enum "1540.66" {
  //              description "1540.66 nm/194.58750 THz 6.25/12.5GHz spacing";
  //            }
  //            enum "1540.61" {
  //              description "1540.61 nm/194.59375 THz 6.25GHz spacing";
  //            }
  //            enum "1540.56" {
  //              description "1540.56 nm/194.60000 THz 6.25/12.5/50/75/100GHz spacing";
  //            }
  //            enum "1540.51" {
  //              description "1540.51 nm/194.60625 THz 6.25GHz spacing";
  //            }
  //            enum "1540.46" {
  //              description "1540.46 nm/194.61250 THz 6.25/12.5GHz spacing";
  //            }
  //            enum "1540.41" {
  //              description "1540.41 nm/194.61875 THz 6.25GHz spacing";
  //            }
  //            enum "1540.36" {
  //              description "1540.36 nm/194.62500 THz 6.25/12.5GHz spacing";
  //            }
  //            enum "1540.31" {
  //              description "1540.31 nm/194.63125 THz 6.25GHz spacing";
  //            }
  //            enum "1540.26" {
  //              description "1540.26 nm/194.63750 THz 6.25/12.5GHz spacing";
  //            }
  //            enum "1540.21" {
  //              description "1540.21 nm/194.64375 THz 6.25GHz spacing";
  //            }
  //            enum "1540.16" {
  //              description "1540.16 nm/194.65000 THz 6.25/12.5/50GHz spacing";
  //            }
  //            enum "1540.11" {
  //              description "1540.11 nm/194.65625 THz 6.25GHz spacing";
  //            }
  //            enum "1540.06" {
  //              description "1540.06 nm/194.66250 THz 6.25/12.5GHz spacing";
  //            }
  //            enum "1540.01" {
  //              description "1540.01 nm/194.66875 THz 6.25GHz spacing";
  //            }
  //            enum "1539.96" {
  //              description "1539.96 nm/194.67500 THz 6.25/12.5/50/75GHz spacing";
  //            }
  //            enum "1539.91" {
  //              description "1539.91 nm/194.68125 THz 6.25GHz spacing";
  //            }
  //            enum "1539.86" {
  //              description "1539.86 nm/194.68750 THz 6.25/12.5GHz spacing";
  //            }
  //            enum "1539.82" {
  //              description "1539.82 nm/194.69375 THz 6.25GHz spacing";
  //            }
  //            enum "1539.77" {
  //              description "1539.77 nm/194.70000 THz 6.25/12.5/50/100GHz spacing";
  //            }
  //            enum "1539.72" {
  //              description "1539.72 nm/194.70625 THz 6.25GHz spacing";
  //            }
  //            enum "1539.67" {
  //              description "1539.67 nm/194.71250 THz 6.25/12.5GHz spacing";
  //            }
  //            enum "1539.62" {
  //              description "1539.62 nm/194.71875 THz 6.25GHz spacing";
  //            }
  //            enum "1539.57" {
  //              description "1539.57 nm/194.72500 THz 6.25/12.5GHz spacing";
  //            }
  //            enum "1539.52" {
  //              description "1539.52 nm/194.73125 THz 6.25GHz spacing";
  //            }
  //            enum "1539.47" {
  //              description "1539.47 nm/194.73750 THz 6.25/12.5GHz spacing";
  //            }
  //            enum "1539.42" {
  //              description "1539.42 nm/194.74375 THz 6.25GHz spacing";
  //            }
  //            enum "1539.37" {
  //              description "1539.37 nm/194.75000 THz 6.25/12.5/50/75GHz spacing";
  //            }
  //            enum "1539.32" {
  //              description "1539.32 nm/194.75625 THz 6.25GHz spacing";
  //            }
  //            enum "1539.27" {
  //              description "1539.27 nm/194.76250 THz 6.25/12.5GHz spacing";
  //            }
  //            enum "1539.22" {
  //              description "1539.22 nm/194.76875 THz 6.25GHz spacing";
  //            }
  //            enum "1539.17" {
  //              description "1539.17 nm/194.77500 THz 6.25/12.5GHz spacing";
  //            }
  //            enum "1539.12" {
  //              description "1539.12 nm/194.78125 THz 6.25GHz spacing";
  //            }
  //            enum "1539.07" {
  //              description "1539.07 nm/194.78750 THz 6.25/12.5GHz spacing";
  //            }
  //            enum "1539.03" {
  //              description "1539.03 nm/194.79375 THz 6.25GHz spacing";
  //            }
  //            enum "1538.98" {
  //              description "1538.98 nm/194.80000 THz 6.25/12.5/50/100GHz spacing";
  //            }
  //            enum "1538.93" {
  //              description "1538.93 nm/194.80625 THz 6.25GHz spacing";
  //            }
  //            enum "1538.88" {
  //              description "1538.88 nm/194.81250 THz 6.25/12.5GHz spacing";
  //            }
  //            enum "1538.83" {
  //              description "1538.83 nm/194.81875 THz 6.25GHz spacing";
  //            }
  //            enum "1538.78" {
  //              description "1538.78 nm/194.82500 THz 6.25/12.5/75GHz spacing";
  //            }
  //            enum "1538.73" {
  //              description "1538.73 nm/194.83125 THz 6.25GHz spacing";
  //            }
  //            enum "1538.68" {
  //              description "1538.68 nm/194.83750 THz 6.25/12.5GHz spacing";
  //            }
  //            enum "1538.63" {
  //              description "1538.63 nm/194.84375 THz 6.25GHz spacing";
  //            }
  //            enum "1538.58" {
  //              description "1538.58 nm/194.85000 THz 6.25/12.5/50GHz spacing";
  //            }
  //            enum "1538.53" {
  //              description "1538.53 nm/194.85625 THz 6.25GHz spacing";
  //            }
  //            enum "1538.48" {
  //              description "1538.48 nm/194.86250 THz 6.25/12.5GHz spacing";
  //            }
  //            enum "1538.43" {
  //              description "1538.43 nm/194.86875 THz 6.25GHz spacing";
  //            }
  //            enum "1538.38" {
  //              description "1538.38 nm/194.87500 THz 6.25/12.5/75GHz spacing";
  //            }
  //            enum "1538.33" {
  //              description "1538.33 nm/194.88125 THz 6.25GHz spacing";
  //            }
  //            enum "1538.28" {
  //              description "1538.28 nm/194.88750 THz 6.25/12.5GHz spacing";
  //            }
  //            enum "1538.24" {
  //              description "1538.24 nm/194.89375 THz 6.25GHz spacing";
  //            }
  //            enum "1538.19" {
  //              description "1538.19 nm/194.90000 THz 6.25/12.5/50/75/100GHz spacing";
  //            }
  //            enum "1538.14" {
  //              description "1538.14 nm/194.90625 THz 6.25GHz spacing";
  //            }
  //            enum "1538.09" {
  //              description "1538.09 nm/194.91250 THz 6.25/12.5GHz spacing";
  //            }
  //            enum "1538.04" {
  //              description "1538.04 nm/194.91875 THz 6.25GHz spacing";
  //            }
  //            enum "1537.99" {
  //              description "1537.99 nm/194.92500 THz 6.25/12.5GHz spacing";
  //            }
  //            enum "1537.94" {
  //              description "1537.94 nm/194.93125 THz 6.25GHz spacing";
  //            }
  //            enum "1537.89" {
  //              description "1537.89 nm/194.93750 THz 6.25/12.5GHz spacing";
  //            }
  //            enum "1537.84" {
  //              description "1537.84 nm/194.94375 THz 6.25GHz spacing";
  //            }
  //            enum "1537.79" {
  //              description "1537.79 nm/194.95000 THz 6.25/12.5/50GHz spacing";
  //            }
  //            enum "1537.74" {
  //              description "1537.74 nm/194.95625 THz 6.25GHz spacing";
  //            }
  //            enum "1537.69" {
  //              description "1537.69 nm/194.96250 THz 6.25/12.5GHz spacing";
  //            }
  //            enum "1537.64" {
  //              description "1537.64 nm/194.96875 THz 6.25GHz spacing";
  //            }
  //            enum "1537.59" {
  //              description "1537.59 nm/194.97500 THz 6.25/12.5/75GHz spacing";
  //            }
  //            enum "1537.55" {
  //              description "1537.55 nm/194.98125 THz 6.25GHz spacing";
  //            }
  //            enum "1537.50" {
  //              description "1537.50 nm/194.98750 THz 6.25/12.5GHz spacing";
  //            }
  //            enum "1537.45" {
  //              description "1537.45 nm/194.99375 THz 6.25GHz spacing";
  //            }
  //            enum "1537.40" {
  //              description "1537.40 nm/195.00000 THz 6.25/12.5/50/100GHz spacing";
  //            }
  //            enum "1537.35" {
  //              description "1537.35 nm/195.00625 THz 6.25GHz spacing";
  //            }
  //            enum "1537.30" {
  //              description "1537.30 nm/195.01250 THz 6.25/12.5GHz spacing";
  //            }
  //            enum "1537.25" {
  //              description "1537.25 nm/195.01875 THz 6.25GHz spacing";
  //            }
  //            enum "1537.20" {
  //              description "1537.20 nm/195.02500 THz 6.25/12.5GHz spacing";
  //            }
  //            enum "1537.15" {
  //              description "1537.15 nm/195.03125 THz 6.25GHz spacing";
  //            }
  //            enum "1537.10" {
  //              description "1537.10 nm/195.03750 THz 6.25/12.5GHz spacing";
  //            }
  //            enum "1537.05" {
  //              description "1537.05 nm/195.04375 THz 6.25GHz spacing";
  //            }
  //            enum "1537.00" {
  //              description "1537.00 nm/195.05000 THz 6.25/12.5/50/75GHz spacing";
  //            }
  //            enum "1536.95" {
  //              description "1536.95 nm/195.05625 THz 6.25GHz spacing";
  //            }
  //            enum "1536.90" {
  //              description "1536.90 nm/195.06250 THz 6.25/12.5GHz spacing";
  //            }
  //            enum "1536.86" {
  //              description "1536.86 nm/195.06875 THz 6.25GHz spacing";
  //            }
  //            enum "1536.81" {
  //              description "1536.81 nm/195.07500 THz 6.25/12.5GHz spacing";
  //            }
  //            enum "1536.76" {
  //              description "1536.76 nm/195.08125 THz 6.25GHz spacing";
  //            }
  //            enum "1536.71" {
  //              description "1536.71 nm/195.08750 THz 6.25/12.5GHz spacing";
  //            }
  //            enum "1536.66" {
  //              description "1536.66 nm/195.09375 THz 6.25GHz spacing";
  //            }
  //            enum "1536.61" {
  //              description "1536.61 nm/195.10000 THz 6.25/12.5/50/100GHz spacing";
  //            }
  //            enum "1536.56" {
  //              description "1536.56 nm/195.10625 THz 6.25GHz spacing";
  //            }
  //            enum "1536.51" {
  //              description "1536.51 nm/195.11250 THz 6.25/12.5GHz spacing";
  //            }
  //            enum "1536.46" {
  //              description "1536.46 nm/195.11875 THz 6.25GHz spacing";
  //            }
  //            enum "1536.41" {
  //              description "1536.41 nm/195.12500 THz 6.25/12.5/75GHz spacing";
  //            }
  //            enum "1536.36" {
  //              description "1536.36 nm/195.13125 THz 6.25GHz spacing";
  //            }
  //            enum "1536.31" {
  //              description "1536.31 nm/195.13750 THz 6.25/12.5GHz spacing";
  //            }
  //            enum "1536.26" {
  //              description "1536.26 nm/195.14375 THz 6.25GHz spacing";
  //            }
  //            enum "1536.22" {
  //              description "1536.22 nm/195.15000 THz 6.25/12.5/50GHz spacing";
  //            }
  //            enum "1536.17" {
  //              description "1536.17 nm/195.15625 THz 6.25GHz spacing";
  //            }
  //            enum "1536.12" {
  //              description "1536.12 nm/195.16250 THz 6.25/12.5GHz spacing";
  //            }
  //            enum "1536.07" {
  //              description "1536.07 nm/195.16875 THz 6.25GHz spacing";
  //            }
  //            enum "1536.02" {
  //              description "1536.02 nm/195.17500 THz 6.25/12.5GHz spacing";
  //            }
  //            enum "1535.97" {
  //              description "1535.97 nm/195.18125 THz 6.25GHz spacing";
  //            }
  //            enum "1535.92" {
  //              description "1535.92 nm/195.18750 THz 6.25/12.5GHz spacing";
  //            }
  //            enum "1535.87" {
  //              description "1535.87 nm/195.19375 THz 6.25GHz spacing";
  //            }
  //            enum "1535.82" {
  //              description "1535.82 nm/195.20000 THz 6.25/12.5/50/75/100GHz spacing";
  //            }
  //            enum "1535.77" {
  //              description "1535.77 nm/195.20625 THz 6.25GHz spacing";
  //            }
  //            enum "1535.72" {
  //              description "1535.72 nm/195.21250 THz 6.25/12.5GHz spacing";
  //            }
  //            enum "1535.67" {
  //              description "1535.67 nm/195.21875 THz 6.25GHz spacing";
  //            }
  //            enum "1535.63" {
  //              description "1535.63 nm/195.22500 THz 6.25/12.5GHz spacing";
  //            }
  //            enum "1535.58" {
  //              description "1535.58 nm/195.23125 THz 6.25GHz spacing";
  //            }
  //            enum "1535.53" {
  //              description "1535.53 nm/195.23750 THz 6.25/12.5GHz spacing";
  //            }
  //            enum "1535.48" {
  //              description "1535.48 nm/195.24375 THz 6.25GHz spacing";
  //            }
  //            enum "1535.43" {
  //              description "1535.43 nm/195.25000 THz 6.25/12.5/50GHz spacing";
  //            }
  //            enum "1535.38" {
  //              description "1535.38 nm/195.25625 THz 6.25GHz spacing";
  //            }
  //            enum "1535.33" {
  //              description "1535.33 nm/195.26250 THz 6.25/12.5GHz spacing";
  //            }
  //            enum "1535.28" {
  //              description "1535.28 nm/195.26875 THz 6.25GHz spacing";
  //            }
  //            enum "1535.23" {
  //              description "1535.23 nm/195.27500 THz 6.25/12.5/75GHz spacing";
  //            }
  //            enum "1535.18" {
  //              description "1535.18 nm/195.28125 THz 6.25GHz spacing";
  //            }
  //            enum "1535.13" {
  //              description "1535.13 nm/195.28750 THz 6.25/12.5GHz spacing";
  //            }
  //            enum "1535.08" {
  //              description "1535.08 nm/195.29375 THz 6.25GHz spacing";
  //            }
  //            enum "1535.04" {
  //              description "1535.04 nm/195.30000 THz 6.25/12.5/50/100GHz spacing";
  //            }
  //            enum "1534.99" {
  //              description "1534.99 nm/195.30625 THz 6.25GHz spacing";
  //            }
  //            enum "1534.94" {
  //              description "1534.94 nm/195.31250 THz 6.25/12.5GHz spacing";
  //            }
  //            enum "1534.89" {
  //              description "1534.89 nm/195.31875 THz 6.25GHz spacing";
  //            }
  //            enum "1534.84" {
  //              description "1534.84 nm/195.32500 THz 6.25/12.5GHz spacing";
  //            }
  //            enum "1534.79" {
  //              description "1534.79 nm/195.33125 THz 6.25GHz spacing";
  //            }
  //            enum "1534.74" {
  //              description "1534.74 nm/195.33750 THz 6.25/12.5GHz spacing";
  //            }
  //            enum "1534.69" {
  //              description "1534.69 nm/195.34375 THz 6.25GHz spacing";
  //            }
  //            enum "1534.64" {
  //              description "1534.64 nm/195.35000 THz 6.25/12.5/50/75GHz spacing";
  //            }
  //            enum "1534.59" {
  //              description "1534.59 nm/195.35625 THz 6.25GHz spacing";
  //            }
  //            enum "1534.54" {
  //              description "1534.54 nm/195.36250 THz 6.25/12.5GHz spacing";
  //            }
  //            enum "1534.50" {
  //              description "1534.50 nm/195.36875 THz 6.25GHz spacing";
  //            }
  //            enum "1534.45" {
  //              description "1534.45 nm/195.37500 THz 6.25/12.5GHz spacing";
  //            }
  //            enum "1534.40" {
  //              description "1534.40 nm/195.38125 THz 6.25GHz spacing";
  //            }
  //            enum "1534.35" {
  //              description "1534.35 nm/195.38750 THz 6.25/12.5GHz spacing";
  //            }
  //            enum "1534.30" {
  //              description "1534.30 nm/195.39375 THz 6.25GHz spacing";
  //            }
  //            enum "1534.25" {
  //              description "1534.25 nm/195.40000 THz 6.25/12.5/50/100GHz spacing";
  //            }
  //            enum "1534.20" {
  //              description "1534.20 nm/195.40625 THz 6.25GHz spacing";
  //            }
  //            enum "1534.15" {
  //              description "1534.15 nm/195.41250 THz 6.25/12.5GHz spacing";
  //            }
  //            enum "1534.10" {
  //              description "1534.10 nm/195.41875 THz 6.25GHz spacing";
  //            }
  //            enum "1534.05" {
  //              description "1534.05 nm/195.42500 THz 6.25/12.5/75GHz spacing";
  //            }
  //            enum "1534.00" {
  //              description "1534.00 nm/195.43125 THz 6.25GHz spacing";
  //            }
  //            enum "1533.96" {
  //              description "1533.96 nm/195.43750 THz 6.25/12.5GHz spacing";
  //            }
  //            enum "1533.91" {
  //              description "1533.91 nm/195.44375 THz 6.25GHz spacing";
  //            }
  //            enum "1533.86" {
  //              description "1533.86 nm/195.45000 THz 6.25/12.5/50GHz spacing";
  //            }
  //            enum "1533.81" {
  //              description "1533.81 nm/195.45625 THz 6.25GHz spacing";
  //            }
  //            enum "1533.76" {
  //              description "1533.76 nm/195.46250 THz 6.25/12.5GHz spacing";
  //            }
  //            enum "1533.71" {
  //              description "1533.71 nm/195.46875 THz 6.25GHz spacing";
  //            }
  //            enum "1533.66" {
  //              description "1533.66 nm/195.47500 THz 6.25/12.5GHz spacing";
  //            }
  //            enum "1533.61" {
  //              description "1533.61 nm/195.48125 THz 6.25GHz spacing";
  //            }
  //            enum "1533.56" {
  //              description "1533.56 nm/195.48750 THz 6.25/12.5GHz spacing";
  //            }
  //            enum "1533.51" {
  //              description "1533.51 nm/195.49375 THz 6.25GHz spacing";
  //            }
  //            enum "1533.47" {
  //              description "1533.47 nm/195.50000 THz 6.25/12.5/50/75/100GHz spacing";
  //            }
  //            enum "1533.42" {
  //              description "1533.42 nm/195.50625 THz 6.25GHz spacing";
  //            }
  //            enum "1533.37" {
  //              description "1533.37 nm/195.51250 THz 6.25/12.5GHz spacing";
  //            }
  //            enum "1533.32" {
  //              description "1533.32 nm/195.51875 THz 6.25GHz spacing";
  //            }
  //            enum "1533.27" {
  //              description "1533.27 nm/195.52500 THz 6.25/12.5GHz spacing";
  //            }
  //            enum "1533.22" {
  //              description "1533.22 nm/195.53125 THz 6.25GHz spacing";
  //            }
  //            enum "1533.17" {
  //              description "1533.17 nm/195.53750 THz 6.25/12.5GHz spacing";
  //            }
  //            enum "1533.12" {
  //              description "1533.12 nm/195.54375 THz 6.25GHz spacing";
  //            }
  //            enum "1533.07" {
  //              description "1533.07 nm/195.55000 THz 6.25/12.5/50GHz spacing";
  //            }
  //            enum "1533.02" {
  //              description "1533.02 nm/195.55625 THz 6.25GHz spacing";
  //            }
  //            enum "1532.98" {
  //              description "1532.98 nm/195.56250 THz 6.25/12.5GHz spacing";
  //            }
  //            enum "1532.93" {
  //              description "1532.93 nm/195.56875 THz 6.25GHz spacing";
  //            }
  //            enum "1532.88" {
  //              description "1532.88 nm/195.57500 THz 6.25/12.5/75GHz spacing";
  //            }
  //            enum "1532.83" {
  //              description "1532.83 nm/195.58125 THz 6.25GHz spacing";
  //            }
  //            enum "1532.78" {
  //              description "1532.78 nm/195.58750 THz 6.25/12.5GHz spacing";
  //            }
  //            enum "1532.73" {
  //              description "1532.73 nm/195.59375 THz 6.25GHz spacing";
  //            }
  //            enum "1532.68" {
  //              description "1532.68 nm/195.60000 THz 6.25/12.5/50/100GHz spacing";
  //            }
  //            enum "1532.63" {
  //              description "1532.63 nm/195.60625 THz 6.25GHz spacing";
  //            }
  //            enum "1532.58" {
  //              description "1532.58 nm/195.61250 THz 6.25/12.5GHz spacing";
  //            }
  //            enum "1532.53" {
  //              description "1532.53 nm/195.61875 THz 6.25GHz spacing";
  //            }
  //            enum "1532.49" {
  //              description "1532.49 nm/195.62500 THz 6.25/12.5GHz spacing";
  //            }
  //            enum "1532.44" {
  //              description "1532.44 nm/195.63125 THz 6.25GHz spacing";
  //            }
  //            enum "1532.39" {
  //              description "1532.39 nm/195.63750 THz 6.25/12.5GHz spacing";
  //            }
  //            enum "1532.34" {
  //              description "1532.34 nm/195.64375 THz 6.25GHz spacing";
  //            }
  //            enum "1532.29" {
  //              description "1532.29 nm/195.65000 THz 6.25/12.5/50/75GHz spacing";
  //            }
  //            enum "1532.24" {
  //              description "1532.24 nm/195.65625 THz 6.25GHz spacing";
  //            }
  //            enum "1532.19" {
  //              description "1532.19 nm/195.66250 THz 6.25/12.5GHz spacing";
  //            }
  //            enum "1532.14" {
  //              description "1532.14 nm/195.66875 THz 6.25GHz spacing";
  //            }
  //            enum "1532.09" {
  //              description "1532.09 nm/195.67500 THz 6.25/12.5GHz spacing";
  //            }
  //            enum "1532.04" {
  //              description "1532.04 nm/195.68125 THz 6.25GHz spacing";
  //            }
  //            enum "1532.00" {
  //              description "1532.00 nm/195.68750 THz 6.25/12.5GHz spacing";
  //            }
  //            enum "1531.95" {
  //              description "1531.95 nm/195.69375 THz 6.25GHz spacing";
  //            }
  //            enum "1531.90" {
  //              description "1531.90 nm/195.70000 THz 6.25/12.5/50/100GHz spacing";
  //            }
  //            enum "1531.85" {
  //              description "1531.85 nm/195.70625 THz 6.25GHz spacing";
  //            }
  //            enum "1531.80" {
  //              description "1531.80 nm/195.71250 THz 6.25/12.5GHz spacing";
  //            }
  //            enum "1531.75" {
  //              description "1531.75 nm/195.71875 THz 6.25GHz spacing";
  //            }
  //            enum "1531.70" {
  //              description "1531.70 nm/195.72500 THz 6.25/12.5/75GHz spacing";
  //            }
  //            enum "1531.65" {
  //              description "1531.65 nm/195.73125 THz 6.25GHz spacing";
  //            }
  //            enum "1531.60" {
  //              description "1531.60 nm/195.73750 THz 6.25/12.5GHz spacing";
  //            }
  //            enum "1531.56" {
  //              description "1531.56 nm/195.74375 THz 6.25GHz spacing";
  //            }
  //            enum "1531.51" {
  //              description "1531.51 nm/195.75000 THz 6.25/12.5/50GHz spacing";
  //            }
  //            enum "1531.46" {
  //              description "1531.46 nm/195.75625 THz 6.25GHz spacing";
  //            }
  //            enum "1531.41" {
  //              description "1531.41 nm/195.76250 THz 6.25/12.5GHz spacing";
  //            }
  //            enum "1531.36" {
  //              description "1531.36 nm/195.76875 THz 6.25GHz spacing";
  //            }
  //            enum "1531.31" {
  //              description "1531.31 nm/195.77500 THz 6.25/12.5GHz spacing";
  //            }
  //            enum "1531.26" {
  //              description "1531.26 nm/195.78125 THz 6.25GHz spacing";
  //            }
  //            enum "1531.21" {
  //              description "1531.21 nm/195.78750 THz 6.25/12.5GHz spacing";
  //            }
  //            enum "1531.16" {
  //              description "1531.16 nm/195.79375 THz 6.25GHz spacing";
  //            }
  //            enum "1531.12" {
  //              description "1531.12 nm/195.80000 THz 6.25/12.5/50/75/100GHz spacing";
  //            }
  //            enum "1531.07" {
  //              description "1531.07 nm/195.80625 THz 6.25GHz spacing";
  //            }
  //            enum "1531.02" {
  //              description "1531.02 nm/195.81250 THz 6.25/12.5GHz spacing";
  //            }
  //            enum "1530.97" {
  //              description "1530.97 nm/195.81875 THz 6.25GHz spacing";
  //            }
  //            enum "1530.92" {
  //              description "1530.92 nm/195.82500 THz 6.25/12.5GHz spacing";
  //            }
  //            enum "1530.87" {
  //              description "1530.87 nm/195.83125 THz 6.25GHz spacing";
  //            }
  //            enum "1530.82" {
  //              description "1530.82 nm/195.83750 THz 6.25/12.5GHz spacing";
  //            }
  //            enum "1530.77" {
  //              description "1530.77 nm/195.84375 THz 6.25GHz spacing";
  //            }
  //            enum "1530.72" {
  //              description "1530.72 nm/195.85000 THz 6.25/12.5/50GHz spacing";
  //            }
  //            enum "1530.68" {
  //              description "1530.68 nm/195.85625 THz 6.25GHz spacing";
  //            }
  //            enum "1530.63" {
  //              description "1530.63 nm/195.86250 THz 6.25/12.5GHz spacing";
  //            }
  //            enum "1530.58" {
  //              description "1530.58 nm/195.86875 THz 6.25GHz spacing";
  //            }
  //            enum "1530.53" {
  //              description "1530.53 nm/195.87500 THz 6.25/12.5/75GHz spacing";
  //            }
  //            enum "1530.48" {
  //              description "1530.48 nm/195.88125 THz 6.25GHz spacing";
  //            }
  //            enum "1530.43" {
  //              description "1530.43 nm/195.88750 THz 6.25/12.5GHz spacing";
  //            }
  //            enum "1530.38" {
  //              description "1530.38 nm/195.89375 THz 6.25GHz spacing";
  //            }
  //            enum "1530.33" {
  //              description "1530.33 nm/195.90000 THz 6.25/12.5/50/100GHz spacing";
  //            }
  //            enum "1530.29" {
  //              description "1530.29 nm/195.90625 THz 6.25GHz spacing";
  //            }
  //            enum "1530.24" {
  //              description "1530.24 nm/195.91250 THz 6.25/12.5GHz spacing";
  //            }
  //            enum "1530.19" {
  //              description "1530.19 nm/195.91875 THz 6.25GHz spacing";
  //            }
  //            enum "1530.14" {
  //              description "1530.14 nm/195.92500 THz 6.25/12.5GHz spacing";
  //            }
  //            enum "1530.09" {
  //              description "1530.09 nm/195.93125 THz 6.25GHz spacing";
  //            }
  //            enum "1530.04" {
  //              description "1530.04 nm/195.93750 THz 6.25/12.5GHz spacing";
  //            }
  //            enum "1529.99" {
  //              description "1529.99 nm/195.94375 THz 6.25GHz spacing";
  //            }
  //            enum "1529.94" {
  //              description "1529.94 nm/195.95000 THz 6.25/12.5/50/75GHz spacing";
  //            }
  //            enum "1529.89" {
  //              description "1529.89 nm/195.95625 THz 6.25GHz spacing";
  //            }
  //            enum "1529.85" {
  //              description "1529.85 nm/195.96250 THz 6.25/12.5GHz spacing";
  //            }
  //            enum "1529.80" {
  //              description "1529.80 nm/195.96875 THz 6.25GHz spacing";
  //            }
  //            enum "1529.75" {
  //              description "1529.75 nm/195.97500 THz 6.25/12.5GHz spacing";
  //            }
  //            enum "1529.70" {
  //              description "1529.70 nm/195.98125 THz 6.25GHz spacing";
  //            }
  //            enum "1529.65" {
  //              description "1529.65 nm/195.98750 THz 6.25/12.5GHz spacing";
  //            }
  //            enum "1529.60" {
  //              description "1529.60 nm/195.99375 THz 6.25GHz spacing";
  //            }
  //            enum "1529.55" {
  //              description "1529.55 nm/196.00000 THz 6.25/12.5/50/100GHz spacing";
  //            }
  //            enum "1529.50" {
  //              description "1529.50 nm/196.00625 THz 6.25GHz spacing";
  //            }
  //            enum "1529.46" {
  //              description "1529.46 nm/196.01250 THz 6.25/12.5GHz spacing";
  //            }
  //            enum "1529.41" {
  //              description "1529.41 nm/196.01875 THz 6.25GHz spacing";
  //            }
  //            enum "1529.36" {
  //              description "1529.36 nm/196.02500 THz 6.25/12.5/75GHz spacing";
  //            }
  //            enum "1529.31" {
  //              description "1529.31 nm/196.03125 THz 6.25GHz spacing";
  //            }
  //            enum "1529.26" {
  //              description "1529.26 nm/196.03750 THz 6.25/12.5GHz spacing";
  //            }
  //            enum "1529.21" {
  //              description "1529.21 nm/196.04375 THz 6.25GHz spacing";
  //            }
  //            enum "1529.16" {
  //              description "1529.16 nm/196.05000 THz 6.25/12.5/50GHz spacing";
  //            }
  //            enum "1529.11" {
  //              description "1529.11 nm/196.05625 THz 6.25GHz spacing";
  //            }
  //            enum "1529.07" {
  //              description "1529.07 nm/196.06250 THz 6.25/12.5GHz spacing";
  //            }
  //            enum "1529.02" {
  //              description "1529.02 nm/196.06875 THz 6.25GHz spacing";
  //            }
  //            enum "1528.97" {
  //              description "1528.97 nm/196.07500 THz 6.25/12.5GHz spacing";
  //            }
  //            enum "1528.92" {
  //              description "1528.92 nm/196.08125 THz 6.25GHz spacing";
  //            }
  //            enum "1528.87" {
  //              description "1528.87 nm/196.08750 THz 6.25/12.5GHz spacing";
  //            }
  //            enum "1528.82" {
  //              description "1528.82 nm/196.09375 THz 6.25GHz spacing";
  //            }
  //            enum "1528.77" {
  //              description "1528.77 nm/196.10000 THz 6.25/12.5/50/75/100GHz spacing";
  //            }
  //            enum "1528.38" {
  //              description "1528.38 nm/196.15040 THz 50Ghz spacing";
  //            }
  //          }
  //        }
  //      }
  //      case case_2 {
  //        leaf frequency {
  //          description "Optical channel frequency in terahertz";
  //          type enumeration {
  //            enum "191.1003" {
  //              description "191.1003 THz/1568.77 nm 50/100Ghz spacing";
  //            }
  //            enum "191.15000" {
  //              description "191.15000 THz/1568.36 nm 6.25/12.5/50GHz spacing";
  //            }
  //            enum "191.15625" {
  //              description "191.15625 THz/1568.31 nm 6.25GHz spacing";
  //            }
  //            enum "191.16250" {
  //              description "191.16250 THz/1568.26 nm 6.25/12.5GHz spacing";
  //            }
  //            enum "191.16875" {
  //              description "191.16875 THz/1568.21 nm 6.25GHz spacing";
  //            }
  //            enum "191.17500" {
  //              description "191.17500 THz/1568.16 nm 6.25/12.5GHz spacing";
  //            }
  //            enum "191.18125" {
  //              description "191.18125 THz/1568.11 nm 6.25GHz spacing";
  //            }
  //            enum "191.18750" {
  //              description "191.18750 THz/1568.05 nm 6.25/12.5GHz spacing";
  //            }
  //            enum "191.19375" {
  //              description "191.19375 THz/1568.00 nm 6.25GHz spacing";
  //            }
  //            enum "191.20000" {
  //              description "191.20000 THz/1567.95 nm 6.25/12.5/50/100GHz spacing";
  //            }
  //            enum "191.20625" {
  //              description "191.20625 THz/1567.90 nm 6.25GHz spacing";
  //            }
  //            enum "191.21250" {
  //              description "191.21250 THz/1567.85 nm 6.25/12.5GHz spacing";
  //            }
  //            enum "191.21875" {
  //              description "191.21875 THz/1567.80 nm 6.25GHz spacing";
  //            }
  //            enum "191.22500" {
  //              description "191.22500 THz/1567.75 nm 6.25/12.5GHz spacing";
  //            }
  //            enum "191.23125" {
  //              description "191.23125 THz/1567.70 nm 6.25GHz spacing";
  //            }
  //            enum "191.23750" {
  //              description "191.23750 THz/1567.64 nm 6.25/12.5GHz spacing";
  //            }
  //            enum "191.24375" {
  //              description "191.24375 THz/1567.59 nm 6.25GHz spacing";
  //            }
  //            enum "191.25000" {
  //              description "191.25000 THz/1567.54 nm 6.25/12.5/50GHz spacing";
  //            }
  //            enum "191.25625" {
  //              description "191.25625 THz/1567.49 nm 6.25GHz spacing";
  //            }
  //            enum "191.26250" {
  //              description "191.26250 THz/1567.44 nm 6.25/12.5GHz spacing";
  //            }
  //            enum "191.26875" {
  //              description "191.26875 THz/1567.39 nm 6.25GHz spacing";
  //            }
  //            enum "191.27500" {
  //              description "191.27500 THz/1567.34 nm 6.25/12.5GHz spacing";
  //            }
  //            enum "191.28125" {
  //              description "191.28125 THz/1567.29 nm 6.25GHz spacing";
  //            }
  //            enum "191.28750" {
  //              description "191.28750 THz/1567.23 nm 6.25/12.5GHz spacing";
  //            }
  //            enum "191.29375" {
  //              description "191.29375 THz/1567.18 nm 6.25GHz spacing";
  //            }
  //            enum "191.30000" {
  //              description "191.30000 THz/1567.13 nm 6.25/12.5/50/100GHz spacing";
  //            }
  //            enum "191.30625" {
  //              description "191.30625 THz/1567.08 nm 6.25GHz spacing";
  //            }
  //            enum "191.31250" {
  //              description "191.31250 THz/1567.03 nm 6.25/12.5GHz spacing";
  //            }
  //            enum "191.31875" {
  //              description "191.31875 THz/1566.98 nm 6.25GHz spacing";
  //            }
  //            enum "191.32500" {
  //              description "191.32500 THz/1566.93 nm 6.25/12.5GHz spacing";
  //            }
  //            enum "191.33125" {
  //              description "191.33125 THz/1566.88 nm 6.25GHz spacing";
  //            }
  //            enum "191.33750" {
  //              description "191.33750 THz/1566.83 nm 6.25/12.5GHz spacing";
  //            }
  //            enum "191.34375" {
  //              description "191.34375 THz/1566.77 nm 6.25GHz spacing";
  //            }
  //            enum "191.35000" {
  //              description "191.35000 THz/1566.72 nm 6.25/12.5/50GHz spacing";
  //            }
  //            enum "191.35625" {
  //              description "191.35625 THz/1566.67 nm 6.25GHz spacing";
  //            }
  //            enum "191.36250" {
  //              description "191.36250 THz/1566.62 nm 6.25/12.5GHz spacing";
  //            }
  //            enum "191.36875" {
  //              description "191.36875 THz/1566.57 nm 6.25GHz spacing";
  //            }
  //            enum "191.37500" {
  //              description "191.37500 THz/1566.52 nm 6.25/12.5/75GHz spacing";
  //            }
  //            enum "191.38125" {
  //              description "191.38125 THz/1566.47 nm 6.25GHz spacing";
  //            }
  //            enum "191.38750" {
  //              description "191.38750 THz/1566.42 nm 6.25/12.5GHz spacing";
  //            }
  //            enum "191.39375" {
  //              description "191.39375 THz/1566.36 nm 6.25GHz spacing";
  //            }
  //            enum "191.40000" {
  //              description "191.40000 THz/1566.31 nm 6.25/12.5/50/100GHz spacing";
  //            }
  //            enum "191.40625" {
  //              description "191.40625 THz/1566.26 nm 6.25GHz spacing";
  //            }
  //            enum "191.41250" {
  //              description "191.41250 THz/1566.21 nm 6.25/12.5GHz spacing";
  //            }
  //            enum "191.41875" {
  //              description "191.41875 THz/1566.16 nm 6.25GHz spacing";
  //            }
  //            enum "191.42500" {
  //              description "191.42500 THz/1566.11 nm 6.25/12.5GHz spacing";
  //            }
  //            enum "191.43125" {
  //              description "191.43125 THz/1566.06 nm 6.25GHz spacing";
  //            }
  //            enum "191.43750" {
  //              description "191.43750 THz/1566.01 nm 6.25/12.5GHz spacing";
  //            }
  //            enum "191.44375" {
  //              description "191.44375 THz/1565.96 nm 6.25GHz spacing";
  //            }
  //            enum "191.45000" {
  //              description "191.45000 THz/1565.90 nm 6.25/12.5/50/75GHz spacing";
  //            }
  //            enum "191.45625" {
  //              description "191.45625 THz/1565.85 nm 6.25GHz spacing";
  //            }
  //            enum "191.46250" {
  //              description "191.46250 THz/1565.80 nm 6.25/12.5GHz spacing";
  //            }
  //            enum "191.46875" {
  //              description "191.46875 THz/1565.75 nm 6.25GHz spacing";
  //            }
  //            enum "191.47500" {
  //              description "191.47500 THz/1565.70 nm 6.25/12.5GHz spacing";
  //            }
  //            enum "191.48125" {
  //              description "191.48125 THz/1565.65 nm 6.25GHz spacing";
  //            }
  //            enum "191.48750" {
  //              description "191.48750 THz/1565.60 nm 6.25/12.5GHz spacing";
  //            }
  //            enum "191.49375" {
  //              description "191.49375 THz/1565.55 nm 6.25GHz spacing";
  //            }
  //            enum "191.50000" {
  //              description "191.50000 THz/1565.50 nm 6.25/12.5/50/100GHz spacing";
  //            }
  //            enum "191.50625" {
  //              description "191.50625 THz/1565.44 nm 6.25GHz spacing";
  //            }
  //            enum "191.51250" {
  //              description "191.51250 THz/1565.39 nm 6.25/12.5GHz spacing";
  //            }
  //            enum "191.51875" {
  //              description "191.51875 THz/1565.34 nm 6.25GHz spacing";
  //            }
  //            enum "191.52500" {
  //              description "191.52500 THz/1565.29 nm 6.25/12.5/75GHz spacing";
  //            }
  //            enum "191.53125" {
  //              description "191.53125 THz/1565.24 nm 6.25GHz spacing";
  //            }
  //            enum "191.53750" {
  //              description "191.53750 THz/1565.19 nm 6.25/12.5GHz spacing";
  //            }
  //            enum "191.54375" {
  //              description "191.54375 THz/1565.14 nm 6.25GHz spacing";
  //            }
  //            enum "191.55000" {
  //              description "191.55000 THz/1565.09 nm 6.25/12.5/50GHz spacing";
  //            }
  //            enum "191.55625" {
  //              description "191.55625 THz/1565.04 nm 6.25GHz spacing";
  //            }
  //            enum "191.56250" {
  //              description "191.56250 THz/1564.99 nm 6.25/12.5GHz spacing";
  //            }
  //            enum "191.56875" {
  //              description "191.56875 THz/1564.93 nm 6.25GHz spacing";
  //            }
  //            enum "191.57500" {
  //              description "191.57500 THz/1564.88 nm 6.25/12.5GHz spacing";
  //            }
  //            enum "191.58125" {
  //              description "191.58125 THz/1564.83 nm 6.25GHz spacing";
  //            }
  //            enum "191.58750" {
  //              description "191.58750 THz/1564.78 nm 6.25/12.5GHz spacing";
  //            }
  //            enum "191.59375" {
  //              description "191.59375 THz/1564.73 nm 6.25GHz spacing";
  //            }
  //            enum "191.60000" {
  //              description "191.60000 THz/1564.68 nm 6.25/12.5/50/75/100GHz spacing";
  //            }
  //            enum "191.60625" {
  //              description "191.60625 THz/1564.63 nm 6.25GHz spacing";
  //            }
  //            enum "191.61250" {
  //              description "191.61250 THz/1564.58 nm 6.25/12.5GHz spacing";
  //            }
  //            enum "191.61875" {
  //              description "191.61875 THz/1564.53 nm 6.25GHz spacing";
  //            }
  //            enum "191.62500" {
  //              description "191.62500 THz/1564.47 nm 6.25/12.5GHz spacing";
  //            }
  //            enum "191.63125" {
  //              description "191.63125 THz/1564.42 nm 6.25GHz spacing";
  //            }
  //            enum "191.63750" {
  //              description "191.63750 THz/1564.37 nm 6.25/12.5GHz spacing";
  //            }
  //            enum "191.64375" {
  //              description "191.64375 THz/1564.32 nm 6.25GHz spacing";
  //            }
  //            enum "191.65000" {
  //              description "191.65000 THz/1564.27 nm 6.25/12.5/50GHz spacing";
  //            }
  //            enum "191.65625" {
  //              description "191.65625 THz/1564.22 nm 6.25GHz spacing";
  //            }
  //            enum "191.66250" {
  //              description "191.66250 THz/1564.17 nm 6.25/12.5GHz spacing";
  //            }
  //            enum "191.66875" {
  //              description "191.66875 THz/1564.12 nm 6.25GHz spacing";
  //            }
  //            enum "191.67500" {
  //              description "191.67500 THz/1564.07 nm 6.25/12.5/75GHz spacing";
  //            }
  //            enum "191.68125" {
  //              description "191.68125 THz/1564.02 nm 6.25GHz spacing";
  //            }
  //            enum "191.68750" {
  //              description "191.68750 THz/1563.96 nm 6.25/12.5GHz spacing";
  //            }
  //            enum "191.69375" {
  //              description "191.69375 THz/1563.91 nm 6.25GHz spacing";
  //            }
  //            enum "191.70000" {
  //              description "191.70000 THz/1563.86 nm 6.25/12.5/50/100GHz spacing";
  //            }
  //            enum "191.70625" {
  //              description "191.70625 THz/1563.81 nm 6.25GHz spacing";
  //            }
  //            enum "191.71250" {
  //              description "191.71250 THz/1563.76 nm 6.25/12.5GHz spacing";
  //            }
  //            enum "191.71875" {
  //              description "191.71875 THz/1563.71 nm 6.25GHz spacing";
  //            }
  //            enum "191.72500" {
  //              description "191.72500 THz/1563.66 nm 6.25/12.5GHz spacing";
  //            }
  //            enum "191.73125" {
  //              description "191.73125 THz/1563.61 nm 6.25GHz spacing";
  //            }
  //            enum "191.73750" {
  //              description "191.73750 THz/1563.56 nm 6.25/12.5GHz spacing";
  //            }
  //            enum "191.74375" {
  //              description "191.74375 THz/1563.51 nm 6.25GHz spacing";
  //            }
  //            enum "191.75000" {
  //              description "191.75000 THz/1563.45 nm 6.25/12.5/50/75GHz spacing";
  //            }
  //            enum "191.75625" {
  //              description "191.75625 THz/1563.40 nm 6.25GHz spacing";
  //            }
  //            enum "191.76250" {
  //              description "191.76250 THz/1563.35 nm 6.25/12.5GHz spacing";
  //            }
  //            enum "191.76875" {
  //              description "191.76875 THz/1563.30 nm 6.25GHz spacing";
  //            }
  //            enum "191.77500" {
  //              description "191.77500 THz/1563.25 nm 6.25/12.5GHz spacing";
  //            }
  //            enum "191.78125" {
  //              description "191.78125 THz/1563.20 nm 6.25GHz spacing";
  //            }
  //            enum "191.78750" {
  //              description "191.78750 THz/1563.15 nm 6.25/12.5GHz spacing";
  //            }
  //            enum "191.79375" {
  //              description "191.79375 THz/1563.10 nm 6.25GHz spacing";
  //            }
  //            enum "191.80000" {
  //              description "191.80000 THz/1563.05 nm 6.25/12.5/50/100GHz spacing";
  //            }
  //            enum "191.80625" {
  //              description "191.80625 THz/1563.00 nm 6.25GHz spacing";
  //            }
  //            enum "191.81250" {
  //              description "191.81250 THz/1562.95 nm 6.25/12.5GHz spacing";
  //            }
  //            enum "191.81875" {
  //              description "191.81875 THz/1562.89 nm 6.25GHz spacing";
  //            }
  //            enum "191.82500" {
  //              description "191.82500 THz/1562.84 nm 6.25/12.5/75GHz spacing";
  //            }
  //            enum "191.83125" {
  //              description "191.83125 THz/1562.79 nm 6.25GHz spacing";
  //            }
  //            enum "191.83750" {
  //              description "191.83750 THz/1562.74 nm 6.25/12.5GHz spacing";
  //            }
  //            enum "191.84375" {
  //              description "191.84375 THz/1562.69 nm 6.25GHz spacing";
  //            }
  //            enum "191.85000" {
  //              description "191.85000 THz/1562.64 nm 6.25/12.5/50GHz spacing";
  //            }
  //            enum "191.85625" {
  //              description "191.85625 THz/1562.59 nm 6.25GHz spacing";
  //            }
  //            enum "191.86250" {
  //              description "191.86250 THz/1562.54 nm 6.25/12.5GHz spacing";
  //            }
  //            enum "191.86875" {
  //              description "191.86875 THz/1562.49 nm 6.25GHz spacing";
  //            }
  //            enum "191.87500" {
  //              description "191.87500 THz/1562.44 nm 6.25/12.5GHz spacing";
  //            }
  //            enum "191.88125" {
  //              description "191.88125 THz/1562.39 nm 6.25GHz spacing";
  //            }
  //            enum "191.88750" {
  //              description "191.88750 THz/1562.33 nm 6.25/12.5GHz spacing";
  //            }
  //            enum "191.89375" {
  //              description "191.89375 THz/1562.28 nm 6.25GHz spacing";
  //            }
  //            enum "191.90000" {
  //              description "191.90000 THz/1562.23 nm 6.25/12.5/50/75/100GHz spacing";
  //            }
  //            enum "191.90625" {
  //              description "191.90625 THz/1562.18 nm 6.25GHz spacing";
  //            }
  //            enum "191.91250" {
  //              description "191.91250 THz/1562.13 nm 6.25/12.5GHz spacing";
  //            }
  //            enum "191.91875" {
  //              description "191.91875 THz/1562.08 nm 6.25GHz spacing";
  //            }
  //            enum "191.92500" {
  //              description "191.92500 THz/1562.03 nm 6.25/12.5GHz spacing";
  //            }
  //            enum "191.93125" {
  //              description "191.93125 THz/1561.98 nm 6.25GHz spacing";
  //            }
  //            enum "191.93750" {
  //              description "191.93750 THz/1561.93 nm 6.25/12.5GHz spacing";
  //            }
  //            enum "191.94375" {
  //              description "191.94375 THz/1561.88 nm 6.25GHz spacing";
  //            }
  //            enum "191.95000" {
  //              description "191.95000 THz/1561.83 nm 6.25/12.5/50GHz spacing";
  //            }
  //            enum "191.95625" {
  //              description "191.95625 THz/1561.77 nm 6.25GHz spacing";
  //            }
  //            enum "191.96250" {
  //              description "191.96250 THz/1561.72 nm 6.25/12.5GHz spacing";
  //            }
  //            enum "191.96875" {
  //              description "191.96875 THz/1561.67 nm 6.25GHz spacing";
  //            }
  //            enum "191.97500" {
  //              description "191.97500 THz/1561.62 nm 6.25/12.5/75GHz spacing";
  //            }
  //            enum "191.98125" {
  //              description "191.98125 THz/1561.57 nm 6.25GHz spacing";
  //            }
  //            enum "191.98750" {
  //              description "191.98750 THz/1561.52 nm 6.25/12.5GHz spacing";
  //            }
  //            enum "191.99375" {
  //              description "191.99375 THz/1561.47 nm 6.25GHz spacing";
  //            }
  //            enum "192.00000" {
  //              description "192.00000 THz/1561.42 nm 6.25/12.5/50/100GHz spacing";
  //            }
  //            enum "192.00625" {
  //              description "192.00625 THz/1561.37 nm 6.25GHz spacing";
  //            }
  //            enum "192.01250" {
  //              description "192.01250 THz/1561.32 nm 6.25/12.5GHz spacing";
  //            }
  //            enum "192.01875" {
  //              description "192.01875 THz/1561.27 nm 6.25GHz spacing";
  //            }
  //            enum "192.02500" {
  //              description "192.02500 THz/1561.22 nm 6.25/12.5GHz spacing";
  //            }
  //            enum "192.03125" {
  //              description "192.03125 THz/1561.16 nm 6.25GHz spacing";
  //            }
  //            enum "192.03750" {
  //              description "192.03750 THz/1561.11 nm 6.25/12.5GHz spacing";
  //            }
  //            enum "192.04375" {
  //              description "192.04375 THz/1561.06 nm 6.25GHz spacing";
  //            }
  //            enum "192.05000" {
  //              description "192.05000 THz/1561.01 nm 6.25/12.5/50/75GHz spacing";
  //            }
  //            enum "192.05625" {
  //              description "192.05625 THz/1560.96 nm 6.25GHz spacing";
  //            }
  //            enum "192.06250" {
  //              description "192.06250 THz/1560.91 nm 6.25/12.5GHz spacing";
  //            }
  //            enum "192.06875" {
  //              description "192.06875 THz/1560.86 nm 6.25GHz spacing";
  //            }
  //            enum "192.07500" {
  //              description "192.07500 THz/1560.81 nm 6.25/12.5GHz spacing";
  //            }
  //            enum "192.08125" {
  //              description "192.08125 THz/1560.76 nm 6.25GHz spacing";
  //            }
  //            enum "192.08750" {
  //              description "192.08750 THz/1560.71 nm 6.25/12.5GHz spacing";
  //            }
  //            enum "192.09375" {
  //              description "192.09375 THz/1560.66 nm 6.25GHz spacing";
  //            }
  //            enum "192.10000" {
  //              description "192.10000 THz/1560.61 nm 6.25/12.5/50/100GHz spacing";
  //            }
  //            enum "192.10625" {
  //              description "192.10625 THz/1560.56 nm 6.25GHz spacing";
  //            }
  //            enum "192.11250" {
  //              description "192.11250 THz/1560.50 nm 6.25/12.5GHz spacing";
  //            }
  //            enum "192.11875" {
  //              description "192.11875 THz/1560.45 nm 6.25GHz spacing";
  //            }
  //            enum "192.12500" {
  //              description "192.12500 THz/1560.40 nm 6.25/12.5/75GHz spacing";
  //            }
  //            enum "192.13125" {
  //              description "192.13125 THz/1560.35 nm 6.25GHz spacing";
  //            }
  //            enum "192.13750" {
  //              description "192.13750 THz/1560.30 nm 6.25/12.5GHz spacing";
  //            }
  //            enum "192.14375" {
  //              description "192.14375 THz/1560.25 nm 6.25GHz spacing";
  //            }
  //            enum "192.15000" {
  //              description "192.15000 THz/1560.20 nm 6.25/12.5/50GHz spacing";
  //            }
  //            enum "192.15625" {
  //              description "192.15625 THz/1560.15 nm 6.25GHz spacing";
  //            }
  //            enum "192.16250" {
  //              description "192.16250 THz/1560.10 nm 6.25/12.5GHz spacing";
  //            }
  //            enum "192.16875" {
  //              description "192.16875 THz/1560.05 nm 6.25GHz spacing";
  //            }
  //            enum "192.17500" {
  //              description "192.17500 THz/1560.00 nm 6.25/12.5GHz spacing";
  //            }
  //            enum "192.18125" {
  //              description "192.18125 THz/1559.95 nm 6.25GHz spacing";
  //            }
  //            enum "192.18750" {
  //              description "192.18750 THz/1559.90 nm 6.25/12.5GHz spacing";
  //            }
  //            enum "192.19375" {
  //              description "192.19375 THz/1559.84 nm 6.25GHz spacing";
  //            }
  //            enum "192.20000" {
  //              description "192.20000 THz/1559.79 nm 6.25/12.5/50/75/100GHz spacing";
  //            }
  //            enum "192.20625" {
  //              description "192.20625 THz/1559.74 nm 6.25GHz spacing";
  //            }
  //            enum "192.21250" {
  //              description "192.21250 THz/1559.69 nm 6.25/12.5GHz spacing";
  //            }
  //            enum "192.21875" {
  //              description "192.21875 THz/1559.64 nm 6.25GHz spacing";
  //            }
  //            enum "192.22500" {
  //              description "192.22500 THz/1559.59 nm 6.25/12.5GHz spacing";
  //            }
  //            enum "192.23125" {
  //              description "192.23125 THz/1559.54 nm 6.25GHz spacing";
  //            }
  //            enum "192.23750" {
  //              description "192.23750 THz/1559.49 nm 6.25/12.5GHz spacing";
  //            }
  //            enum "192.24375" {
  //              description "192.24375 THz/1559.44 nm 6.25GHz spacing";
  //            }
  //            enum "192.25000" {
  //              description "192.25000 THz/1559.39 nm 6.25/12.5/50GHz spacing";
  //            }
  //            enum "192.25625" {
  //              description "192.25625 THz/1559.34 nm 6.25GHz spacing";
  //            }
  //            enum "192.26250" {
  //              description "192.26250 THz/1559.29 nm 6.25/12.5GHz spacing";
  //            }
  //            enum "192.26875" {
  //              description "192.26875 THz/1559.24 nm 6.25GHz spacing";
  //            }
  //            enum "192.27500" {
  //              description "192.27500 THz/1559.19 nm 6.25/12.5GHz spacing";
  //            }
  //            enum "192.28125" {
  //              description "192.28125 THz/1559.14 nm 6.25GHz spacing";
  //            }
  //            enum "192.28750" {
  //              description "192.28750 THz/1559.08 nm 6.25/12.5GHz spacing";
  //            }
  //            enum "192.29375" {
  //              description "192.29375 THz/1559.03 nm 6.25GHz spacing";
  //            }
  //            enum "192.30000" {
  //              description "192.30000 THz/1558.98 nm 6.25/12.5/50/100GHz spacing";
  //            }
  //            enum "192.30625" {
  //              description "192.30625 THz/1558.93 nm 6.25GHz spacing";
  //            }
  //            enum "192.31250" {
  //              description "192.31250 THz/1558.88 nm 6.25/12.5GHz spacing";
  //            }
  //            enum "192.31875" {
  //              description "192.31875 THz/1558.83 nm 6.25GHz spacing";
  //            }
  //            enum "192.32500" {
  //              description "192.32500 THz/1558.78 nm 6.25/12.5GHz spacing";
  //            }
  //            enum "192.33125" {
  //              description "192.33125 THz/1558.73 nm 6.25GHz spacing";
  //            }
  //            enum "192.33750" {
  //              description "192.33750 THz/1558.68 nm 6.25/12.5GHz spacing";
  //            }
  //            enum "192.34375" {
  //              description "192.34375 THz/1558.63 nm 6.25GHz spacing";
  //            }
  //            enum "192.35000" {
  //              description "192.35000 THz/1558.58 nm 6.25/12.5/50/75GHz spacing";
  //            }
  //            enum "192.35625" {
  //              description "192.35625 THz/1558.53 nm 6.25GHz spacing";
  //            }
  //            enum "192.36250" {
  //              description "192.36250 THz/1558.48 nm 6.25/12.5GHz spacing";
  //            }
  //            enum "192.36875" {
  //              description "192.36875 THz/1558.43 nm 6.25GHz spacing";
  //            }
  //            enum "192.37500" {
  //              description "192.37500 THz/1558.38 nm 6.25/12.5GHz spacing";
  //            }
  //            enum "192.38125" {
  //              description "192.38125 THz/1558.32 nm 6.25GHz spacing";
  //            }
  //            enum "192.38750" {
  //              description "192.38750 THz/1558.27 nm 6.25/12.5GHz spacing";
  //            }
  //            enum "192.39375" {
  //              description "192.39375 THz/1558.22 nm 6.25GHz spacing";
  //            }
  //            enum "192.40000" {
  //              description "192.40000 THz/1558.17 nm 6.25/12.5/50/100GHz spacing";
  //            }
  //            enum "192.40625" {
  //              description "192.40625 THz/1558.12 nm 6.25GHz spacing";
  //            }
  //            enum "192.41250" {
  //              description "192.41250 THz/1558.07 nm 6.25/12.5GHz spacing";
  //            }
  //            enum "192.41875" {
  //              description "192.41875 THz/1558.02 nm 6.25GHz spacing";
  //            }
  //            enum "192.42500" {
  //              description "192.42500 THz/1557.97 nm 6.25/12.5/75GHz spacing";
  //            }
  //            enum "192.43125" {
  //              description "192.43125 THz/1557.92 nm 6.25GHz spacing";
  //            }
  //            enum "192.43750" {
  //              description "192.43750 THz/1557.87 nm 6.25/12.5GHz spacing";
  //            }
  //            enum "192.44375" {
  //              description "192.44375 THz/1557.82 nm 6.25GHz spacing";
  //            }
  //            enum "192.45000" {
  //              description "192.45000 THz/1557.77 nm 6.25/12.5/50GHz spacing";
  //            }
  //            enum "192.45625" {
  //              description "192.45625 THz/1557.72 nm 6.25GHz spacing";
  //            }
  //            enum "192.46250" {
  //              description "192.46250 THz/1557.67 nm 6.25/12.5GHz spacing";
  //            }
  //            enum "192.46875" {
  //              description "192.46875 THz/1557.62 nm 6.25GHz spacing";
  //            }
  //            enum "192.47500" {
  //              description "192.47500 THz/1557.57 nm 6.25/12.5GHz spacing";
  //            }
  //            enum "192.48125" {
  //              description "192.48125 THz/1557.52 nm 6.25GHz spacing";
  //            }
  //            enum "192.48750" {
  //              description "192.48750 THz/1557.46 nm 6.25/12.5GHz spacing";
  //            }
  //            enum "192.49375" {
  //              description "192.49375 THz/1557.41 nm 6.25GHz spacing";
  //            }
  //            enum "192.50000" {
  //              description "192.50000 THz/1557.36 nm 6.25/12.5/50/75/100GHz spacing";
  //            }
  //            enum "192.50625" {
  //              description "192.50625 THz/1557.31 nm 6.25GHz spacing";
  //            }
  //            enum "192.51250" {
  //              description "192.51250 THz/1557.26 nm 6.25/12.5GHz spacing";
  //            }
  //            enum "192.51875" {
  //              description "192.51875 THz/1557.21 nm 6.25GHz spacing";
  //            }
  //            enum "192.52500" {
  //              description "192.52500 THz/1557.16 nm 6.25/12.5GHz spacing";
  //            }
  //            enum "192.53125" {
  //              description "192.53125 THz/1557.11 nm 6.25GHz spacing";
  //            }
  //            enum "192.53750" {
  //              description "192.53750 THz/1557.06 nm 6.25/12.5GHz spacing";
  //            }
  //            enum "192.54375" {
  //              description "192.54375 THz/1557.01 nm 6.25GHz spacing";
  //            }
  //            enum "192.55000" {
  //              description "192.55000 THz/1556.96 nm 6.25/12.5/50GHz spacing";
  //            }
  //            enum "192.55625" {
  //              description "192.55625 THz/1556.91 nm 6.25GHz spacing";
  //            }
  //            enum "192.56250" {
  //              description "192.56250 THz/1556.86 nm 6.25/12.5GHz spacing";
  //            }
  //            enum "192.56875" {
  //              description "192.56875 THz/1556.81 nm 6.25GHz spacing";
  //            }
  //            enum "192.57500" {
  //              description "192.57500 THz/1556.76 nm 6.25/12.5/75GHz spacing";
  //            }
  //            enum "192.58125" {
  //              description "192.58125 THz/1556.71 nm 6.25GHz spacing";
  //            }
  //            enum "192.58750" {
  //              description "192.58750 THz/1556.66 nm 6.25/12.5GHz spacing";
  //            }
  //            enum "192.59375" {
  //              description "192.59375 THz/1556.61 nm 6.25GHz spacing";
  //            }
  //            enum "192.60000" {
  //              description "192.60000 THz/1556.55 nm 6.25/12.5/50/100GHz spacing";
  //            }
  //            enum "192.60625" {
  //              description "192.60625 THz/1556.50 nm 6.25GHz spacing";
  //            }
  //            enum "192.61250" {
  //              description "192.61250 THz/1556.45 nm 6.25/12.5GHz spacing";
  //            }
  //            enum "192.61875" {
  //              description "192.61875 THz/1556.40 nm 6.25GHz spacing";
  //            }
  //            enum "192.62500" {
  //              description "192.62500 THz/1556.35 nm 6.25/12.5GHz spacing";
  //            }
  //            enum "192.63125" {
  //              description "192.63125 THz/1556.30 nm 6.25GHz spacing";
  //            }
  //            enum "192.63750" {
  //              description "192.63750 THz/1556.25 nm 6.25/12.5GHz spacing";
  //            }
  //            enum "192.64375" {
  //              description "192.64375 THz/1556.20 nm 6.25GHz spacing";
  //            }
  //            enum "192.65000" {
  //              description "192.65000 THz/1556.15 nm 6.25/12.5/50/75GHz spacing";
  //            }
  //            enum "192.65625" {
  //              description "192.65625 THz/1556.10 nm 6.25GHz spacing";
  //            }
  //            enum "192.66250" {
  //              description "192.66250 THz/1556.05 nm 6.25/12.5GHz spacing";
  //            }
  //            enum "192.66875" {
  //              description "192.66875 THz/1556.00 nm 6.25GHz spacing";
  //            }
  //            enum "192.67500" {
  //              description "192.67500 THz/1555.95 nm 6.25/12.5GHz spacing";
  //            }
  //            enum "192.68125" {
  //              description "192.68125 THz/1555.90 nm 6.25GHz spacing";
  //            }
  //            enum "192.68750" {
  //              description "192.68750 THz/1555.85 nm 6.25/12.5GHz spacing";
  //            }
  //            enum "192.69375" {
  //              description "192.69375 THz/1555.80 nm 6.25GHz spacing";
  //            }
  //            enum "192.70000" {
  //              description "192.70000 THz/1555.75 nm 6.25/12.5/50/100GHz spacing";
  //            }
  //            enum "192.70625" {
  //              description "192.70625 THz/1555.70 nm 6.25GHz spacing";
  //            }
  //            enum "192.71250" {
  //              description "192.71250 THz/1555.65 nm 6.25/12.5GHz spacing";
  //            }
  //            enum "192.71875" {
  //              description "192.71875 THz/1555.60 nm 6.25GHz spacing";
  //            }
  //            enum "192.72500" {
  //              description "192.72500 THz/1555.55 nm 6.25/12.5/75GHz spacing";
  //            }
  //            enum "192.73125" {
  //              description "192.73125 THz/1555.49 nm 6.25GHz spacing";
  //            }
  //            enum "192.73750" {
  //              description "192.73750 THz/1555.44 nm 6.25/12.5GHz spacing";
  //            }
  //            enum "192.74375" {
  //              description "192.74375 THz/1555.39 nm 6.25GHz spacing";
  //            }
  //            enum "192.75000" {
  //              description "192.75000 THz/1555.34 nm 6.25/12.5/50GHz spacing";
  //            }
  //            enum "192.75625" {
  //              description "192.75625 THz/1555.29 nm 6.25GHz spacing";
  //            }
  //            enum "192.76250" {
  //              description "192.76250 THz/1555.24 nm 6.25/12.5GHz spacing";
  //            }
  //            enum "192.76875" {
  //              description "192.76875 THz/1555.19 nm 6.25GHz spacing";
  //            }
  //            enum "192.77500" {
  //              description "192.77500 THz/1555.14 nm 6.25/12.5GHz spacing";
  //            }
  //            enum "192.78125" {
  //              description "192.78125 THz/1555.09 nm 6.25GHz spacing";
  //            }
  //            enum "192.78750" {
  //              description "192.78750 THz/1555.04 nm 6.25/12.5GHz spacing";
  //            }
  //            enum "192.79375" {
  //              description "192.79375 THz/1554.99 nm 6.25GHz spacing";
  //            }
  //            enum "192.80000" {
  //              description "192.80000 THz/1554.94 nm 6.25/12.5/50/75/100GHz spacing";
  //            }
  //            enum "192.80625" {
  //              description "192.80625 THz/1554.89 nm 6.25GHz spacing";
  //            }
  //            enum "192.81250" {
  //              description "192.81250 THz/1554.84 nm 6.25/12.5GHz spacing";
  //            }
  //            enum "192.81875" {
  //              description "192.81875 THz/1554.79 nm 6.25GHz spacing";
  //            }
  //            enum "192.82500" {
  //              description "192.82500 THz/1554.74 nm 6.25/12.5GHz spacing";
  //            }
  //            enum "192.83125" {
  //              description "192.83125 THz/1554.69 nm 6.25GHz spacing";
  //            }
  //            enum "192.83750" {
  //              description "192.83750 THz/1554.64 nm 6.25/12.5GHz spacing";
  //            }
  //            enum "192.84375" {
  //              description "192.84375 THz/1554.59 nm 6.25GHz spacing";
  //            }
  //            enum "192.85000" {
  //              description "192.85000 THz/1554.54 nm 6.25/12.5/50GHz spacing";
  //            }
  //            enum "192.85625" {
  //              description "192.85625 THz/1554.49 nm 6.25GHz spacing";
  //            }
  //            enum "192.86250" {
  //              description "192.86250 THz/1554.44 nm 6.25/12.5GHz spacing";
  //            }
  //            enum "192.86875" {
  //              description "192.86875 THz/1554.39 nm 6.25GHz spacing";
  //            }
  //            enum "192.87500" {
  //              description "192.87500 THz/1554.34 nm 6.25/12.5/75GHz spacing";
  //            }
  //            enum "192.88125" {
  //              description "192.88125 THz/1554.29 nm 6.25GHz spacing";
  //            }
  //            enum "192.88750" {
  //              description "192.88750 THz/1554.23 nm 6.25/12.5GHz spacing";
  //            }
  //            enum "192.89375" {
  //              description "192.89375 THz/1554.18 nm 6.25GHz spacing";
  //            }
  //            enum "192.90000" {
  //              description "192.90000 THz/1554.13 nm 6.25/12.5/50/100GHz spacing";
  //            }
  //            enum "192.90625" {
  //              description "192.90625 THz/1554.08 nm 6.25GHz spacing";
  //            }
  //            enum "192.91250" {
  //              description "192.91250 THz/1554.03 nm 6.25/12.5GHz spacing";
  //            }
  //            enum "192.91875" {
  //              description "192.91875 THz/1553.98 nm 6.25GHz spacing";
  //            }
  //            enum "192.92500" {
  //              description "192.92500 THz/1553.93 nm 6.25/12.5GHz spacing";
  //            }
  //            enum "192.93125" {
  //              description "192.93125 THz/1553.88 nm 6.25GHz spacing";
  //            }
  //            enum "192.93750" {
  //              description "192.93750 THz/1553.83 nm 6.25/12.5GHz spacing";
  //            }
  //            enum "192.94375" {
  //              description "192.94375 THz/1553.78 nm 6.25GHz spacing";
  //            }
  //            enum "192.95000" {
  //              description "192.95000 THz/1553.73 nm 6.25/12.5/50/75GHz spacing";
  //            }
  //            enum "192.95625" {
  //              description "192.95625 THz/1553.68 nm 6.25GHz spacing";
  //            }
  //            enum "192.96250" {
  //              description "192.96250 THz/1553.63 nm 6.25/12.5GHz spacing";
  //            }
  //            enum "192.96875" {
  //              description "192.96875 THz/1553.58 nm 6.25GHz spacing";
  //            }
  //            enum "192.97500" {
  //              description "192.97500 THz/1553.53 nm 6.25/12.5GHz spacing";
  //            }
  //            enum "192.98125" {
  //              description "192.98125 THz/1553.48 nm 6.25GHz spacing";
  //            }
  //            enum "192.98750" {
  //              description "192.98750 THz/1553.43 nm 6.25/12.5GHz spacing";
  //            }
  //            enum "192.99375" {
  //              description "192.99375 THz/1553.38 nm 6.25GHz spacing";
  //            }
  //            enum "193.00000" {
  //              description "193.00000 THz/1553.33 nm 6.25/12.5/50/100GHz spacing";
  //            }
  //            enum "193.00625" {
  //              description "193.00625 THz/1553.28 nm 6.25GHz spacing";
  //            }
  //            enum "193.01250" {
  //              description "193.01250 THz/1553.23 nm 6.25/12.5GHz spacing";
  //            }
  //            enum "193.01875" {
  //              description "193.01875 THz/1553.18 nm 6.25GHz spacing";
  //            }
  //            enum "193.02500" {
  //              description "193.02500 THz/1553.13 nm 6.25/12.5/75GHz spacing";
  //            }
  //            enum "193.03125" {
  //              description "193.03125 THz/1553.08 nm 6.25GHz spacing";
  //            }
  //            enum "193.03750" {
  //              description "193.03750 THz/1553.03 nm 6.25/12.5GHz spacing";
  //            }
  //            enum "193.04375" {
  //              description "193.04375 THz/1552.98 nm 6.25GHz spacing";
  //            }
  //            enum "193.05000" {
  //              description "193.05000 THz/1552.93 nm 6.25/12.5/50GHz spacing";
  //            }
  //            enum "193.05625" {
  //              description "193.05625 THz/1552.88 nm 6.25GHz spacing";
  //            }
  //            enum "193.06250" {
  //              description "193.06250 THz/1552.83 nm 6.25/12.5GHz spacing";
  //            }
  //            enum "193.06875" {
  //              description "193.06875 THz/1552.78 nm 6.25GHz spacing";
  //            }
  //            enum "193.07500" {
  //              description "193.07500 THz/1552.73 nm 6.25/12.5GHz spacing";
  //            }
  //            enum "193.08125" {
  //              description "193.08125 THz/1552.68 nm 6.25GHz spacing";
  //            }
  //            enum "193.08750" {
  //              description "193.08750 THz/1552.62 nm 6.25/12.5GHz spacing";
  //            }
  //            enum "193.09375" {
  //              description "193.09375 THz/1552.57 nm 6.25GHz spacing";
  //            }
  //            enum "193.10000" {
  //              description "193.10000 THz/1552.52 nm 6.25/12.5/50/75/100GHz spacing";
  //            }
  //            enum "193.10625" {
  //              description "193.10625 THz/1552.47 nm 6.25GHz spacing";
  //            }
  //            enum "193.11250" {
  //              description "193.11250 THz/1552.42 nm 6.25/12.5GHz spacing";
  //            }
  //            enum "193.11875" {
  //              description "193.11875 THz/1552.37 nm 6.25GHz spacing";
  //            }
  //            enum "193.12500" {
  //              description "193.12500 THz/1552.32 nm 6.25/12.5GHz spacing";
  //            }
  //            enum "193.13125" {
  //              description "193.13125 THz/1552.27 nm 6.25GHz spacing";
  //            }
  //            enum "193.13750" {
  //              description "193.13750 THz/1552.22 nm 6.25/12.5GHz spacing";
  //            }
  //            enum "193.14375" {
  //              description "193.14375 THz/1552.17 nm 6.25GHz spacing";
  //            }
  //            enum "193.15000" {
  //              description "193.15000 THz/1552.12 nm 6.25/12.5/50GHz spacing";
  //            }
  //            enum "193.15625" {
  //              description "193.15625 THz/1552.07 nm 6.25GHz spacing";
  //            }
  //            enum "193.16250" {
  //              description "193.16250 THz/1552.02 nm 6.25/12.5GHz spacing";
  //            }
  //            enum "193.16875" {
  //              description "193.16875 THz/1551.97 nm 6.25GHz spacing";
  //            }
  //            enum "193.17500" {
  //              description "193.17500 THz/1551.92 nm 6.25/12.5/75GHz spacing";
  //            }
  //            enum "193.18125" {
  //              description "193.18125 THz/1551.87 nm 6.25GHz spacing";
  //            }
  //            enum "193.18750" {
  //              description "193.18750 THz/1551.82 nm 6.25/12.5GHz spacing";
  //            }
  //            enum "193.19375" {
  //              description "193.19375 THz/1551.77 nm 6.25GHz spacing";
  //            }
  //            enum "193.20000" {
  //              description "193.20000 THz/1551.72 nm 6.25/12.5/50/100GHz spacing";
  //            }
  //            enum "193.20625" {
  //              description "193.20625 THz/1551.67 nm 6.25GHz spacing";
  //            }
  //            enum "193.21250" {
  //              description "193.21250 THz/1551.62 nm 6.25/12.5GHz spacing";
  //            }
  //            enum "193.21875" {
  //              description "193.21875 THz/1551.57 nm 6.25GHz spacing";
  //            }
  //            enum "193.22500" {
  //              description "193.22500 THz/1551.52 nm 6.25/12.5GHz spacing";
  //            }
  //            enum "193.23125" {
  //              description "193.23125 THz/1551.47 nm 6.25GHz spacing";
  //            }
  //            enum "193.23750" {
  //              description "193.23750 THz/1551.42 nm 6.25/12.5GHz spacing";
  //            }
  //            enum "193.24375" {
  //              description "193.24375 THz/1551.37 nm 6.25GHz spacing";
  //            }
  //            enum "193.25000" {
  //              description "193.25000 THz/1551.32 nm 6.25/12.5/50/75GHz spacing";
  //            }
  //            enum "193.25625" {
  //              description "193.25625 THz/1551.27 nm 6.25GHz spacing";
  //            }
  //            enum "193.26250" {
  //              description "193.26250 THz/1551.22 nm 6.25/12.5GHz spacing";
  //            }
  //            enum "193.26875" {
  //              description "193.26875 THz/1551.17 nm 6.25GHz spacing";
  //            }
  //            enum "193.27500" {
  //              description "193.27500 THz/1551.12 nm 6.25/12.5GHz spacing";
  //            }
  //            enum "193.28125" {
  //              description "193.28125 THz/1551.07 nm 6.25GHz spacing";
  //            }
  //            enum "193.28750" {
  //              description "193.28750 THz/1551.02 nm 6.25/12.5GHz spacing";
  //            }
  //            enum "193.29375" {
  //              description "193.29375 THz/1550.97 nm 6.25GHz spacing";
  //            }
  //            enum "193.30000" {
  //              description "193.30000 THz/1550.92 nm 6.25/12.5/50/100GHz spacing";
  //            }
  //            enum "193.30625" {
  //              description "193.30625 THz/1550.87 nm 6.25GHz spacing";
  //            }
  //            enum "193.31250" {
  //              description "193.31250 THz/1550.82 nm 6.25/12.5GHz spacing";
  //            }
  //            enum "193.31875" {
  //              description "193.31875 THz/1550.77 nm 6.25GHz spacing";
  //            }
  //            enum "193.32500" {
  //              description "193.32500 THz/1550.72 nm 6.25/12.5/75GHz spacing";
  //            }
  //            enum "193.33125" {
  //              description "193.33125 THz/1550.67 nm 6.25GHz spacing";
  //            }
  //            enum "193.33750" {
  //              description "193.33750 THz/1550.62 nm 6.25/12.5GHz spacing";
  //            }
  //            enum "193.34375" {
  //              description "193.34375 THz/1550.57 nm 6.25GHz spacing";
  //            }
  //            enum "193.35000" {
  //              description "193.35000 THz/1550.52 nm 6.25/12.5/50GHz spacing";
  //            }
  //            enum "193.35625" {
  //              description "193.35625 THz/1550.47 nm 6.25GHz spacing";
  //            }
  //            enum "193.36250" {
  //              description "193.36250 THz/1550.42 nm 6.25/12.5GHz spacing";
  //            }
  //            enum "193.36875" {
  //              description "193.36875 THz/1550.37 nm 6.25GHz spacing";
  //            }
  //            enum "193.37500" {
  //              description "193.37500 THz/1550.32 nm 6.25/12.5GHz spacing";
  //            }
  //            enum "193.38125" {
  //              description "193.38125 THz/1550.27 nm 6.25GHz spacing";
  //            }
  //            enum "193.38750" {
  //              description "193.38750 THz/1550.22 nm 6.25/12.5GHz spacing";
  //            }
  //            enum "193.39375" {
  //              description "193.39375 THz/1550.17 nm 6.25GHz spacing";
  //            }
  //            enum "193.40000" {
  //              description "193.40000 THz/1550.12 nm 6.25/12.5/50/75/100GHz spacing";
  //            }
  //            enum "193.40625" {
  //              description "193.40625 THz/1550.07 nm 6.25GHz spacing";
  //            }
  //            enum "193.41250" {
  //              description "193.41250 THz/1550.02 nm 6.25/12.5GHz spacing";
  //            }
  //            enum "193.41875" {
  //              description "193.41875 THz/1549.97 nm 6.25GHz spacing";
  //            }
  //            enum "193.42500" {
  //              description "193.42500 THz/1549.92 nm 6.25/12.5GHz spacing";
  //            }
  //            enum "193.43125" {
  //              description "193.43125 THz/1549.87 nm 6.25GHz spacing";
  //            }
  //            enum "193.43750" {
  //              description "193.43750 THz/1549.82 nm 6.25/12.5GHz spacing";
  //            }
  //            enum "193.44375" {
  //              description "193.44375 THz/1549.77 nm 6.25GHz spacing";
  //            }
  //            enum "193.45000" {
  //              description "193.45000 THz/1549.72 nm 6.25/12.5/50GHz spacing";
  //            }
  //            enum "193.45625" {
  //              description "193.45625 THz/1549.67 nm 6.25GHz spacing";
  //            }
  //            enum "193.46250" {
  //              description "193.46250 THz/1549.62 nm 6.25/12.5GHz spacing";
  //            }
  //            enum "193.46875" {
  //              description "193.46875 THz/1549.57 nm 6.25GHz spacing";
  //            }
  //            enum "193.47500" {
  //              description "193.47500 THz/1549.52 nm 6.25/12.5/75GHz spacing";
  //            }
  //            enum "193.48125" {
  //              description "193.48125 THz/1549.47 nm 6.25GHz spacing";
  //            }
  //            enum "193.48750" {
  //              description "193.48750 THz/1549.42 nm 6.25/12.5GHz spacing";
  //            }
  //            enum "193.49375" {
  //              description "193.49375 THz/1549.37 nm 6.25GHz spacing";
  //            }
  //            enum "193.50000" {
  //              description "193.50000 THz/1549.32 nm 6.25/12.5/50/100GHz spacing";
  //            }
  //            enum "193.50625" {
  //              description "193.50625 THz/1549.26 nm 6.25GHz spacing";
  //            }
  //            enum "193.51250" {
  //              description "193.51250 THz/1549.21 nm 6.25/12.5GHz spacing";
  //            }
  //            enum "193.51875" {
  //              description "193.51875 THz/1549.16 nm 6.25GHz spacing";
  //            }
  //            enum "193.52500" {
  //              description "193.52500 THz/1549.11 nm 6.25/12.5GHz spacing";
  //            }
  //            enum "193.53125" {
  //              description "193.53125 THz/1549.06 nm 6.25GHz spacing";
  //            }
  //            enum "193.53750" {
  //              description "193.53750 THz/1549.01 nm 6.25/12.5GHz spacing";
  //            }
  //            enum "193.54375" {
  //              description "193.54375 THz/1548.96 nm 6.25GHz spacing";
  //            }
  //            enum "193.55000" {
  //              description "193.55000 THz/1548.91 nm 6.25/12.5/50/75GHz spacing";
  //            }
  //            enum "193.55625" {
  //              description "193.55625 THz/1548.86 nm 6.25GHz spacing";
  //            }
  //            enum "193.56250" {
  //              description "193.56250 THz/1548.81 nm 6.25/12.5GHz spacing";
  //            }
  //            enum "193.56875" {
  //              description "193.56875 THz/1548.76 nm 6.25GHz spacing";
  //            }
  //            enum "193.57500" {
  //              description "193.57500 THz/1548.71 nm 6.25/12.5GHz spacing";
  //            }
  //            enum "193.58125" {
  //              description "193.58125 THz/1548.66 nm 6.25GHz spacing";
  //            }
  //            enum "193.58750" {
  //              description "193.58750 THz/1548.61 nm 6.25/12.5GHz spacing";
  //            }
  //            enum "193.59375" {
  //              description "193.59375 THz/1548.56 nm 6.25GHz spacing";
  //            }
  //            enum "193.60000" {
  //              description "193.60000 THz/1548.51 nm 6.25/12.5/50/100GHz spacing";
  //            }
  //            enum "193.60625" {
  //              description "193.60625 THz/1548.46 nm 6.25GHz spacing";
  //            }
  //            enum "193.61250" {
  //              description "193.61250 THz/1548.41 nm 6.25/12.5GHz spacing";
  //            }
  //            enum "193.61875" {
  //              description "193.61875 THz/1548.36 nm 6.25GHz spacing";
  //            }
  //            enum "193.62500" {
  //              description "193.62500 THz/1548.31 nm 6.25/12.5/75GHz spacing";
  //            }
  //            enum "193.63125" {
  //              description "193.63125 THz/1548.26 nm 6.25GHz spacing";
  //            }
  //            enum "193.63750" {
  //              description "193.63750 THz/1548.21 nm 6.25/12.5GHz spacing";
  //            }
  //            enum "193.64375" {
  //              description "193.64375 THz/1548.16 nm 6.25GHz spacing";
  //            }
  //            enum "193.65000" {
  //              description "193.65000 THz/1548.11 nm 6.25/12.5/50GHz spacing";
  //            }
  //            enum "193.65625" {
  //              description "193.65625 THz/1548.06 nm 6.25GHz spacing";
  //            }
  //            enum "193.66250" {
  //              description "193.66250 THz/1548.02 nm 6.25/12.5GHz spacing";
  //            }
  //            enum "193.66875" {
  //              description "193.66875 THz/1547.97 nm 6.25GHz spacing";
  //            }
  //            enum "193.67500" {
  //              description "193.67500 THz/1547.92 nm 6.25/12.5GHz spacing";
  //            }
  //            enum "193.68125" {
  //              description "193.68125 THz/1547.87 nm 6.25GHz spacing";
  //            }
  //            enum "193.68750" {
  //              description "193.68750 THz/1547.82 nm 6.25/12.5GHz spacing";
  //            }
  //            enum "193.69375" {
  //              description "193.69375 THz/1547.77 nm 6.25GHz spacing";
  //            }
  //            enum "193.70000" {
  //              description "193.70000 THz/1547.72 nm 6.25/12.5/50/100/75GHz spacing";
  //            }
  //            enum "193.70625" {
  //              description "193.70625 THz/1547.67 nm 6.25GHz spacing";
  //            }
  //            enum "193.71250" {
  //              description "193.71250 THz/1547.62 nm 6.25/12.5GHz spacing";
  //            }
  //            enum "193.71875" {
  //              description "193.71875 THz/1547.57 nm 6.25GHz spacing";
  //            }
  //            enum "193.72500" {
  //              description "193.72500 THz/1547.52 nm 6.25/12.5GHz spacing";
  //            }
  //            enum "193.73125" {
  //              description "193.73125 THz/1547.47 nm 6.25GHz spacing";
  //            }
  //            enum "193.73750" {
  //              description "193.73750 THz/1547.42 nm 6.25/12.5GHz spacing";
  //            }
  //            enum "193.74375" {
  //              description "193.74375 THz/1547.37 nm 6.25GHz spacing";
  //            }
  //            enum "193.75000" {
  //              description "193.75000 THz/1547.32 nm 6.25/12.5/50GHz spacing";
  //            }
  //            enum "193.75625" {
  //              description "193.75625 THz/1547.27 nm 6.25GHz spacing";
  //            }
  //            enum "193.76250" {
  //              description "193.76250 THz/1547.22 nm 6.25/12.5GHz spacing";
  //            }
  //            enum "193.76875" {
  //              description "193.76875 THz/1547.17 nm 6.25GHz spacing";
  //            }
  //            enum "193.77500" {
  //              description "193.77500 THz/1547.12 nm 6.25/12.5/75GHz spacing";
  //            }
  //            enum "193.78125" {
  //              description "193.78125 THz/1547.07 nm 6.25GHz spacing";
  //            }
  //            enum "193.78750" {
  //              description "193.78750 THz/1547.02 nm 6.25/12.5GHz spacing";
  //            }
  //            enum "193.79375" {
  //              description "193.79375 THz/1546.97 nm 6.25GHz spacing";
  //            }
  //            enum "193.80000" {
  //              description "193.80000 THz/1546.92 nm 6.25/12.5/50/100GHz spacing";
  //            }
  //            enum "193.80625" {
  //              description "193.80625 THz/1546.87 nm 6.25GHz spacing";
  //            }
  //            enum "193.81250" {
  //              description "193.81250 THz/1546.82 nm 6.25/12.5GHz spacing";
  //            }
  //            enum "193.81875" {
  //              description "193.81875 THz/1546.77 nm 6.25GHz spacing";
  //            }
  //            enum "193.82500" {
  //              description "193.82500 THz/1546.72 nm 6.25/12.5GHz spacing";
  //            }
  //            enum "193.83125" {
  //              description "193.83125 THz/1546.67 nm 6.25GHz spacing";
  //            }
  //            enum "193.83750" {
  //              description "193.83750 THz/1546.62 nm 6.25/12.5GHz spacing";
  //            }
  //            enum "193.84375" {
  //              description "193.84375 THz/1546.57 nm 6.25GHz spacing";
  //            }
  //            enum "193.85000" {
  //              description "193.85000 THz/1546.52 nm 6.25/12.5/50/75GHz spacing";
  //            }
  //            enum "193.85625" {
  //              description "193.85625 THz/1546.47 nm 6.25GHz spacing";
  //            }
  //            enum "193.86250" {
  //              description "193.86250 THz/1546.42 nm 6.25/12.5GHz spacing";
  //            }
  //            enum "193.86875" {
  //              description "193.86875 THz/1546.37 nm 6.25GHz spacing";
  //            }
  //            enum "193.87500" {
  //              description "193.87500 THz/1546.32 nm 6.25/12.5GHz spacing";
  //            }
  //            enum "193.88125" {
  //              description "193.88125 THz/1546.27 nm 6.25GHz spacing";
  //            }
  //            enum "193.88750" {
  //              description "193.88750 THz/1546.22 nm 6.25/12.5GHz spacing";
  //            }
  //            enum "193.89375" {
  //              description "193.89375 THz/1546.17 nm 6.25GHz spacing";
  //            }
  //            enum "193.90000" {
  //              description "193.90000 THz/1546.12 nm 6.25/12.5/50/100GHz spacing";
  //            }
  //            enum "193.90625" {
  //              description "193.90625 THz/1546.07 nm 6.25GHz spacing";
  //            }
  //            enum "193.91250" {
  //              description "193.91250 THz/1546.02 nm 6.25/12.5GHz spacing";
  //            }
  //            enum "193.91875" {
  //              description "193.91875 THz/1545.97 nm 6.25GHz spacing";
  //            }
  //            enum "193.92500" {
  //              description "193.92500 THz/1545.92 nm 6.25/12.5/75GHz spacing";
  //            }
  //            enum "193.93125" {
  //              description "193.93125 THz/1545.87 nm 6.25GHz spacing";
  //            }
  //            enum "193.93750" {
  //              description "193.93750 THz/1545.82 nm 6.25/12.5GHz spacing";
  //            }
  //            enum "193.94375" {
  //              description "193.94375 THz/1545.77 nm 6.25GHz spacing";
  //            }
  //            enum "193.95000" {
  //              description "193.95000 THz/1545.72 nm 6.25/12.5/50GHz spacing";
  //            }
  //            enum "193.95625" {
  //              description "193.95625 THz/1545.67 nm 6.25GHz spacing";
  //            }
  //            enum "193.96250" {
  //              description "193.96250 THz/1545.62 nm 6.25/12.5GHz spacing";
  //            }
  //            enum "193.96875" {
  //              description "193.96875 THz/1545.57 nm 6.25GHz spacing";
  //            }
  //            enum "193.97500" {
  //              description "193.97500 THz/1545.52 nm 6.25/12.5GHz spacing";
  //            }
  //            enum "193.98125" {
  //              description "193.98125 THz/1545.47 nm 6.25GHz spacing";
  //            }
  //            enum "193.98750" {
  //              description "193.98750 THz/1545.42 nm 6.25/12.5GHz spacing";
  //            }
  //            enum "193.99375" {
  //              description "193.99375 THz/1545.37 nm 6.25GHz spacing";
  //            }
  //            enum "194.00000" {
  //              description "194.00000 THz/1545.32 nm 6.25/12.5/50/75/100GHz spacing";
  //            }
  //            enum "194.00625" {
  //              description "194.00625 THz/1545.27 nm 6.25GHz spacing";
  //            }
  //            enum "194.01250" {
  //              description "194.01250 THz/1545.22 nm 6.25/12.5GHz spacing";
  //            }
  //            enum "194.01875" {
  //              description "194.01875 THz/1545.17 nm 6.25GHz spacing";
  //            }
  //            enum "194.02500" {
  //              description "194.02500 THz/1545.12 nm 6.25/12.5GHz spacing";
  //            }
  //            enum "194.03125" {
  //              description "194.03125 THz/1545.07 nm 6.25GHz spacing";
  //            }
  //            enum "194.03750" {
  //              description "194.03750 THz/1545.02 nm 6.25/12.5GHz spacing";
  //            }
  //            enum "194.04375" {
  //              description "194.04375 THz/1544.97 nm 6.25GHz spacing";
  //            }
  //            enum "194.05000" {
  //              description "194.05000 THz/1544.92 nm 6.25/12.5/50GHz spacing";
  //            }
  //            enum "194.05625" {
  //              description "194.05625 THz/1544.87 nm 6.25GHz spacing";
  //            }
  //            enum "194.06250" {
  //              description "194.06250 THz/1544.82 nm 6.25/12.5GHz spacing";
  //            }
  //            enum "194.06875" {
  //              description "194.06875 THz/1544.77 nm 6.25GHz spacing";
  //            }
  //            enum "194.07500" {
  //              description "194.07500 THz/1544.72 nm 6.25/12.5/75GHz spacing";
  //            }
  //            enum "194.08125" {
  //              description "194.08125 THz/1544.68 nm 6.25GHz spacing";
  //            }
  //            enum "194.08750" {
  //              description "194.08750 THz/1544.63 nm 6.25/12.5GHz spacing";
  //            }
  //            enum "194.09375" {
  //              description "194.09375 THz/1544.58 nm 6.25GHz spacing";
  //            }
  //            enum "194.10000" {
  //              description "194.10000 THz/1544.53 nm 6.25/12.5/50/100GHz spacing";
  //            }
  //            enum "194.10625" {
  //              description "194.10625 THz/1544.48 nm 6.25GHz spacing";
  //            }
  //            enum "194.11250" {
  //              description "194.11250 THz/1544.43 nm 6.25/12.5GHz spacing";
  //            }
  //            enum "194.11875" {
  //              description "194.11875 THz/1544.38 nm 6.25GHz spacing";
  //            }
  //            enum "194.12500" {
  //              description "194.12500 THz/1544.33 nm 6.25/12.5GHz spacing";
  //            }
  //            enum "194.13125" {
  //              description "194.13125 THz/1544.28 nm 6.25GHz spacing";
  //            }
  //            enum "194.13750" {
  //              description "194.13750 THz/1544.23 nm 6.25/12.5GHz spacing";
  //            }
  //            enum "194.14375" {
  //              description "194.14375 THz/1544.18 nm 6.25GHz spacing";
  //            }
  //            enum "194.15000" {
  //              description "194.15000 THz/1544.13 nm 6.25/12.5/50/75GHz spacing";
  //            }
  //            enum "194.15625" {
  //              description "194.15625 THz/1544.08 nm 6.25GHz spacing";
  //            }
  //            enum "194.16250" {
  //              description "194.16250 THz/1544.03 nm 6.25/12.5GHz spacing";
  //            }
  //            enum "194.16875" {
  //              description "194.16875 THz/1543.98 nm 6.25GHz spacing";
  //            }
  //            enum "194.17500" {
  //              description "194.17500 THz/1543.93 nm 6.25/12.5GHz spacing";
  //            }
  //            enum "194.18125" {
  //              description "194.18125 THz/1543.88 nm 6.25GHz spacing";
  //            }
  //            enum "194.18750" {
  //              description "194.18750 THz/1543.83 nm 6.25/12.5GHz spacing";
  //            }
  //            enum "194.19375" {
  //              description "194.19375 THz/1543.78 nm 6.25GHz spacing";
  //            }
  //            enum "194.20000" {
  //              description "194.20000 THz/1543.73 nm 6.25/12.5/50/100GHz spacing";
  //            }
  //            enum "194.20625" {
  //              description "194.20625 THz/1543.68 nm 6.25GHz spacing";
  //            }
  //            enum "194.21250" {
  //              description "194.21250 THz/1543.63 nm 6.25/12.5GHz spacing";
  //            }
  //            enum "194.21875" {
  //              description "194.21875 THz/1543.58 nm 6.25GHz spacing";
  //            }
  //            enum "194.22500" {
  //              description "194.22500 THz/1543.53 nm 6.25/12.5/75GHz spacing";
  //            }
  //            enum "194.23125" {
  //              description "194.23125 THz/1543.48 nm 6.25GHz spacing";
  //            }
  //            enum "194.23750" {
  //              description "194.23750 THz/1543.43 nm 6.25/12.5GHz spacing";
  //            }
  //            enum "194.24375" {
  //              description "194.24375 THz/1543.38 nm 6.25GHz spacing";
  //            }
  //            enum "194.25000" {
  //              description "194.25000 THz/1543.33 nm 6.25/12.5/50/75GHz spacing";
  //            }
  //            enum "194.25625" {
  //              description "194.25625 THz/1543.28 nm 6.25GHz spacing";
  //            }
  //            enum "194.26250" {
  //              description "194.26250 THz/1543.23 nm 6.25/12.5GHz spacing";
  //            }
  //            enum "194.26875" {
  //              description "194.26875 THz/1543.18 nm 6.25GHz spacing";
  //            }
  //            enum "194.27500" {
  //              description "194.27500 THz/1543.13 nm 6.25/12.5GHz spacing";
  //            }
  //            enum "194.28125" {
  //              description "194.28125 THz/1543.08 nm 6.25GHz spacing";
  //            }
  //            enum "194.28750" {
  //              description "194.28750 THz/1543.04 nm 6.25/12.5GHz spacing";
  //            }
  //            enum "194.29375" {
  //              description "194.29375 THz/1542.99 nm 6.25GHz spacing";
  //            }
  //            enum "194.30000" {
  //              description "194.30000 THz/1542.94 nm 6.25/12.5/50/75/100GHz spacing";
  //            }
  //            enum "194.30625" {
  //              description "194.30625 THz/1542.89 nm 6.25GHz spacing";
  //            }
  //            enum "194.31250" {
  //              description "194.31250 THz/1542.84 nm 6.25/12.5GHz spacing";
  //            }
  //            enum "194.31875" {
  //              description "194.31875 THz/1542.79 nm 6.25GHz spacing";
  //            }
  //            enum "194.32500" {
  //              description "194.32500 THz/1542.74 nm 6.25/12.5GHz spacing";
  //            }
  //            enum "194.33125" {
  //              description "194.33125 THz/1542.69 nm 6.25GHz spacing";
  //            }
  //            enum "194.33750" {
  //              description "194.33750 THz/1542.64 nm 6.25/12.5GHz spacing";
  //            }
  //            enum "194.34375" {
  //              description "194.34375 THz/1542.59 nm 6.25GHz spacing";
  //            }
  //            enum "194.35000" {
  //              description "194.35000 THz/1542.54 nm 6.25/12.5/50GHz spacing";
  //            }
  //            enum "194.35625" {
  //              description "194.35625 THz/1542.49 nm 6.25GHz spacing";
  //            }
  //            enum "194.36250" {
  //              description "194.36250 THz/1542.44 nm 6.25/12.5GHz spacing";
  //            }
  //            enum "194.36875" {
  //              description "194.36875 THz/1542.39 nm 6.25GHz spacing";
  //            }
  //            enum "194.37500" {
  //              description "194.37500 THz/1542.34 nm 6.25/12.5/75GHz spacing";
  //            }
  //            enum "194.38125" {
  //              description "194.38125 THz/1542.29 nm 6.25GHz spacing";
  //            }
  //            enum "194.38750" {
  //              description "194.38750 THz/1542.24 nm 6.25/12.5GHz spacing";
  //            }
  //            enum "194.39375" {
  //              description "194.39375 THz/1542.19 nm 6.25GHz spacing";
  //            }
  //            enum "194.40000" {
  //              description "194.40000 THz/1542.14 nm 6.25/12.5/50/100GHz spacing";
  //            }
  //            enum "194.40625" {
  //              description "194.40625 THz/1542.09 nm 6.25GHz spacing";
  //            }
  //            enum "194.41250" {
  //              description "194.41250 THz/1542.04 nm 6.25/12.5GHz spacing";
  //            }
  //            enum "194.41875" {
  //              description "194.41875 THz/1541.99 nm 6.25GHz spacing";
  //            }
  //            enum "194.42500" {
  //              description "194.42500 THz/1541.94 nm 6.25/12.5GHz spacing";
  //            }
  //            enum "194.43125" {
  //              description "194.43125 THz/1541.89 nm 6.25GHz spacing";
  //            }
  //            enum "194.43750" {
  //              description "194.43750 THz/1541.84 nm 6.25/12.5GHz spacing";
  //            }
  //            enum "194.44375" {
  //              description "194.44375 THz/1541.80 nm 6.25GHz spacing";
  //            }
  //            enum "194.45000" {
  //              description "194.45000 THz/1541.75 nm 6.25/12.5/50/75GHz spacing";
  //            }
  //            enum "194.45625" {
  //              description "194.45625 THz/1541.70 nm 6.25GHz spacing";
  //            }
  //            enum "194.46250" {
  //              description "194.46250 THz/1541.65 nm 6.25/12.5GHz spacing";
  //            }
  //            enum "194.46875" {
  //              description "194.46875 THz/1541.60 nm 6.25GHz spacing";
  //            }
  //            enum "194.47500" {
  //              description "194.47500 THz/1541.55 nm 6.25/12.5GHz spacing";
  //            }
  //            enum "194.48125" {
  //              description "194.48125 THz/1541.50 nm 6.25GHz spacing";
  //            }
  //            enum "194.48750" {
  //              description "194.48750 THz/1541.45 nm 6.25/12.5GHz spacing";
  //            }
  //            enum "194.49375" {
  //              description "194.49375 THz/1541.40 nm 6.25GHz spacing";
  //            }
  //            enum "194.50000" {
  //              description "194.50000 THz/1541.35 nm 6.25/12.5/50/100GHz spacing";
  //            }
  //            enum "194.50625" {
  //              description "194.50625 THz/1541.30 nm 6.25GHz spacing";
  //            }
  //            enum "194.51250" {
  //              description "194.51250 THz/1541.25 nm 6.25/12.5GHz spacing";
  //            }
  //            enum "194.51875" {
  //              description "194.51875 THz/1541.20 nm 6.25GHz spacing";
  //            }
  //            enum "194.52500" {
  //              description "194.52500 THz/1541.15 nm 6.25/12.5/75GHz spacing";
  //            }
  //            enum "194.53125" {
  //              description "194.53125 THz/1541.10 nm 6.25GHz spacing";
  //            }
  //            enum "194.53750" {
  //              description "194.53750 THz/1541.05 nm 6.25/12.5GHz spacing";
  //            }
  //            enum "194.54375" {
  //              description "194.54375 THz/1541.00 nm 6.25GHz spacing";
  //            }
  //            enum "194.55000" {
  //              description "194.55000 THz/1540.95 nm 6.25/12.5/50GHz spacing";
  //            }
  //            enum "194.55625" {
  //              description "194.55625 THz/1540.90 nm 6.25GHz spacing";
  //            }
  //            enum "194.56250" {
  //              description "194.56250 THz/1540.85 nm 6.25/12.5GHz spacing";
  //            }
  //            enum "194.56875" {
  //              description "194.56875 THz/1540.80 nm 6.25GHz spacing";
  //            }
  //            enum "194.57500" {
  //              description "194.57500 THz/1540.76 nm 6.25/12.5GHz spacing";
  //            }
  //            enum "194.58125" {
  //              description "194.58125 THz/1540.71 nm 6.25GHz spacing";
  //            }
  //            enum "194.58750" {
  //              description "194.58750 THz/1540.66 nm 6.25/12.5GHz spacing";
  //            }
  //            enum "194.59375" {
  //              description "194.59375 THz/1540.61 nm 6.25GHz spacing";
  //            }
  //            enum "194.60000" {
  //              description "194.60000 THz/1540.56 nm 6.25/12.5/50/75/100GHz spacing";
  //            }
  //            enum "194.60625" {
  //              description "194.60625 THz/1540.51 nm 6.25GHz spacing";
  //            }
  //            enum "194.61250" {
  //              description "194.61250 THz/1540.46 nm 6.25/12.5GHz spacing";
  //            }
  //            enum "194.61875" {
  //              description "194.61875 THz/1540.41 nm 6.25GHz spacing";
  //            }
  //            enum "194.62500" {
  //              description "194.62500 THz/1540.36 nm 6.25/12.5GHz spacing";
  //            }
  //            enum "194.63125" {
  //              description "194.63125 THz/1540.31 nm 6.25GHz spacing";
  //            }
  //            enum "194.63750" {
  //              description "194.63750 THz/1540.26 nm 6.25/12.5GHz spacing";
  //            }
  //            enum "194.64375" {
  //              description "194.64375 THz/1540.21 nm 6.25GHz spacing";
  //            }
  //            enum "194.65000" {
  //              description "194.65000 THz/1540.16 nm 6.25/12.5/50GHz spacing";
  //            }
  //            enum "194.65625" {
  //              description "194.65625 THz/1540.11 nm 6.25GHz spacing";
  //            }
  //            enum "194.66250" {
  //              description "194.66250 THz/1540.06 nm 6.25/12.5GHz spacing";
  //            }
  //            enum "194.66875" {
  //              description "194.66875 THz/1540.01 nm 6.25GHz spacing";
  //            }
  //            enum "194.67500" {
  //              description "194.67500 THz/1539.96 nm 6.25/12.5/75GHz spacing";
  //            }
  //            enum "194.68125" {
  //              description "194.68125 THz/1539.91 nm 6.25GHz spacing";
  //            }
  //            enum "194.68750" {
  //              description "194.68750 THz/1539.86 nm 6.25/12.5GHz spacing";
  //            }
  //            enum "194.69375" {
  //              description "194.69375 THz/1539.82 nm 6.25GHz spacing";
  //            }
  //            enum "194.70000" {
  //              description "194.70000 THz/1539.77 nm 6.25/12.5/50/100GHz spacing";
  //            }
  //            enum "194.70625" {
  //              description "194.70625 THz/1539.72 nm 6.25GHz spacing";
  //            }
  //            enum "194.71250" {
  //              description "194.71250 THz/1539.67 nm 6.25/12.5GHz spacing";
  //            }
  //            enum "194.71875" {
  //              description "194.71875 THz/1539.62 nm 6.25GHz spacing";
  //            }
  //            enum "194.72500" {
  //              description "194.72500 THz/1539.57 nm 6.25/12.5GHz spacing";
  //            }
  //            enum "194.73125" {
  //              description "194.73125 THz/1539.52 nm 6.25GHz spacing";
  //            }
  //            enum "194.73750" {
  //              description "194.73750 THz/1539.47 nm 6.25/12.5GHz spacing";
  //            }
  //            enum "194.74375" {
  //              description "194.74375 THz/1539.42 nm 6.25GHz spacing";
  //            }
  //            enum "194.75000" {
  //              description "194.75000 THz/1539.37 nm 6.25/12.5/50/75GHz spacing";
  //            }
  //            enum "194.75625" {
  //              description "194.75625 THz/1539.32 nm 6.25GHz spacing";
  //            }
  //            enum "194.76250" {
  //              description "194.76250 THz/1539.27 nm 6.25/12.5GHz spacing";
  //            }
  //            enum "194.76875" {
  //              description "194.76875 THz/1539.22 nm 6.25GHz spacing";
  //            }
  //            enum "194.77500" {
  //              description "194.77500 THz/1539.17 nm 6.25/12.5GHz spacing";
  //            }
  //            enum "194.78125" {
  //              description "194.78125 THz/1539.12 nm 6.25GHz spacing";
  //            }
  //            enum "194.78750" {
  //              description "194.78750 THz/1539.07 nm 6.25/12.5GHz spacing";
  //            }
  //            enum "194.79375" {
  //              description "194.79375 THz/1539.03 nm 6.25GHz spacing";
  //            }
  //            enum "194.80000" {
  //              description "194.80000 THz/1538.98 nm 6.25/12.5/50/100GHz spacing";
  //            }
  //            enum "194.80625" {
  //              description "194.80625 THz/1538.93 nm 6.25GHz spacing";
  //            }
  //            enum "194.81250" {
  //              description "194.81250 THz/1538.88 nm 6.25/12.5GHz spacing";
  //            }
  //            enum "194.81875" {
  //              description "194.81875 THz/1538.83 nm 6.25GHz spacing";
  //            }
  //            enum "194.82500" {
  //              description "194.82500 THz/1538.78 nm 6.25/12.5/75GHz spacing";
  //            }
  //            enum "194.83125" {
  //              description "194.83125 THz/1538.73 nm 6.25GHz spacing";
  //            }
  //            enum "194.83750" {
  //              description "194.83750 THz/1538.68 nm 6.25/12.5GHz spacing";
  //            }
  //            enum "194.84375" {
  //              description "194.84375 THz/1538.63 nm 6.25GHz spacing";
  //            }
  //            enum "194.85000" {
  //              description "194.85000 THz/1538.58 nm 6.25/12.5/50GHz spacing";
  //            }
  //            enum "194.85625" {
  //              description "194.85625 THz/1538.53 nm 6.25GHz spacing";
  //            }
  //            enum "194.86250" {
  //              description "194.86250 THz/1538.48 nm 6.25/12.5GHz spacing";
  //            }
  //            enum "194.86875" {
  //              description "194.86875 THz/1538.43 nm 6.25GHz spacing";
  //            }
  //            enum "194.87500" {
  //              description "194.87500 THz/1538.38 nm 6.25/12.5GHz spacing";
  //            }
  //            enum "194.88125" {
  //              description "194.88125 THz/1538.33 nm 6.25GHz spacing";
  //            }
  //            enum "194.88750" {
  //              description "194.88750 THz/1538.28 nm 6.25/12.5GHz spacing";
  //            }
  //            enum "194.89375" {
  //              description "194.89375 THz/1538.24 nm 6.25GHz spacing";
  //            }
  //            enum "194.90000" {
  //              description "194.90000 THz/1538.19 nm 6.25/12.5/50/75/100GHz spacing";
  //            }
  //            enum "194.90625" {
  //              description "194.90625 THz/1538.14 nm 6.25GHz spacing";
  //            }
  //            enum "194.91250" {
  //              description "194.91250 THz/1538.09 nm 6.25/12.5GHz spacing";
  //            }
  //            enum "194.91875" {
  //              description "194.91875 THz/1538.04 nm 6.25GHz spacing";
  //            }
  //            enum "194.92500" {
  //              description "194.92500 THz/1537.99 nm 6.25/12.5GHz spacing";
  //            }
  //            enum "194.93125" {
  //              description "194.93125 THz/1537.94 nm 6.25GHz spacing";
  //            }
  //            enum "194.93750" {
  //              description "194.93750 THz/1537.89 nm 6.25/12.5GHz spacing";
  //            }
  //            enum "194.94375" {
  //              description "194.94375 THz/1537.84 nm 6.25GHz spacing";
  //            }
  //            enum "194.95000" {
  //              description "194.95000 THz/1537.79 nm 6.25/12.5/50GHz spacing";
  //            }
  //            enum "194.95625" {
  //              description "194.95625 THz/1537.74 nm 6.25GHz spacing";
  //            }
  //            enum "194.96250" {
  //              description "194.96250 THz/1537.69 nm 6.25/12.5GHz spacing";
  //            }
  //            enum "194.96875" {
  //              description "194.96875 THz/1537.64 nm 6.25GHz spacing";
  //            }
  //            enum "194.97500" {
  //              description "194.97500 THz/1537.59 nm 6.25/12.5/75GHz spacing";
  //            }
  //            enum "194.98125" {
  //              description "194.98125 THz/1537.55 nm 6.25GHz spacing";
  //            }
  //            enum "194.98750" {
  //              description "194.98750 THz/1537.50 nm 6.25/12.5GHz spacing";
  //            }
  //            enum "194.99375" {
  //              description "194.99375 THz/1537.45 nm 6.25GHz spacing";
  //            }
  //            enum "195.00000" {
  //              description "195.00000 THz/1537.40 nm 6.25/12.5/50/100GHz spacing";
  //            }
  //            enum "195.00625" {
  //              description "195.00625 THz/1537.35 nm 6.25GHz spacing";
  //            }
  //            enum "195.01250" {
  //              description "195.01250 THz/1537.30 nm 6.25/12.5GHz spacing";
  //            }
  //            enum "195.01875" {
  //              description "195.01875 THz/1537.25 nm 6.25GHz spacing";
  //            }
  //            enum "195.02500" {
  //              description "195.02500 THz/1537.20 nm 6.25/12.5GHz spacing";
  //            }
  //            enum "195.03125" {
  //              description "195.03125 THz/1537.15 nm 6.25GHz spacing";
  //            }
  //            enum "195.03750" {
  //              description "195.03750 THz/1537.10 nm 6.25/12.5GHz spacing";
  //            }
  //            enum "195.04375" {
  //              description "195.04375 THz/1537.05 nm 6.25GHz spacing";
  //            }
  //            enum "195.05000" {
  //              description "195.05000 THz/1537.00 nm 6.25/12.5/50/75GHz spacing";
  //            }
  //            enum "195.05625" {
  //              description "195.05625 THz/1536.95 nm 6.25GHz spacing";
  //            }
  //            enum "195.06250" {
  //              description "195.06250 THz/1536.90 nm 6.25/12.5GHz spacing";
  //            }
  //            enum "195.06875" {
  //              description "195.06875 THz/1536.86 nm 6.25GHz spacing";
  //            }
  //            enum "195.07500" {
  //              description "195.07500 THz/1536.81 nm 6.25/12.5GHz spacing";
  //            }
  //            enum "195.08125" {
  //              description "195.08125 THz/1536.76 nm 6.25GHz spacing";
  //            }
  //            enum "195.08750" {
  //              description "195.08750 THz/1536.71 nm 6.25/12.5GHz spacing";
  //            }
  //            enum "195.09375" {
  //              description "195.09375 THz/1536.66 nm 6.25GHz spacing";
  //            }
  //            enum "195.10000" {
  //              description "195.10000 THz/1536.61 nm 6.25/12.5/50/100GHz spacing";
  //            }
  //            enum "195.10625" {
  //              description "195.10625 THz/1536.56 nm 6.25GHz spacing";
  //            }
  //            enum "195.11250" {
  //              description "195.11250 THz/1536.51 nm 6.25/12.5GHz spacing";
  //            }
  //            enum "195.11875" {
  //              description "195.11875 THz/1536.46 nm 6.25GHz spacing";
  //            }
  //            enum "195.12500" {
  //              description "195.12500 THz/1536.41 nm 6.25/12.5/75GHz spacing";
  //            }
  //            enum "195.13125" {
  //              description "195.13125 THz/1536.36 nm 6.25GHz spacing";
  //            }
  //            enum "195.13750" {
  //              description "195.13750 THz/1536.31 nm 6.25/12.5GHz spacing";
  //            }
  //            enum "195.14375" {
  //              description "195.14375 THz/1536.26 nm 6.25GHz spacing";
  //            }
  //            enum "195.15000" {
  //              description "195.15000 THz/1536.22 nm 6.25/12.5/50GHz spacing";
  //            }
  //            enum "195.15625" {
  //              description "195.15625 THz/1536.17 nm 6.25GHz spacing";
  //            }
  //            enum "195.16250" {
  //              description "195.16250 THz/1536.12 nm 6.25/12.5GHz spacing";
  //            }
  //            enum "195.16875" {
  //              description "195.16875 THz/1536.07 nm 6.25GHz spacing";
  //            }
  //            enum "195.17500" {
  //              description "195.17500 THz/1536.02 nm 6.25/12.5GHz spacing";
  //            }
  //            enum "195.18125" {
  //              description "195.18125 THz/1535.97 nm 6.25GHz spacing";
  //            }
  //            enum "195.18750" {
  //              description "195.18750 THz/1535.92 nm 6.25/12.5GHz spacing";
  //            }
  //            enum "195.19375" {
  //              description "195.19375 THz/1535.87 nm 6.25GHz spacing";
  //            }
  //            enum "195.20000" {
  //              description "195.20000 THz/1535.82 nm 6.25/12.5/50/75/100GHz spacing";
  //            }
  //            enum "195.20625" {
  //              description "195.20625 THz/1535.77 nm 6.25GHz spacing";
  //            }
  //            enum "195.21250" {
  //              description "195.21250 THz/1535.72 nm 6.25/12.5GHz spacing";
  //            }
  //            enum "195.21875" {
  //              description "195.21875 THz/1535.67 nm 6.25GHz spacing";
  //            }
  //            enum "195.22500" {
  //              description "195.22500 THz/1535.63 nm 6.25/12.5GHz spacing";
  //            }
  //            enum "195.23125" {
  //              description "195.23125 THz/1535.58 nm 6.25GHz spacing";
  //            }
  //            enum "195.23750" {
  //              description "195.23750 THz/1535.53 nm 6.25/12.5GHz spacing";
  //            }
  //            enum "195.24375" {
  //              description "195.24375 THz/1535.48 nm 6.25GHz spacing";
  //            }
  //            enum "195.25000" {
  //              description "195.25000 THz/1535.43 nm 6.25/12.5/50GHz spacing";
  //            }
  //            enum "195.25625" {
  //              description "195.25625 THz/1535.38 nm 6.25GHz spacing";
  //            }
  //            enum "195.26250" {
  //              description "195.26250 THz/1535.33 nm 6.25/12.5GHz spacing";
  //            }
  //            enum "195.26875" {
  //              description "195.26875 THz/1535.28 nm 6.25GHz spacing";
  //            }
  //            enum "195.27500" {
  //              description "195.27500 THz/1535.23 nm 6.25/12.5/75GHz spacing";
  //            }
  //            enum "195.28125" {
  //              description "195.28125 THz/1535.18 nm 6.25GHz spacing";
  //            }
  //            enum "195.28750" {
  //              description "195.28750 THz/1535.13 nm 6.25/12.5GHz spacing";
  //            }
  //            enum "195.29375" {
  //              description "195.29375 THz/1535.08 nm 6.25GHz spacing";
  //            }
  //            enum "195.30000" {
  //              description "195.30000 THz/1535.04 nm 6.25/12.5/50/100GHz spacing";
  //            }
  //            enum "195.30625" {
  //              description "195.30625 THz/1534.99 nm 6.25GHz spacing";
  //            }
  //            enum "195.31250" {
  //              description "195.31250 THz/1534.94 nm 6.25/12.5GHz spacing";
  //            }
  //            enum "195.31875" {
  //              description "195.31875 THz/1534.89 nm 6.25GHz spacing";
  //            }
  //            enum "195.32500" {
  //              description "195.32500 THz/1534.84 nm 6.25/12.5GHz spacing";
  //            }
  //            enum "195.33125" {
  //              description "195.33125 THz/1534.79 nm 6.25GHz spacing";
  //            }
  //            enum "195.33750" {
  //              description "195.33750 THz/1534.74 nm 6.25/12.5GHz spacing";
  //            }
  //            enum "195.34375" {
  //              description "195.34375 THz/1534.69 nm 6.25GHz spacing";
  //            }
  //            enum "195.35000" {
  //              description "195.35000 THz/1534.64 nm 6.25/12.5/50/75GHz spacing";
  //            }
  //            enum "195.35625" {
  //              description "195.35625 THz/1534.59 nm 6.25GHz spacing";
  //            }
  //            enum "195.36250" {
  //              description "195.36250 THz/1534.54 nm 6.25/12.5GHz spacing";
  //            }
  //            enum "195.36875" {
  //              description "195.36875 THz/1534.50 nm 6.25GHz spacing";
  //            }
  //            enum "195.37500" {
  //              description "195.37500 THz/1534.45 nm 6.25/12.5GHz spacing";
  //            }
  //            enum "195.38125" {
  //              description "195.38125 THz/1534.40 nm 6.25GHz spacing";
  //            }
  //            enum "195.38750" {
  //              description "195.38750 THz/1534.35 nm 6.25/12.5GHz spacing";
  //            }
  //            enum "195.39375" {
  //              description "195.39375 THz/1534.30 nm 6.25GHz spacing";
  //            }
  //            enum "195.40000" {
  //              description "195.40000 THz/1534.25 nm 6.25/12.5/50/100GHz spacing";
  //            }
  //            enum "195.40625" {
  //              description "195.40625 THz/1534.20 nm 6.25GHz spacing";
  //            }
  //            enum "195.41250" {
  //              description "195.41250 THz/1534.15 nm 6.25/12.5GHz spacing";
  //            }
  //            enum "195.41875" {
  //              description "195.41875 THz/1534.10 nm 6.25GHz spacing";
  //            }
  //            enum "195.42500" {
  //              description "195.42500 THz/1534.05 nm 6.25/12.5/75GHz spacing";
  //            }
  //            enum "195.43125" {
  //              description "195.43125 THz/1534.00 nm 6.25GHz spacing";
  //            }
  //            enum "195.43750" {
  //              description "195.43750 THz/1533.96 nm 6.25/12.5GHz spacing";
  //            }
  //            enum "195.44375" {
  //              description "195.44375 THz/1533.91 nm 6.25GHz spacing";
  //            }
  //            enum "195.45000" {
  //              description "195.45000 THz/1533.86 nm 6.25/12.5/50GHz spacing";
  //            }
  //            enum "195.45625" {
  //              description "195.45625 THz/1533.81 nm 6.25GHz spacing";
  //            }
  //            enum "195.46250" {
  //              description "195.46250 THz/1533.76 nm 6.25/12.5GHz spacing";
  //            }
  //            enum "195.46875" {
  //              description "195.46875 THz/1533.71 nm 6.25GHz spacing";
  //            }
  //            enum "195.47500" {
  //              description "195.47500 THz/1533.66 nm 6.25/12.5GHz spacing";
  //            }
  //            enum "195.48125" {
  //              description "195.48125 THz/1533.61 nm 6.25GHz spacing";
  //            }
  //            enum "195.48750" {
  //              description "195.48750 THz/1533.56 nm 6.25/12.5GHz spacing";
  //            }
  //            enum "195.49375" {
  //              description "195.49375 THz/1533.51 nm 6.25GHz spacing";
  //            }
  //            enum "195.50000" {
  //              description "195.50000 THz/1533.47 nm 6.25/12.5/50/75/100GHz spacing";
  //            }
  //            enum "195.50625" {
  //              description "195.50625 THz/1533.42 nm 6.25GHz spacing";
  //            }
  //            enum "195.51250" {
  //              description "195.51250 THz/1533.37 nm 6.25/12.5GHz spacing";
  //            }
  //            enum "195.51875" {
  //              description "195.51875 THz/1533.32 nm 6.25GHz spacing";
  //            }
  //            enum "195.52500" {
  //              description "195.52500 THz/1533.27 nm 6.25/12.5GHz spacing";
  //            }
  //            enum "195.53125" {
  //              description "195.53125 THz/1533.22 nm 6.25GHz spacing";
  //            }
  //            enum "195.53750" {
  //              description "195.53750 THz/1533.17 nm 6.25/12.5GHz spacing";
  //            }
  //            enum "195.54375" {
  //              description "195.54375 THz/1533.12 nm 6.25GHz spacing";
  //            }
  //            enum "195.55000" {
  //              description "195.55000 THz/1533.07 nm 6.25/12.5/50GHz spacing";
  //            }
  //            enum "195.55625" {
  //              description "195.55625 THz/1533.02 nm 6.25GHz spacing";
  //            }
  //            enum "195.56250" {
  //              description "195.56250 THz/1532.98 nm 6.25/12.5GHz spacing";
  //            }
  //            enum "195.56875" {
  //              description "195.56875 THz/1532.93 nm 6.25GHz spacing";
  //            }
  //            enum "195.57500" {
  //              description "195.57500 THz/1532.88 nm 6.25/12.5/75GHz spacing";
  //            }
  //            enum "195.58125" {
  //              description "195.58125 THz/1532.83 nm 6.25GHz spacing";
  //            }
  //            enum "195.58750" {
  //              description "195.58750 THz/1532.78 nm 6.25/12.5GHz spacing";
  //            }
  //            enum "195.59375" {
  //              description "195.59375 THz/1532.73 nm 6.25GHz spacing";
  //            }
  //            enum "195.60000" {
  //              description "195.60000 THz/1532.68 nm 6.25/12.5/50/100GHz spacing";
  //            }
  //            enum "195.60625" {
  //              description "195.60625 THz/1532.63 nm 6.25GHz spacing";
  //            }
  //            enum "195.61250" {
  //              description "195.61250 THz/1532.58 nm 6.25/12.5GHz spacing";
  //            }
  //            enum "195.61875" {
  //              description "195.61875 THz/1532.53 nm 6.25GHz spacing";
  //            }
  //            enum "195.62500" {
  //              description "195.62500 THz/1532.49 nm 6.25/12.5GHz spacing";
  //            }
  //            enum "195.63125" {
  //              description "195.63125 THz/1532.44 nm 6.25GHz spacing";
  //            }
  //            enum "195.63750" {
  //              description "195.63750 THz/1532.39 nm 6.25/12.5GHz spacing";
  //            }
  //            enum "195.64375" {
  //              description "195.64375 THz/1532.34 nm 6.25GHz spacing";
  //            }
  //            enum "195.65000" {
  //              description "195.65000 THz/1532.29 nm 6.25/12.5/50/75GHz spacing";
  //            }
  //            enum "195.65625" {
  //              description "195.65625 THz/1532.24 nm 6.25GHz spacing";
  //            }
  //            enum "195.66250" {
  //              description "195.66250 THz/1532.19 nm 6.25/12.5GHz spacing";
  //            }
  //            enum "195.66875" {
  //              description "195.66875 THz/1532.14 nm 6.25GHz spacing";
  //            }
  //            enum "195.67500" {
  //              description "195.67500 THz/1532.09 nm 6.25/12.5GHz spacing";
  //            }
  //            enum "195.68125" {
  //              description "195.68125 THz/1532.04 nm 6.25GHz spacing";
  //            }
  //            enum "195.68750" {
  //              description "195.68750 THz/1532.00 nm 6.25/12.5GHz spacing";
  //            }
  //            enum "195.69375" {
  //              description "195.69375 THz/1531.95 nm 6.25GHz spacing";
  //            }
  //            enum "195.70000" {
  //              description "195.70000 THz/1531.90 nm 6.25/12.5/50/100GHz spacing";
  //            }
  //            enum "195.70625" {
  //              description "195.70625 THz/1531.85 nm 6.25GHz spacing";
  //            }
  //            enum "195.71250" {
  //              description "195.71250 THz/1531.80 nm 6.25/12.5GHz spacing";
  //            }
  //            enum "195.71875" {
  //              description "195.71875 THz/1531.75 nm 6.25GHz spacing";
  //            }
  //            enum "195.72500" {
  //              description "195.72500 THz/1531.70 nm 6.25/12.5/75GHz spacing";
  //            }
  //            enum "195.73125" {
  //              description "195.73125 THz/1531.65 nm 6.25GHz spacing";
  //            }
  //            enum "195.73750" {
  //              description "195.73750 THz/1531.60 nm 6.25/12.5GHz spacing";
  //            }
  //            enum "195.74375" {
  //              description "195.74375 THz/1531.56 nm 6.25GHz spacing";
  //            }
  //            enum "195.75000" {
  //              description "195.75000 THz/1531.51 nm 6.25/12.5/50GHz spacing";
  //            }
  //            enum "195.75625" {
  //              description "195.75625 THz/1531.46 nm 6.25GHz spacing";
  //            }
  //            enum "195.76250" {
  //              description "195.76250 THz/1531.41 nm 6.25/12.5GHz spacing";
  //            }
  //            enum "195.76875" {
  //              description "195.76875 THz/1531.36 nm 6.25GHz spacing";
  //            }
  //            enum "195.77500" {
  //              description "195.77500 THz/1531.31 nm 6.25/12.5GHz spacing";
  //            }
  //            enum "195.78125" {
  //              description "195.78125 THz/1531.26 nm 6.25GHz spacing";
  //            }
  //            enum "195.78750" {
  //              description "195.78750 THz/1531.21 nm 6.25/12.5GHz spacing";
  //            }
  //            enum "195.79375" {
  //              description "195.79375 THz/1531.16 nm 6.25GHz spacing";
  //            }
  //            enum "195.80000" {
  //              description "195.80000 THz/1531.12 nm 6.25/12.5/50/75/100GHz spacing";
  //            }
  //            enum "195.80625" {
  //              description "195.80625 THz/1531.07 nm 6.25GHz spacing";
  //            }
  //            enum "195.81250" {
  //              description "195.81250 THz/1531.02 nm 6.25/12.5GHz spacing";
  //            }
  //            enum "195.81875" {
  //              description "195.81875 THz/1530.97 nm 6.25GHz spacing";
  //            }
  //            enum "195.82500" {
  //              description "195.82500 THz/1530.92 nm 6.25/12.5GHz spacing";
  //            }
  //            enum "195.83125" {
  //              description "195.83125 THz/1530.87 nm 6.25GHz spacing";
  //            }
  //            enum "195.83750" {
  //              description "195.83750 THz/1530.82 nm 6.25/12.5GHz spacing";
  //            }
  //            enum "195.84375" {
  //              description "195.84375 THz/1530.77 nm 6.25GHz spacing";
  //            }
  //            enum "195.85000" {
  //              description "195.85000 THz/1530.72 nm 6.25/12.5/50GHz spacing";
  //            }
  //            enum "195.85625" {
  //              description "195.85625 THz/1530.68 nm 6.25GHz spacing";
  //            }
  //            enum "195.86250" {
  //              description "195.86250 THz/1530.63 nm 6.25/12.5GHz spacing";
  //            }
  //            enum "195.86875" {
  //              description "195.86875 THz/1530.58 nm 6.25GHz spacing";
  //            }
  //            enum "195.87500" {
  //              description "195.87500 THz/1530.53 nm 6.25/12.5/75GHz spacing";
  //            }
  //            enum "195.88125" {
  //              description "195.88125 THz/1530.48 nm 6.25GHz spacing";
  //            }
  //            enum "195.88750" {
  //              description "195.88750 THz/1530.43 nm 6.25/12.5GHz spacing";
  //            }
  //            enum "195.89375" {
  //              description "195.89375 THz/1530.38 nm 6.25GHz spacing";
  //            }
  //            enum "195.90000" {
  //              description "195.90000 THz/1530.33 nm 6.25/12.5/50/100GHz spacing";
  //            }
  //            enum "195.90625" {
  //              description "195.90625 THz/1530.29 nm 6.25GHz spacing";
  //            }
  //            enum "195.91250" {
  //              description "195.91250 THz/1530.24 nm 6.25/12.5GHz spacing";
  //            }
  //            enum "195.91875" {
  //              description "195.91875 THz/1530.19 nm 6.25GHz spacing";
  //            }
  //            enum "195.92500" {
  //              description "195.92500 THz/1530.14 nm 6.25/12.5GHz spacing";
  //            }
  //            enum "195.93125" {
  //              description "195.93125 THz/1530.09 nm 6.25GHz spacing";
  //            }
  //            enum "195.93750" {
  //              description "195.93750 THz/1530.04 nm 6.25/12.5GHz spacing";
  //            }
  //            enum "195.94375" {
  //              description "195.94375 THz/1529.99 nm 6.25GHz spacing";
  //            }
  //            enum "195.95000" {
  //              description "195.95000 THz/1529.94 nm 6.25/12.5/50/75GHz spacing";
  //            }
  //            enum "195.95625" {
  //              description "195.95625 THz/1529.89 nm 6.25GHz spacing";
  //            }
  //            enum "195.96250" {
  //              description "195.96250 THz/1529.85 nm 6.25/12.5GHz spacing";
  //            }
  //            enum "195.96875" {
  //              description "195.96875 THz/1529.80 nm 6.25GHz spacing";
  //            }
  //            enum "195.97500" {
  //              description "195.97500 THz/1529.75 nm 6.25/12.5GHz spacing";
  //            }
  //            enum "195.98125" {
  //              description "195.98125 THz/1529.70 nm 6.25GHz spacing";
  //            }
  //            enum "195.98750" {
  //              description "195.98750 THz/1529.65 nm 6.25/12.5GHz spacing";
  //            }
  //            enum "195.99375" {
  //              description "195.99375 THz/1529.60 nm 6.25GHz spacing";
  //            }
  //            enum "196.00000" {
  //              description "196.00000 THz/1529.55 nm 6.25/12.5/50/100GHz spacing";
  //            }
  //            enum "196.00625" {
  //              description "196.00625 THz/1529.50 nm 6.25GHz spacing";
  //            }
  //            enum "196.01250" {
  //              description "196.01250 THz/1529.46 nm 6.25/12.5GHz spacing";
  //            }
  //            enum "196.01875" {
  //              description "196.01875 THz/1529.41 nm 6.25GHz spacing";
  //            }
  //            enum "196.02500" {
  //              description "196.02500 THz/1529.36 nm 6.25/12.5/75GHz spacing";
  //            }
  //            enum "196.03125" {
  //              description "196.03125 THz/1529.31 nm 6.25GHz spacing";
  //            }
  //            enum "196.03750" {
  //              description "196.03750 THz/1529.26 nm 6.25/12.5GHz spacing";
  //            }
  //            enum "196.04375" {
  //              description "196.04375 THz/1529.21 nm 6.25GHz spacing";
  //            }
  //            enum "196.05000" {
  //              description "196.05000 THz/1529.16 nm 6.25/12.5/50GHz spacing";
  //            }
  //            enum "196.05625" {
  //              description "196.05625 THz/1529.11 nm 6.25GHz spacing";
  //            }
  //            enum "196.06250" {
  //              description "196.06250 THz/1529.07 nm 6.25/12.5GHz spacing";
  //            }
  //            enum "196.06875" {
  //              description "196.06875 THz/1529.02 nm 6.25GHz spacing";
  //            }
  //            enum "196.07500" {
  //              description "196.07500 THz/1528.97 nm 6.25/12.5GHz spacing";
  //            }
  //            enum "196.08125" {
  //              description "196.08125 THz/1528.92 nm 6.25GHz spacing";
  //            }
  //            enum "196.08750" {
  //              description "196.08750 THz/1528.87 nm 6.25/12.5GHz spacing";
  //            }
  //            enum "196.09375" {
  //              description "196.09375 THz/1528.82 nm 6.25GHz spacing";
  //            }
  //            enum "196.10000" {
  //              description "196.10000 THz/1528.77 nm 6.25/12.5/50/75/100GHz spacing";
  //            }
  //            enum "196.15040" {
  //              description "196.15040 THz/1528.38 nm 50Ghz spacing";
  //            }
  //          }
  //        }
  //      }
  //    }
  //    leaf tx-power {
  //      description "Transmit laser output power";
  //      units "dBm";
  //      type string {
  //      }
  //    }
  //    choice laser-enable-choice {
  //      leaf laser-enable {
  //        description "Enable transmit laser";
  //        type empty;
  //      }
  //      leaf no-laser-enable {
  //        description "Don't enable transmit laser";
  //        type empty;
  //      }
  //    }
  //  }
  //  grouping odu-attributes {
  //    description "Optical Data Unit configuration attributes";
  //    // uses apply-advanced;
  //    leaf rate {
  //      description "Specific type of ODU, according to data rate";
  //      type enumeration {
  //        enum "odu4" {
  //          description "ODU4 for 100 Gbps";
  //        }
  //      }
  //    }
  //    choice is-ma-choice {
  //      leaf is-ma {
  //        description "Link is enabled for maintenance tasks, alarms are masked";
  //        type empty;
  //      }
  //      leaf no-is-ma {
  //        description "Don't link is enabled for maintenance tasks, alarms are masked";
  //        type empty;
  //      }
  //    }
  //    container tti {
  //      description "Configuration of OTU trail trace identifier";
  //      presence "enable tti";
  //      uses otn-tti-attributes;
  //    }
  //    container degrade {
  //      description "Configuration of OTU degrade defect detection";
  //      presence "enable degrade";
  //      uses otn-degrade;
  //    }
  //    leaf exp-payload-type {
  //      description "Expected OPU payload type";
  //      type union {
  //        type uint8;
  //        type string {
  //          pattern "<.*>|$.*";
  //        }
  //      }
  //    }
  //    container prbs {
  //      description "Configuration of framed pseudorandom binary sequence test signal";
  //      presence "enable prbs";
  //      uses prbs-config;
  //    }
  //  }
  //  grouping otn-degrade {
  //    description "Configuration of degrade defect detection";
  //    // uses apply-advanced;
  //    leaf degm {
  //      description "Number of consecutive intervals error rate above threshold";
  //      type union {
  //        type string {
  //          pattern "<.*>|$.*";
  //        }
  //        type uint16 {
  //          range "2 .. 10";
  //        }
  //      }
  //    }
  //    leaf degthr {
  //      description "Threshold - percentage errored blocks, ex. 1.23 = 1.23%";
  //      type string {
  //      }
  //    }
  //  }
  //  grouping otn-tti-attributes {
  //    description "Configuration of OTN trail trace identifier";
  //    // uses apply-advanced;
  //    leaf sapi {
  //      description "Transmitted source access point identifier field";
  //      type string {
  //        length "0 .. 15";
  //      }
  //    }
  //    leaf dapi {
  //      description "Transmitted destination access point identifier field";
  //      type string {
  //        length "0 .. 15";
  //      }
  //    }
  //    leaf operator {
  //      description "Transmitted operator field";
  //      type string {
  //        length "0 .. 32";
  //      }
  //    }
  //    leaf exp-sapi {
  //      description "Expected received source access point identifier field";
  //      type string {
  //        length "0 .. 15";
  //      }
  //    }
  //    leaf exp-dapi {
  //      description "Expected received destination access point identifier field";
  //      type string {
  //        length "0 .. 15";
  //      }
  //    }
  //    leaf tim-detect-mode {
  //      description "Trace input mismatch defect detection mode";
  //      type enumeration {
  //        enum "disabled" {
  //          description "Detection of trace input mismatch defect disabled";
  //        }
  //        enum "sapi-only" {
  //          description "Detection of trace input mismatch defect on SAPI field only";
  //        }
  //        enum "dapi-only" {
  //          description "Detection of trace input mismatch defect on DAPI field only";
  //        }
  //        enum "sapi-and-dapi" {
  //          description "Detection of trace input mismatch defect on both SAPI and DAPI fields";
  //        }
  //      }
  //    }
  //    choice tim-act-enable-choice {
  //      leaf tim-act-enable {
  //        description "Enable trace input mismatch consequential actions";
  //        type empty;
  //      }
  //      leaf no-tim-act-enable {
  //        description "Don't enable trace input mismatch consequential actions";
  //        type empty;
  //      }
  //    }
  //  }
  //  grouping otn_options_type {
  //    // uses apply-advanced;
  //    choice laser-enable-choice {
  //      leaf laser-enable {
  //        description "Enable Laser";
  //        type empty;
  //      }
  //      leaf no-laser-enable {
  //        description "Don't enable Laser";
  //        type empty;
  //      }
  //    }
  //    choice is-ma-choice {
  //      leaf is-ma {
  //        description "Link is enabled with alarms masked";
  //        type empty;
  //      }
  //      leaf no-is-ma {
  //        description "Don't link is enabled with alarms masked";
  //        type empty;
  //      }
  //    }
  //    choice line-loopback-choice {
  //      leaf line-loopback {
  //        description "Enable line loopback";
  //        type empty;
  //      }
  //      leaf no-line-loopback {
  //        description "Don't enable line loopback";
  //        type empty;
  //      }
  //    }
  //    choice local-loopback-choice {
  //      leaf local-loopback {
  //        description "Enable local host loopback";
  //        type empty;
  //      }
  //      leaf no-local-loopback {
  //        description "Don't enable local host loopback";
  //        type empty;
  //      }
  //    }
  //    choice prbs-choice {
  //      leaf prbs {
  //        description "Enable otn payload prbs";
  //        type empty;
  //      }
  //      leaf no-prbs {
  //        description "Don't enable otn payload prbs";
  //        type empty;
  //      }
  //    }
  //    choice odu-ttim-action-enable-choice {
  //      leaf odu-ttim-action-enable {
  //        description "Enable consequent action for ODU TTIM";
  //        type empty;
  //      }
  //      leaf no-odu-ttim-action-enable {
  //        description "Don't enable consequent action for ODU TTIM";
  //        type empty;
  //      }
  //    }
  //    choice otu-ttim-action-enable-choice {
  //      leaf otu-ttim-action-enable {
  //        description "Enable consequent action for OTU TTIM";
  //        type empty;
  //      }
  //      leaf no-otu-ttim-action-enable {
  //        description "Don't enable consequent action for OTU TTIM";
  //        type empty;
  //      }
  //    }
  //    choice transport-monitoring-choice {
  //      leaf transport-monitoring {
  //        description "Enable transport monitoring";
  //        type empty;
  //      }
  //      leaf no-transport-monitoring {
  //        description "Don't enable transport monitoring";
  //        type empty;
  //      }
  //    }
  //    container odu-delay-management {
  //      description "Set odu delay management";
  //      // uses apply-advanced;
  //      choice monitor-end-point-choice {
  //        leaf monitor-end-point {
  //          description "Originate connection monitor end point";
  //          type empty;
  //        }
  //        leaf no-monitor-end-point {
  //          description "Don't originate connection monitor end point";
  //          type empty;
  //        }
  //      }
  //      choice start-measurement-choice {
  //        leaf start-measurement {
  //          description "Enable to start a dm measurement";
  //          type empty;
  //        }
  //        leaf no-start-measurement {
  //          description "Don't enable to start a dm measurement";
  //          type empty;
  //        }
  //      }
  //      choice bypass-choice {
  //        leaf bypass {
  //          description "Act as tandem passing dm value through node";
  //          type empty;
  //        }
  //        leaf no-bypass {
  //          description "Don't act as tandem passing dm value through node";
  //          type empty;
  //        }
  //      }
  //      leaf number-of-frames {
  //        description "Number of consequent frames to declare dm done";
  //        type union {
  //          type string {
  //            pattern "<.*>|$.*";
  //          }
  //          type uint32 {
  //            range "0 .. 255";
  //          }
  //        }
  //      }
  //      choice remote-loop-enable-choice {
  //        leaf remote-loop-enable {
  //          description "Enable remote DM loop on remote end";
  //          type empty;
  //        }
  //        leaf no-remote-loop-enable {
  //          description "Don't enable remote DM loop on remote end";
  //          type empty;
  //        }
  //      }
  //    }
  //    container signal-degrade {
  //      description "Signal degrade thresholds";
  //      // uses apply-advanced;
  //      leaf interval {
  //        description "Time interval";
  //        default "10";
  //        units "milliseconds";
  //        type union {
  //          type string {
  //            pattern "<.*>|$.*";
  //          }
  //          type uint32 {
  //            range "1 .. 1000";
  //          }
  //        }
  //      }
  //      leaf ber-threshold-clear {
  //        description "Ber threshold for signal degrade clear (format: xe-n, example: 4.5e-3)";
  //        type string {
  //        }
  //      }
  //      leaf ber-threshold-signal-degrade {
  //        description "Ber threshold for signal-degrade (format: xe-n, example: 4.5e-3)";
  //        type string {
  //        }
  //      }
  //      leaf q-threshold-signal-degrade-clear {
  //        description "Q threshold for signal-degrade clear (e.g. 14.26)";
  //        units "dB";
  //        type string;
  //      }
  //      leaf q-threshold-signal-degrade {
  //        description "Q threshold for signal-degrade (e.g. 9.26)";
  //        units "dB";
  //        type string;
  //      }
  //    }
  //    container odu-signal-degrade {
  //      description "Signal degrade thresholds for ODU";
  //      // uses apply-advanced;
  //      leaf interval {
  //        description "Time interval";
  //        default "10";
  //        units "milliseconds";
  //        type union {
  //          type string {
  //            pattern "<.*>|$.*";
  //          }
  //          type uint32 {
  //            range "1 .. 1000";
  //          }
  //        }
  //      }
  //      leaf ber-threshold-clear {
  //        description "Ber th for sd clear (format: xe-n, example: 4.5e-3)";
  //        default "1.0e-9";
  //        type string {
  //        }
  //      }
  //      leaf ber-threshold-signal-degrade {
  //        description "Ber th for sd (format: xe-n, example: 4.5e-3)";
  //        default "1.0e-6";
  //        type string {
  //        }
  //      }
  //    }
  //    container preemptive-fast-reroute {
  //      description "Preemptive fast reroute";
  //      // uses apply-advanced;
  //      choice odu-signal-degrade-monitor-enable-choice {
  //        leaf odu-signal-degrade-monitor-enable {
  //          description "Enable ODU signal degrade monitoring";
  //          type empty;
  //        }
  //        leaf no-odu-signal-degrade-monitor-enable {
  //          description "Don't enable ODU signal degrade monitoring";
  //          type empty;
  //        }
  //      }
  //      choice odu-backward-frr-enable-choice {
  //        leaf odu-backward-frr-enable {
  //          description "Enable ODU backward frr insertion";
  //          type empty;
  //        }
  //        leaf no-odu-backward-frr-enable {
  //          description "Don't enable ODU backward frr insertion";
  //          type empty;
  //        }
  //      }
  //      choice signal-degrade-monitor-enable-choice {
  //        leaf signal-degrade-monitor-enable {
  //          description "Enable signal degrade monitoring";
  //          type empty;
  //        }
  //        leaf no-signal-degrade-monitor-enable {
  //          description "Don't enable signal degrade monitoring";
  //          type empty;
  //        }
  //      }
  //      choice backward-frr-enable-choice {
  //        leaf backward-frr-enable {
  //          description "Enable backward frr insertion";
  //          type empty;
  //        }
  //        leaf no-backward-frr-enable {
  //          description "Don't enable backward frr insertion";
  //          type empty;
  //        }
  //      }
  //    }
  //    leaf fec {
  //      description "Forward Error Correction mode";
  //      type enumeration {
  //        enum "none" {
  //          description "GFEC all 0's";
  //        }
  //        enum "gfec" {
  //          description "GFEC-Generic Forward Error Correction";
  //        }
  //        enum "efec" {
  //          description "EFEC-Enhanced Forward Error Correction";
  //        }
  //        enum "gfec-sdfec" {
  //          description "Both gfec and sdfec";
  //        }
  //        enum "ufec" {
  //          description "UFEC-Ultra Forward Error Correction";
  //        }
  //        enum "sdfec" {
  //          description "SDFEC-Soft Decision Forward Error Correction";
  //        }
  //        enum "hgfec" {
  //          description "HGFEC-High Gain Forward Error Correction";
  //        }
  //        enum "sdfec15" {
  //          description "SDFEC with 15 percent overhead - non-differential";
  //        }
  //      }
  //    }
  //    choice insert-odu-oci-choice {
  //      leaf insert-odu-oci {
  //        description "Force odu open connection indication";
  //        type empty;
  //      }
  //      leaf no-insert-odu-oci {
  //        description "Don't force odu open connection indication";
  //        type empty;
  //      }
  //    }
  //    choice insert-odu-lck-choice {
  //      leaf insert-odu-lck {
  //        description "Force odu locked maintenance signal";
  //        type empty;
  //      }
  //      leaf no-insert-odu-lck {
  //        description "Don't force odu locked maintenance signal";
  //        type empty;
  //      }
  //    }
  //    leaf rate {
  //      description "Optical Transmission Network mode";
  //      type enumeration {
  //        enum "pass-thru" {
  //          description "Pass through mode - No OTN framing";
  //        }
  //        enum "fixed-stuff-bytes" {
  //          description "Fixed Stuff Bytes 11.0957Gbps";
  //        }
  //        enum "no-fixed-stuff-bytes" {
  //          description "No Fixed Stuff Bytes 11.0491Gbps";
  //        }
  //        enum "oc192" {
  //          description "OTU2 for OC192 10.7Gbps";
  //        }
  //        enum "otu3" {
  //          description "OTU3 for 40Gbps";
  //        }
  //        enum "otu4" {
  //          description "OTU4/OTU4v for 100Gbps-127Gbps";
  //        }
  //      }
  //    }
  //    container bytes {
  //      description "Set OTN header bytes";
  //      // uses apply-advanced;
  //      leaf transmit-payload-type {
  //        description "Transmit payload type";
  //        type union {
  //          type string {
  //            pattern "<.*>|$.*";
  //          }
  //          type uint32 {
  //            range "0 .. 255";
  //          }
  //        }
  //      }
  //    }
  //    container tti {
  //      description "Trace Identifier";
  //      // uses apply-advanced;
  //      leaf otu-dapi {
  //        description "OTU Destination Access Point Identifier";
  //        type string;
  //      }
  //      leaf otu-sapi {
  //        description "OTU Source Access Point Identifier";
  //        type string;
  //      }
  //      leaf otu-expected-receive-dapi {
  //        description "OTU Expected Receive Destination Access Point Identifier";
  //        type string;
  //      }
  //      leaf otu-expected-receive-sapi {
  //        description "OTU Expected Receive Source Access Point Identifier";
  //        type string;
  //      }
  //      leaf odu-dapi {
  //        description "ODU Destination Access Point Identifier";
  //        type string;
  //      }
  //      leaf odu-sapi {
  //        description "ODU Source Access Point Identifier";
  //        type string;
  //      }
  //      leaf odu-expected-receive-dapi {
  //        description "ODU Expected Receive Destination Access Point Identifier";
  //        type string;
  //      }
  //      leaf odu-expected-receive-sapi {
  //        description "ODU Expected Receive Source Access Point Identifier";
  //        type string;
  //      }
  //      choice otu-dapi-first-byte-nul-choice {
  //        leaf otu-dapi-first-byte-nul {
  //          description "Insert all-0s to first byte";
  //          type empty;
  //        }
  //        leaf no-otu-dapi-first-byte-nul {
  //          description "Don't insert all-0s to first byte";
  //          type empty;
  //        }
  //      }
  //      choice otu-sapi-first-byte-nul-choice {
  //        leaf otu-sapi-first-byte-nul {
  //          description "Insert all-0s to first byte";
  //          type empty;
  //        }
  //        leaf no-otu-sapi-first-byte-nul {
  //          description "Don't insert all-0s to first byte";
  //          type empty;
  //        }
  //      }
  //      choice otu-expected-receive-dapi-first-byte-nul-choice {
  //        leaf otu-expected-receive-dapi-first-byte-nul {
  //          description "Insert all-0s to first byte";
  //          type empty;
  //        }
  //        leaf no-otu-expected-receive-dapi-first-byte-nul {
  //          description "Don't insert all-0s to first byte";
  //          type empty;
  //        }
  //      }
  //      choice otu-expected-receive-sapi-first-byte-nul-choice {
  //        leaf otu-expected-receive-sapi-first-byte-nul {
  //          description "Insert all-0s to first byte";
  //          type empty;
  //        }
  //        leaf no-otu-expected-receive-sapi-first-byte-nul {
  //          description "Don't insert all-0s to first byte";
  //          type empty;
  //        }
  //      }
  //      choice odu-dapi-first-byte-nul-choice {
  //        leaf odu-dapi-first-byte-nul {
  //          description "Insert all-0s to first byte";
  //          type empty;
  //        }
  //        leaf no-odu-dapi-first-byte-nul {
  //          description "Don't insert all-0s to first byte";
  //          type empty;
  //        }
  //      }
  //      choice odu-sapi-first-byte-nul-choice {
  //        leaf odu-sapi-first-byte-nul {
  //          description "Insert all-0s to first byte";
  //          type empty;
  //        }
  //        leaf no-odu-sapi-first-byte-nul {
  //          description "Don't insert all-0s to first byte";
  //          type empty;
  //        }
  //      }
  //      choice odu-expected-receive-dapi-first-byte-nul-choice {
  //        leaf odu-expected-receive-dapi-first-byte-nul {
  //          description "Insert all-0s to first byte";
  //          type empty;
  //        }
  //        leaf no-odu-expected-receive-dapi-first-byte-nul {
  //          description "Don't insert all-0s to first byte";
  //          type empty;
  //        }
  //      }
  //      choice odu-expected-receive-sapi-first-byte-nul-choice {
  //        leaf odu-expected-receive-sapi-first-byte-nul {
  //          description "Insert all-0s to first byte";
  //          type empty;
  //        }
  //        leaf no-odu-expected-receive-sapi-first-byte-nul {
  //          description "Don't insert all-0s to first byte";
  //          type empty;
  //        }
  //      }
  //    }
  //    container trigger {
  //      description "Defect triggers";
  //      // uses apply-advanced;
  //      container oc-los {
  //        description "OC Loss Of Signal defect trigger";
  //        choice oc_los_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container oc-lof {
  //        description "OC Loss Of Frame defect trigger";
  //        choice oc_lof_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container oc-lom {
  //        description "OC Loss Of Multiframe defect trigger";
  //        choice oc_lom_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container oc-wavelength-lock {
  //        description "OC Wavelength Lock defect trigger";
  //        choice oc_wavelength_lock_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container oc-tsf {
  //        description "Oc tsf defect trigger";
  //        choice oc-tsf-choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container otu-ais {
  //        description "OTU Alarm Indication Signal defect trigger";
  //        choice otu_ais_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container otu-bdi {
  //        description "OTU Backward Defect Indication defect trigger";
  //        choice otu_bdi_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container otu-iae {
  //        description "OTU Incoming Alignment defect trigger";
  //        choice otu_iae_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container otu-ttim {
  //        description "OTU Trail Trace Identifier Mismatch defect trigger";
  //        choice otu_ttim_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container otu-sd {
  //        description "OTU Signal Degrade defect trigger";
  //        choice otu_sd_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container otu-fec-deg {
  //        description "OTU FEC Degrade defect trigger";
  //        choice otu_fec_deg_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container otu-fec-exe {
  //        description "OTU FEC Excessive Error defect trigger";
  //        choice otu_fec_exe_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container odu-ais {
  //        description "ODU Alarm Indication Signal defect trigger";
  //        choice odu_ais_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container odu-bdi {
  //        description "ODU Backward Defect Indication defect trigger";
  //        choice odu_bdi_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container odu-iae {
  //        description "Odu iae defect trigger";
  //        choice odu-iae-choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container odu-bei {
  //        description "Odu backward error indication defect trigger";
  //        choice odu_bei_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container odu-oci {
  //        description "ODU Open Connection Indication defect trigger";
  //        choice odu_oci_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container odu-lck {
  //        description "ODU Locked defect trigger";
  //        choice odu_lck_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container odu-ttim {
  //        description "ODU Trail Trace Identifier Mismatch defect trigger";
  //        choice odu_ttim_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container odu-sd {
  //        description "ODU Signal Degrade defect trigger";
  //        choice odu_sd_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //      container opu-ptim {
  //        description "Payload Type Mismatch defect trigger";
  //        choice opu_ptm_choices {
  //          case case_1 {
  //            leaf ignore {
  //              description "Ignore the defect";
  //              type empty;
  //            }
  //          }
  //          case case_2 {
  //            container hold-time {
  //              description "Delay before clearing or raising the alarm for defect";
  //              leaf up {
  //                description "Delay before clearing the alarm when the defect is absent";
  //                units "milliseconds";
  //                type union {
  //                  type string {
  //                    pattern "<.*>|$.*";
  //                  }
  //                  type uint32 {
  //                    range "1 .. 65534";
  //                  }
  //                }
  //              }
  //              leaf down {
  //                description "Delay before raising the alarm when the defect occurs";
  //                units "milliseconds";
  //                type union {
  //                  type string {
  //                    pattern "<.*>|$.*";
  //                  }
  //                  type uint32 {
  //                    range "1 .. 65534";
  //                  }
  //                }
  //              }
  //            }
  //          }
  //        }
  //      }
  //    }
  //    container tca {
  //      description "TCA - threshold crossing alerts";
  //      // uses apply-advanced;
  //      container otu-tca-es {
  //        description "OTU Errored Seconds Threshold crossing defect trigger";
  //        choice enable-tca-choice {
  //          leaf enable-tca {
  //            description "Enable the OTU errored seconds threshold crossing alert";
  //            type empty;
  //          }
  //          leaf no-enable-tca {
  //            description "Don't enable the OTU errored seconds threshold crossing alert";
  //            type empty;
  //          }
  //        }
  //        leaf threshold {
  //          description "TCA threshold for OTU errored seconds in 15 minutes";
  //          default "135";
  //          type union {
  //            type string {
  //              pattern "<.*>|$.*";
  //            }
  //            type uint32 {
  //              range "1 .. 900";
  //            }
  //          }
  //        }
  //        leaf threshold-24hrs {
  //          description "TCA threshold for OTU errored seconds in 24 hours";
  //          default "162";
  //          type union {
  //            type string {
  //              pattern "<.*>|$.*";
  //            }
  //            type uint32 {
  //              range "1 .. 86400";
  //            }
  //          }
  //        }
  //      }
  //      container otu-tca-ses {
  //        description "OTU Severely Errored Seconds Threshold crossing defect trigger";
  //        choice enable-tca-choice {
  //          leaf enable-tca {
  //            description "Enable the OTU severely errored seconds threshold crossing alert";
  //            type empty;
  //          }
  //          leaf no-enable-tca {
  //            description "Don't enable the OTU severely errored seconds threshold crossing alert";
  //            type empty;
  //          }
  //        }
  //        leaf threshold {
  //          description "TCA threshold for OTU severely errored seconds in 15 minutes";
  //          default "90";
  //          type union {
  //            type string {
  //              pattern "<.*>|$.*";
  //            }
  //            type uint32 {
  //              range "1 .. 900";
  //            }
  //          }
  //        }
  //        leaf threshold-24hrs {
  //          description "TCA threshold for OTU severely errored seconds in 24 hours";
  //          default "108";
  //          type union {
  //            type string {
  //              pattern "<.*>|$.*";
  //            }
  //            type uint32 {
  //              range "1 .. 86400";
  //            }
  //          }
  //        }
  //      }
  //      container otu-tca-uas {
  //        description "OTU Unavailable Seconds Threshold crossing defect trigger";
  //        choice enable-tca-choice {
  //          leaf enable-tca {
  //            description "Enable the OTU unavailable seconds threshold crossing alert";
  //            type empty;
  //          }
  //          leaf no-enable-tca {
  //            description "Don't enable the OTU unavailable seconds threshold crossing alert";
  //            type empty;
  //          }
  //        }
  //        leaf threshold {
  //          description "TCA threshold for OTU unavailable seconds in 15 minutes";
  //          default "90";
  //          type union {
  //            type string {
  //              pattern "<.*>|$.*";
  //            }
  //            type uint32 {
  //              range "10 .. 900";
  //            }
  //          }
  //        }
  //        leaf threshold-24hrs {
  //          description "TCA threshold for OTU unavailable seconds in 24 hours";
  //          default "108";
  //          type union {
  //            type string {
  //              pattern "<.*>|$.*";
  //            }
  //            type uint32 {
  //              range "10 .. 86400";
  //            }
  //          }
  //        }
  //      }
  //      container otu-tca-bbe {
  //        description "OTU Background Block Error Threshold crossing defect trigger";
  //        choice enable-tca-choice {
  //          leaf enable-tca {
  //            description "Enable the OTU BBE threshold crossing alert";
  //            type empty;
  //          }
  //          leaf no-enable-tca {
  //            description "Don't enable the OTU BBE threshold crossing alert";
  //            type empty;
  //          }
  //        }
  //        leaf threshold {
  //          description "TCA threshold for OTU BBE in 15 minutes";
  //          default "800";
  //          type union {
  //            type string {
  //              pattern "<.*>|$.*";
  //            }
  //            type uint32 {
  //              range "1 .. 771000000";
  //            }
  //          }
  //        }
  //        leaf threshold-24hrs {
  //          description "TCA threshold for OTU BBE in 24 hours";
  //          default "960";
  //          type union {
  //            type string {
  //              pattern "<.*>|$.*";
  //            }
  //            type uint32 {
  //              range "1 .. 771000000";
  //            }
  //          }
  //        }
  //      }
  //      container otu-tca-es-fe {
  //        description "OTU far-end Errored Seconds Threshold crossing defect trigger";
  //        choice enable-tca-choice {
  //          leaf enable-tca {
  //            description "Enable the OTU far-end errored seconds threshold crossing alert";
  //            type empty;
  //          }
  //          leaf no-enable-tca {
  //            description "Don't enable the OTU far-end errored seconds threshold crossing alert";
  //            type empty;
  //          }
  //        }
  //        leaf threshold {
  //          description "TCA threshold for OTU far-end errored seconds in 15 minutes";
  //          default "135";
  //          type union {
  //            type string {
  //              pattern "<.*>|$.*";
  //            }
  //            type uint32 {
  //              range "1 .. 900";
  //            }
  //          }
  //        }
  //        leaf threshold-24hrs {
  //          description "TCA threshold for OTU far-end errored seconds in 24 hours";
  //          default "162";
  //          type union {
  //            type string {
  //              pattern "<.*>|$.*";
  //            }
  //            type uint32 {
  //              range "1 .. 86400";
  //            }
  //          }
  //        }
  //      }
  //      container otu-tca-ses-fe {
  //        description "OTU far-end Severely Errored Seconds Threshold crossing defect trigger";
  //        choice enable-tca-choice {
  //          leaf enable-tca {
  //            description "Enable the OTU far-end Unavailable Seconds threshold crossing alert";
  //            type empty;
  //          }
  //          leaf no-enable-tca {
  //            description "Don't enable the OTU far-end Unavailable Seconds threshold crossing alert";
  //            type empty;
  //          }
  //        }
  //        leaf threshold {
  //          description "TCA threshold for OTU far-end severely errored seconds in 15 minutes";
  //          default "90";
  //          type union {
  //            type string {
  //              pattern "<.*>|$.*";
  //            }
  //            type uint32 {
  //              range "1 .. 900";
  //            }
  //          }
  //        }
  //        leaf threshold-24hrs {
  //          description "TCA threshold for OTU far-end severely errored seconds in 24 hours";
  //          default "108";
  //          type union {
  //            type string {
  //              pattern "<.*>|$.*";
  //            }
  //            type uint32 {
  //              range "1 .. 86400";
  //            }
  //          }
  //        }
  //      }
  //      container otu-tca-uas-fe {
  //        description "OTU far-end Unavailable Seconds Threshold crossing defect trigger";
  //        choice enable-tca-choice {
  //          leaf enable-tca {
  //            description "Enable the OTU far end unavailabe second threshold crossing alert";
  //            type empty;
  //          }
  //          leaf no-enable-tca {
  //            description "Don't enable the OTU far end unavailabe second threshold crossing alert";
  //            type empty;
  //          }
  //        }
  //        leaf threshold {
  //          description "TCA threshold for OTU far-end unavailable seconds in 15 minutes";
  //          default "90";
  //          type union {
  //            type string {
  //              pattern "<.*>|$.*";
  //            }
  //            type uint32 {
  //              range "10 .. 900";
  //            }
  //          }
  //        }
  //        leaf threshold-24hrs {
  //          description "TCA threshold for OTU far-end unavailable seconds in 24 hours";
  //          default "108";
  //          type union {
  //            type string {
  //              pattern "<.*>|$.*";
  //            }
  //            type uint32 {
  //              range "10 .. 86400";
  //            }
  //          }
  //        }
  //      }
  //      container otu-tca-bbe-fe {
  //        description "OTU far-end Background Block Error (BEI) Threshold crossing defect trigger";
  //        choice enable-tca-choice {
  //          leaf enable-tca {
  //            description "Enable the OTU BBE (BEI) threshold crossing alert";
  //            type empty;
  //          }
  //          leaf no-enable-tca {
  //            description "Don't enable the OTU BBE (BEI) threshold crossing alert";
  //            type empty;
  //          }
  //        }
  //        leaf threshold {
  //          description "TCA threshold for OTU far-end BBE (BEI) in 15 minutes";
  //          default "800";
  //          type union {
  //            type string {
  //              pattern "<.*>|$.*";
  //            }
  //            type uint32 {
  //              range "1 .. 771000000";
  //            }
  //          }
  //        }
  //        leaf threshold-24hrs {
  //          description "TCA threshold for OTU far-end BBE (BEI) in 24 hours";
  //          default "960";
  //          type union {
  //            type string {
  //              pattern "<.*>|$.*";
  //            }
  //            type uint32 {
  //              range "1 .. 771000000";
  //            }
  //          }
  //        }
  //      }
  //      container odu-tca-es {
  //        description "ODU Errored Seconds Threshold crossing defect trigger";
  //        choice enable-tca-choice {
  //          leaf enable-tca {
  //            description "Enable the ODU errored seconds threshold crossing alert";
  //            type empty;
  //          }
  //          leaf no-enable-tca {
  //            description "Don't enable the ODU errored seconds threshold crossing alert";
  //            type empty;
  //          }
  //        }
  //        leaf threshold {
  //          description "TCA threshold for ODU errored seconds in 15 minutes";
  //          default "135";
  //          type union {
  //            type string {
  //              pattern "<.*>|$.*";
  //            }
  //            type uint32 {
  //              range "1 .. 900";
  //            }
  //          }
  //        }
  //        leaf threshold-24hrs {
  //          description "TCA threshold for ODU errored seconds in 24 hours";
  //          default "162";
  //          type union {
  //            type string {
  //              pattern "<.*>|$.*";
  //            }
  //            type uint32 {
  //              range "1 .. 86400";
  //            }
  //          }
  //        }
  //      }
  //      container odu-tca-ses {
  //        description "ODU Severely Errored Seconds Threshold crossing defect trigger";
  //        choice enable-tca-choice {
  //          leaf enable-tca {
  //            description "Enable the ODU severely errored seconds threshold crossing alert";
  //            type empty;
  //          }
  //          leaf no-enable-tca {
  //            description "Don't enable the ODU severely errored seconds threshold crossing alert";
  //            type empty;
  //          }
  //        }
  //        leaf threshold {
  //          description "TCA threshold for ODU severely errored seconds in 15 minutes";
  //          default "90";
  //          type union {
  //            type string {
  //              pattern "<.*>|$.*";
  //            }
  //            type uint32 {
  //              range "1 .. 900";
  //            }
  //          }
  //        }
  //        leaf threshold-24hrs {
  //          description "TCA threshold for ODU severely-errored seconds in 24 hours";
  //          default "108";
  //          type union {
  //            type string {
  //              pattern "<.*>|$.*";
  //            }
  //            type uint32 {
  //              range "1 .. 86400";
  //            }
  //          }
  //        }
  //      }
  //      container odu-tca-uas {
  //        description "ODU Unavailable Seconds Threshold crossing defect trigger";
  //        choice enable-tca-choice {
  //          leaf enable-tca {
  //            description "Enable the ODU unavailable seconds threshold crossing alert";
  //            type empty;
  //          }
  //          leaf no-enable-tca {
  //            description "Don't enable the ODU unavailable seconds threshold crossing alert";
  //            type empty;
  //          }
  //        }
  //        leaf threshold {
  //          description "TCA threshold for ODU unavailable seconds in 15 minutes";
  //          default "90";
  //          type union {
  //            type string {
  //              pattern "<.*>|$.*";
  //            }
  //            type uint32 {
  //              range "10 .. 900";
  //            }
  //          }
  //        }
  //        leaf threshold-24hrs {
  //          description "TCA threshold for ODU unavailable seconds in 24 hours";
  //          default "108";
  //          type union {
  //            type string {
  //              pattern "<.*>|$.*";
  //            }
  //            type uint32 {
  //              range "10 .. 86400";
  //            }
  //          }
  //        }
  //      }
  //      container odu-tca-bbe {
  //        description "ODU Background Block Error Threshold crossing defect trigger";
  //        choice enable-tca-choice {
  //          leaf enable-tca {
  //            description "Enable the ODU BBE threshold crossing alert";
  //            type empty;
  //          }
  //          leaf no-enable-tca {
  //            description "Don't enable the ODU BBE threshold crossing alert";
  //            type empty;
  //          }
  //        }
  //        leaf threshold {
  //          description "TCA threshold for ODU BBE in 15 minutes";
  //          default "800";
  //          type union {
  //            type string {
  //              pattern "<.*>|$.*";
  //            }
  //            type uint32 {
  //              range "1 .. 771000000";
  //            }
  //          }
  //        }
  //        leaf threshold-24hrs {
  //          description "TCA threshold for ODU backgrand block error in 24 hours";
  //          default "960";
  //          type union {
  //            type string {
  //              pattern "<.*>|$.*";
  //            }
  //            type uint32 {
  //              range "1 .. 771000000";
  //            }
  //          }
  //        }
  //      }
  //      container odu-tca-es-fe {
  //        description "ODU far-end Errored Seconds Threshold crossing defect trigger";
  //        choice enable-tca-choice {
  //          leaf enable-tca {
  //            description "Enable the ODU far-end errored seconds threshold crossing alert";
  //            type empty;
  //          }
  //          leaf no-enable-tca {
  //            description "Don't enable the ODU far-end errored seconds threshold crossing alert";
  //            type empty;
  //          }
  //        }
  //        leaf threshold {
  //          description "TCA threshold for ODU far-end errored seconds in 15 minutes";
  //          default "135";
  //          type union {
  //            type string {
  //              pattern "<.*>|$.*";
  //            }
  //            type uint32 {
  //              range "1 .. 900";
  //            }
  //          }
  //        }
  //        leaf threshold-24hrs {
  //          description "TCA threshold for ODU far-end errored seconds in 24 hours";
  //          default "162";
  //          type union {
  //            type string {
  //              pattern "<.*>|$.*";
  //            }
  //            type uint32 {
  //              range "1 .. 86400";
  //            }
  //          }
  //        }
  //      }
  //      container odu-tca-ses-fe {
  //        description "ODU far-end Severely Errored Seconds Threshold crossing defect trigger";
  //        choice enable-tca-choice {
  //          leaf enable-tca {
  //            description "Enable the ODU far-end Unavailable Seconds threshold crossing alert";
  //            type empty;
  //          }
  //          leaf no-enable-tca {
  //            description "Don't enable the ODU far-end Unavailable Seconds threshold crossing alert";
  //            type empty;
  //          }
  //        }
  //        leaf threshold {
  //          description "TCA threshold for ODU far-end severely errored seconds in 15 minutes";
  //          default "90";
  //          type union {
  //            type string {
  //              pattern "<.*>|$.*";
  //            }
  //            type uint32 {
  //              range "1 .. 900";
  //            }
  //          }
  //        }
  //        leaf threshold-24hrs {
  //          description "TCA threshold for ODU severely-errored seconds in 24 hours";
  //          default "108";
  //          type union {
  //            type string {
  //              pattern "<.*>|$.*";
  //            }
  //            type uint32 {
  //              range "1 .. 86400";
  //            }
  //          }
  //        }
  //      }
  //      container odu-tca-uas-fe {
  //        description "ODU far-end Unavailable Seconds Threshold crossing defect trigger";
  //        choice enable-tca-choice {
  //          leaf enable-tca {
  //            description "Enable the ODU far end unavailabe second threshold crossing alert";
  //            type empty;
  //          }
  //          leaf no-enable-tca {
  //            description "Don't enable the ODU far end unavailabe second threshold crossing alert";
  //            type empty;
  //          }
  //        }
  //        leaf threshold {
  //          description "TCA threshold for ODU far-end unavailable seconds in 15 minutes";
  //          default "90";
  //          type union {
  //            type string {
  //              pattern "<.*>|$.*";
  //            }
  //            type uint32 {
  //              range "10 .. 900";
  //            }
  //          }
  //        }
  //        leaf threshold-24hrs {
  //          description "TCA threshold for ODU far-end unavailable seconds in 24 hours";
  //          default "108";
  //          type union {
  //            type string {
  //              pattern "<.*>|$.*";
  //            }
  //            type uint32 {
  //              range "10 .. 86400";
  //            }
  //          }
  //        }
  //      }
  //      container odu-tca-bbe-fe {
  //        description "ODU far-end Background Block Error (BEI) Threshold crossing defect trigger";
  //        choice enable-tca-choice {
  //          leaf enable-tca {
  //            description "Enable the ODU BBE (BEI) threshold crossing alert";
  //            type empty;
  //          }
  //          leaf no-enable-tca {
  //            description "Don't enable the ODU BBE (BEI) threshold crossing alert";
  //            type empty;
  //          }
  //        }
  //        leaf threshold {
  //          description "TCA threshold for ODU far-end BBE (BEI) in 15 minutes";
  //          default "800";
  //          type union {
  //            type string {
  //              pattern "<.*>|$.*";
  //            }
  //            type uint32 {
  //              range "1 .. 771000000";
  //            }
  //          }
  //        }
  //        leaf threshold-24hrs {
  //          description "TCA threshold for ODU far-end backgrand block error in 24 hours";
  //          default "960";
  //          type union {
  //            type string {
  //              pattern "<.*>|$.*";
  //            }
  //            type uint32 {
  //              range "1 .. 771000000";
  //            }
  //          }
  //        }
  //      }
  //      container otu-tca-fec-ber {
  //        description "OTU Errored Seconds Threshold crossing defect trigger";
  //        choice enable-tca-choice {
  //          leaf enable-tca {
  //            description "Enable the OTU errored seconds threshold crossing alert";
  //            type empty;
  //          }
  //          leaf no-enable-tca {
  //            description "Don't enable the OTU errored seconds threshold crossing alert";
  //            type empty;
  //          }
  //        }
  //        leaf threshold {
  //          description "TCA threshold for BER value in format: xe-n, x is an integer or decimal number, n = 0..9";
  //          default "10e-3";
  //          type string {
  //          }
  //        }
  //        leaf threshold-24hrs {
  //          description "TCA threshold for BER value in format: xe-n, x is an integer or decimal number, n = 0..9";
  //          default "10e-3";
  //          type string {
  //          }
  //        }
  //      }
  //    }
  //  }
  //  grouping otu-attributes {
  //    description "Optical transmission unit configuration attributes";
  //    // uses apply-advanced;
  //    leaf rate {
  //      description "Specific type of OTU, according to data rate";
  //      type enumeration {
  //        enum "otu4" {
  //          description "OTU4 for 100 Gbps";
  //        }
  //      }
  //    }
  //    choice is-ma-choice {
  //      leaf is-ma {
  //        description "Link is enabled for maintenance tasks, alarms are masked";
  //        type empty;
  //      }
  //      leaf no-is-ma {
  //        description "Don't link is enabled for maintenance tasks, alarms are masked";
  //        type empty;
  //      }
  //    }
  //    leaf fec {
  //      description "Forward error correction type";
  //      type enumeration {
  //        enum "none" {
  //          description "No forward error correction applied";
  //        }
  //        enum "gfec" {
  //          description "ITU-T G.709 standard forward error correction";
  //        }
  //        enum "hgfec" {
  //          description "High gain FEC";
  //        }
  //      }
  //    }
  //    leaf loopback {
  //      description "Enabled loopback mode";
  //      type enumeration {
  //        enum "none" {
  //          description "No loopback mode active";
  //        }
  //        enum "local" {
  //          description "Local loopback (host side)";
  //        }
  //        enum "line" {
  //          description "Line loopback (network side)";
  //        }
  //      }
  //    }
  //    container tti {
  //      description "Configuration of OTU trail trace identifier";
  //      presence "enable tti";
  //      uses otn-tti-attributes;
  //    }
  //    container degrade {
  //      description "Configuration of OTU degrade defect detection";
  //      presence "enable degrade";
  //      uses otn-degrade;
  //    }
  //  }
  //  grouping ppp_options_type {
  //    // uses apply-advanced;
  //    leaf dynamic-profile {
  //      description "Dynamic profile name";
  //      type string;
  //    }
  //    container chap {
  //      presence "enable chap";
  //      description "Challenge Handshake Authentication Protocol options";
  //      // uses apply-advanced;
  //      choice access-data {
  //        case case_1 {
  //          leaf access-profile {
  //            description "Profile containing client list and access parameters";
  //            type string {
  //              length "1 .. 63";
  //            }
  //          }
  //        }
  //        case case_2 {
  //          leaf default-chap-secret {
  //            description "Default CHAP secret to be used when no matching access profile exists";
  //            type jt:unreadable;
  //          }
  //        }
  //      }
  //      leaf local-name {
  //        description "Name sent in CHAP-Challenge and CHAP-Response";
  //        type string;
  //      }
  //      leaf no-rfc2486 {
  //        description "RFC2486 compliance is not enforced";
  //        type empty;
  //      }
  //      leaf passive {
  //        description "Handle incoming CHAP requests only";
  //        type empty;
  //      }
  //      container challenge-length {
  //        description "CHAP challenge length";
  //        leaf minimum {
  //          description "Minimum CHAP challenge length";
  //          default "16";
  //          units "bytes";
  //          type union {
  //            type string {
  //              pattern "<.*>|$.*";
  //            }
  //            type uint8 {
  //              range "8 .. 63";
  //            }
  //          }
  //        }
  //        leaf maximum {
  //          description "Maximum CHAP challenge length";
  //          default "32";
  //          units "bytes";
  //          type union {
  //            type string {
  //              pattern "<.*>|$.*";
  //            }
  //            type uint8 {
  //              range "8 .. 63";
  //            }
  //          }
  //        }
  //      }
  //    }
  //    container pap {
  //      presence "enable pap";
  //      description "Password Authentication Protocol options";
  //      // uses apply-advanced;
  //      choice access-data {
  //        case case_1 {
  //          leaf access-profile {
  //            description "Profile containing client list and access parameters";
  //            type string {
  //              length "1 .. 63";
  //            }
  //          }
  //        }
  //        case case_2 {
  //          leaf default-password {
  //            description "Default PAP password used in the absence of matching profile";
  //            type jt:unreadable;
  //          }
  //        }
  //      }
  //      leaf local-name {
  //        description "Name sent in PAP request packet";
  //        type string;
  //      }
  //      leaf no-rfc2486 {
  //        description "RFC2486 compliance is not enforced";
  //        type empty;
  //      }
  //      leaf local-password {
  //        description "Password sent in PAP request packet";
  //        type jt:unreadable;
  //      }
  //      leaf passive {
  //        description "Do not handle PAP authentication requests";
  //        type empty;
  //      }
  //    }
  //    leaf-list authentication {
  //      ordered-by user;
  //      description "Order in which PPP authentication protocols are negotiated";
  //      type enumeration {
  //        enum "pap" {
  //          description "Password Authentication Protocol";
  //        }
  //        enum "chap" {
  //          description "Challenge Handshake Authentication Protocol";
  //        }
  //      }
  //    }
  //    container compression {
  //      description "Set compression options";
  //      leaf acfc {
  //        description "Negotiate Address/Control field compression";
  //        type empty;
  //      }
  //      leaf pfc {
  //        description "Negotiate Protocol field compression";
  //        type empty;
  //      }
  //    }
  //    leaf lcp-restart-timer {
  //      description "LCP restart timer";
  //      units "milliseconds";
  //      type union {
  //        type string {
  //          pattern "<.*>|$.*";
  //        }
  //        type uint16 {
  //          range "20 .. 10000";
  //        }
  //      }
  //    }
  //    leaf ncp-restart-timer {
  //      description "NCP restart timer";
  //      units "milliseconds";
  //      type union {
  //        type string {
  //          pattern "<.*>|$.*";
  //        }
  //        type uint16 {
  //          range "500 .. 10000";
  //        }
  //      }
  //    }
  //    leaf no-termination-request {
  //      description "Don't send PPP termination requests";
  //      type empty;
  //    }
  //    leaf loopback-clear-timer {
  //      description "Loopback clear timer";
  //      units "seconds";
  //      type union {
  //        type string {
  //          pattern "<.*>|$.*";
  //        }
  //        type uint8 {
  //          range "1 .. 60";
  //        }
  //      }
  //    }
  //    leaf lcp-max-conf-req {
  //      description "Maximum LCP Conf-Req to be sent, 0 means infinite";
  //      type union {
  //        type string {
  //          pattern "<.*>|$.*";
  //        }
  //        type uint32 {
  //          range "0 .. 65535";
  //        }
  //      }
  //    }
  //    leaf ncp-max-conf-req {
  //      description "Maximum NCP Conf-Req to be sent, 0 means infinite";
  //      type union {
  //        type string {
  //          pattern "<.*>|$.*";
  //        }
  //        type uint32 {
  //          range "0 .. 65535";
  //        }
  //      }
  //    }
  //    leaf on-demand-ip-address {
  //      description "Enable On-Demand IPv4 address allocation and de-allocation";
  //      type empty;
  //    }
  //    leaf aaa-options {
  //      description "Attach AAA options name to dynamic-profile";
  //      type string {
  //        length "1 .. 63";
  //      }
  //    }
  //    container initiate-ncp {
  //      description "Enable server initiated NCP";
  //      // uses apply-advanced;
  //      leaf ip {
  //        description "Enable server initiated IPNCP";
  //        type empty;
  //      }
  //      leaf ipv6 {
  //        description "Enable server initiated IPv6NCP";
  //        type empty;
  //      }
  //      leaf dual-stack-passive {
  //        description "Disable server initiated IPNCP/IPv6NCP for dual-stack client";
  //        type empty;
  //      }
  //    }
  //    leaf mru {
  //      description "The Maximum Receive Unit size in bytes";
  //      type union {
  //        type string {
  //          pattern "<.*>|$.*";
  //        }
  //        type uint32 {
  //          range "64 .. 9192";
  //        }
  //      }
  //    }
  //    leaf mtu {
  //      description "The Maximum Transfer Unit size in bytes";
  //      type string;
  //    }
  //    leaf peer-ip-address-optional {
  //      description "Set Peer IP Address Optional in IP NCP Negotiations";
  //      type empty;
  //    }
  //    leaf ipcp-suggest-dns-option {
  //      description "Suggest peer to negotiate with DNS Addresses options";
  //      type empty;
  //    }
  //    leaf ignore-magic-number-mismatch {
  //      description "Ignore magic-number validation failure in LCP keepalive";
  //      type empty;
  //    }
  //    container local-authentication {
  //      description "Local Authentication Protocol options";
  //      uses local_auth_type;
  //    }
  //    leaf lcp-connection-update {
  //      description "Enable LCP connection update request to peer";
  //      type empty;
  //    }
  //  }
  //  grouping local_auth_type {
  //    description "Local authentication";
  //    // uses apply-advanced;
  //    leaf password {
  //      description "Username password";
  //      type string {
  //        length "1 .. 64";
  //      }
  //    }
  //    container username-include {
  //      description "Add username options";
  //      // uses apply-advanced;
  //      leaf mac-address {
  //        description "Include MAC address";
  //        type empty;
  //      }
  //      leaf circuit-id {
  //        description "Include circuit-id ";
  //        type empty;
  //      }
  //      leaf remote-id {
  //        description "Include remote-id ";
  //        type empty;
  //      }
  //      leaf domain-name {
  //        description "Domain name";
  //        type string {
  //          length "1 .. 64";
  //        }
  //      }
  //      leaf delimiter {
  //        description "Delimiter/separator character";
  //        type string {
  //          length 1;
  //        }
  //      }
  //    }
  //  }
  //  grouping pppoe_options_type {
  //    // uses apply-advanced;
  //    leaf underlying-interface {
  //      description "Underlying interface name";
  //      type string;
  //    }
  //    leaf idle-timeout {
  //      description "Time for which session can be idle (0 = forever)";
  //      units "seconds";
  //      type union {
  //        type string {
  //          pattern "<.*>|$.*";
  //        }
  //        type uint32 {
  //          range "0 .. 4294967295";
  //        }
  //      }
  //    }
  //    leaf access-concentrator {
  //      description "Name of the access concentrator (PPPoE server)";
  //      type string;
  //    }
  //    leaf service-name {
  //      description "Service to be requested (from PPPoE server)";
  //      type string;
  //    }
  //    leaf auto-reconnect {
  //      description "Time to reconnect after session terminates (0 = never)";
  //      units "seconds";
  //      type union {
  //        type string {
  //          pattern "<.*>|$.*";
  //        }
  //        type uint32 {
  //          range "0 .. 4294967295";
  //        }
  //      }
  //    }
  //    choice pppoe-mode {
  //      case case_1 {
  //        leaf server {
  //          description "PPPoE operates in server mode";
  //          type empty;
  //        }
  //      }
  //      case case_2 {
  //        leaf client {
  //          description "PPPoE operates in client mode";
  //          type empty;
  //        }
  //      }
  //    }
  //    leaf ppp-max-payload {
  //      description "Specify the value of ppp-max-payload tag";
  //      type union {
  //        type string {
  //          pattern "<.*>|$.*";
  //        }
  //        type uint32 {
  //          range "1492 .. 9192";
  //        }
  //      }
  //    }
  //  }
  //  grouping pppoe_underlying_options_type {
  //    // uses apply-advanced;
  //    leaf access-concentrator {
  //      description "Name of the access concentrator (PPPoE server)";
  //      type string {
  //        length "1 .. 64";
  //      }
  //    }
  //    leaf direct-connect {
  //      description "Ignore received VS tags for PPPoE sessions";
  //      type empty;
  //    }
  //    leaf duplicate-protection {
  //      description "Disallow multiple PPPoE sessions to a single client";
  //      type empty;
  //    }
  //    leaf dynamic-profile {
  //      description "Attach dynamic-profile to interface";
  //      type string {
  //        length "1 .. 64";
  //      }
  //    }
  //    leaf max-sessions {
  //      description "Maximum number of PPPoE sessions allowed on underlying interface";
  //      type union {
  //        type string {
  //          pattern "<.*>|$.*";
  //        }
  //        type uint32;
  //      }
  //    }
  //    leaf max-sessions-vsa-ignore {
  //      description "Ignore the max-sessions VSA";
  //      type empty;
  //    }
  //    leaf service-name-table {
  //      description "Attach Service Name Table to interface";
  //      type string {
  //        length "1 .. 32";
  //      }
  //    }
  //    container short-cycle-protection {
  //      presence "enable short-cycle-protection";
  //      description "Enable short cycle protection on underlying interface";
  //      // uses apply-advanced;
  //      leaf lockout-time-min {
  //        description "Minimum lockout time";
  //        units "seconds";
  //        type union {
  //          type string {
  //            pattern "<.*>|$.*";
  //          }
  //          type uint32 {
  //            range "1 .. 86400";
  //          }
  //        }
  //      }
  //      leaf lockout-time-max {
  //        description "Maximum lockout time";
  //        units "seconds";
  //        type union {
  //          type string {
  //            pattern "<.*>|$.*";
  //          }
  //          type uint32 {
  //            range "1 .. 86400";
  //          }
  //        }
  //      }
  //      leaf filter {
  //        description "Granularity of blocking filter";
  //        type enumeration {
  //          enum "aci" {
  //            description "Block by Agent Circuit ID";
  //          }
  //        }
  //      }
  //    }
  //  }
  //  grouping prbs-config {
  //    description "Configuration of pseudorandom binary sequence test signal";
  //    // uses apply-advanced;
  //    choice enable-prbs-choice {
  //      leaf enable-prbs {
  //        description "Enable PRBS test pattern generation and monitoring";
  //        type empty;
  //      }
  //      leaf no-enable-prbs {
  //        description "Don't enable PRBS test pattern generation and monitoring";
  //        type empty;
  //      }
  //    }
  //    leaf direction {
  //      description "Direction of generated and received PRBS test signal";
  //      default "line";
  //      type enumeration {
  //        enum "local" {
  //          description "Test signal generated towards and received from host-side";
  //        }
  //        enum "line" {
  //          description "Test signal generated towards and received from network-side";
  //        }
  //      }
  //    }
  //    leaf pattern {
  //      description "Pattern to use for PRBS test signal";
  //      default "prbs-31";
  //      type enumeration {
  //        enum "prbs-31" {
  //          description "2^31 polynomial PRBS test signal, as per G.709";
  //        }
  //        enum "prbs-23" {
  //          description "2^23 polynomial PRBS test signal, SONET/SDH framed";
  //        }
  //        enum "prbs-15" {
  //          description "2^15 polynomial PRBS test signal";
  //        }
  //        enum "prbs-7" {
  //          description "2^7 polynomial PRBS test signal";
  //        }
  //      }
  //    }
  //    choice invert-choice {
  //      leaf invert {
  //        description "Invert the test pattern";
  //        type empty;
  //      }
  //      leaf no-invert {
  //        description "Don't invert the test pattern";
  //        type empty;
  //      }
  //    }
  //  }
  //  grouping radius_options_vlan_type {
  //    // uses apply-advanced;
  //    list nas-port-options {
  //      key name;
  //      ordered-by user;
  //      description "Attach NAS Port options to VLAN/SVLAN ranges";
  //      max-elements 16;
  //      leaf name {
  //        description "Profile name";
  //        type string;
  //      }
  //      // uses apply-advanced;
  //      leaf nas-port-type {
  //        description "Configure NAS port type";
  //        type string;
  //      }
  //      container nas-port-extended-format {
  //        description "Configure NAS port format";
  //        // uses apply-advanced;
  //        leaf ae-width {
  //          description "Number of bits for the  aggregated ethernet identifier field";
  //          units "bits";
  //          type union {
  //            type string {
  //              pattern "<.*>|$.*";
  //            }
  //            type uint32 {
  //              range "0 .. 32";
  //            }
  //          }
  //        }
  //        leaf slot {
  //          description "Value to write to the slot field";
  //          type union {
  //            type string {
  //              pattern "<.*>|$.*";
  //            }
  //            type uint32 {
  //              range "0 .. 255";
  //            }
  //          }
  //        }
  //        leaf slot-width {
  //          description "Number of bits for the slot field";
  //          units "bits";
  //          type union {
  //            type string {
  //              pattern "<.*>|$.*";
  //            }
  //            type uint32 {
  //              range "0 .. 32";
  //            }
  //          }
  //        }
  //        leaf adapter {
  //          description "Value to write to the adapter field";
  //          type union {
  //            type string {
  //              pattern "<.*>|$.*";
  //            }
  //            type uint32 {
  //              range "0 .. 255";
  //            }
  //          }
  //        }
  //        leaf adapter-width {
  //          description "Number of bits for the adapter field";
  //          units "bits";
  //          type union {
  //            type string {
  //              pattern "<.*>|$.*";
  //            }
  //            type uint32 {
  //              range "0 .. 32";
  //            }
  //          }
  //        }
  //        leaf port {
  //          description "Value to write to the port field";
  //          type union {
  //            type string {
  //              pattern "<.*>|$.*";
  //            }
  //            type uint32 {
  //              range "0 .. 255";
  //            }
  //          }
  //        }
  //        leaf port-width {
  //          description "Number of bits for the port field";
  //          units "bits";
  //          type union {
  //            type string {
  //              pattern "<.*>|$.*";
  //            }
  //            type uint32 {
  //              range "0 .. 32";
  //            }
  //          }
  //        }
  //        leaf pw-width {
  //          description "Number of bits for the pseudo-wire field";
  //          units "bits";
  //          type union {
  //            type string {
  //              pattern "<.*>|$.*";
  //            }
  //            type uint32 {
  //              range "0 .. 32";
  //            }
  //          }
  //        }
  //        leaf stacked-vlan-width {
  //          description "Number of bits for the S-VLAN subinterface field";
  //          units "bits";
  //          type union {
  //            type string {
  //              pattern "<.*>|$.*";
  //            }
  //            type uint32 {
  //              range "0 .. 32";
  //            }
  //          }
  //        }
  //        leaf vlan-width {
  //          description "Number of bits for the VLAN subinterface field";
  //          units "bits";
  //          type union {
  //            type string {
  //              pattern "<.*>|$.*";
  //            }
  //            type uint32 {
  //              range "0 .. 32";
  //            }
  //          }
  //        }
  //        leaf stacked {
  //          description "Include the S-VLAN ID for subscribers on interfaces";
  //          type empty;
  //        }
  //        leaf vpi-width {
  //          description "Number of bits for the ATM VPI field";
  //          units "bits";
  //          type union {
  //            type string {
  //              pattern "<.*>|$.*";
  //            }
  //            type uint32 {
  //              range "0 .. 32";
  //            }
  //          }
  //        }
  //        leaf vci-width {
  //          description "Number of bits for the ATM VCI field";
  //          units "bits";
  //          type union {
  //            type string {
  //              pattern "<.*>|$.*";
  //            }
  //            type uint32 {
  //              range "0 .. 32";
  //            }
  //          }
  //        }
  //      }
  //      list stacked-vlan-ranges {
  //        key name;
  //        ordered-by user;
  //        description "Configure interface based on stacked-vlan range";
  //        leaf name {
  //          description "SVLAN range: [any | <low-tag>-<high-tag>],[any | <low-tag>-<high-tag>]";
  //          type string {
  //          }
  //        }
  //        // uses apply-advanced;
  //      }
  //      list vlan-ranges {
  //        key name;
  //        ordered-by user;
  //        description "Configure interface based on vlan range";
  //        leaf name {
  //          description "VLAN range: [any | <low-tag>-<high-tag>]";
  //          type string {
  //          }
  //        }
  //        // uses apply-advanced;
  //      }
  //    }
  //  }
  //  grouping sonet_options_type {
  //    // uses apply-advanced;
  //    leaf vtmapping {
  //      description "VT mapping mode";
  //      type enumeration {
  //        enum "klm" {
  //          description "KLM mode";
  //        }
  //        enum "itu-t" {
  //          description "ITU-T mode";
  //        }
  //      }
  //    }
  //    leaf fcs {
  //      description "Frame checksum";
  //      type enumeration {
  //        enum "32" {
  //          description "32-bit mode";
  //        }
  //        enum "16" {
  //          description "16-bit mode";
  //        }
  //      }
  //    }
  //    leaf path-trace {
  //      description "Path trace string";
  //      type string;
  //    }
  //    leaf loopback {
  //      description "Loopback mode";
  //      type enumeration {
  //        enum "local" {
  //          description "Local loopback";
  //        }
  //        enum "remote" {
  //          description "Remote loopback";
  //        }
  //      }
  //    }
  //    container trigger {
  //      description "Defect triggers";
  //      // uses apply-advanced;
  //      container lol {
  //        description "LOL defect trigger";
  //        choice lol_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container pll {
  //        description "PLL defect trigger";
  //        choice pll_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container lof {
  //        description "LOF defect trigger";
  //        choice lof_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container los {
  //        description "LOS defect trigger";
  //        choice los_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container ais-l {
  //        description "AIS-L defect trigger";
  //        choice ais_l_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container rfi-l {
  //        description "RFI-L defect trigger";
  //        choice rfi_l_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container ber-sd {
  //        description "BER-SD defect trigger";
  //        // uses apply-advanced;
  //        choice ber_sd_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container ber-sf {
  //        description "BER-SF defect trigger";
  //        // uses apply-advanced;
  //        choice ber_sf_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container ais-p {
  //        description "AIS-P defect trigger";
  //        choice ais_p_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container lop-p {
  //        description "LOP-P defect trigger";
  //        choice lop_p_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container rfi-p {
  //        description "RFI-P defect trigger";
  //        choice rfi_p_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container uneq-p {
  //        description "UNEQ-P defect trigger";
  //        choice uneq_p_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container plm-p {
  //        description "PLM-P defect trigger";
  //        choice plm_p_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container locd {
  //        description "LOCD defect trigger (ATM only)";
  //        choice locd_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //      container lcdp {
  //        description "LCD-P defect trigger (Ethernet WAN only)";
  //        choice lcdp_choices {
  //          case case_1 {
  //            leaf ignore {
  //              description "Ignore the defect";
  //              type empty;
  //            }
  //          }
  //          case case_2 {
  //            container hold-time {
  //              description "Delay before marking interface up or down for defect";
  //              leaf up {
  //                description "Delay before marking interface up when defect is absent";
  //                units "milliseconds";
  //                type union {
  //                  type string {
  //                    pattern "<.*>|$.*";
  //                  }
  //                  type uint32 {
  //                    range "1 .. 65534";
  //                  }
  //                }
  //              }
  //              leaf down {
  //                description "Delay before marking interface down when defect occurs";
  //                units "milliseconds";
  //                type union {
  //                  type string {
  //                    pattern "<.*>|$.*";
  //                  }
  //                  type uint32 {
  //                    range "1 .. 65534";
  //                  }
  //                }
  //              }
  //            }
  //          }
  //        }
  //      }
  //    }
  //    container aps {
  //      description "Automatic Protection Switching";
  //      uses aps_type;
  //    }
  //    choice payload_scrambler_choices {
  //      case case_1 {
  //        container payload-scrambler {
  //          presence "enable payload-scrambler";
  //          description "Enable payload scrambling";
  //          choice payload-choice {
  //          }
  //        }
  //      }
  //      case case_2 {
  //        leaf no-payload-scrambler {
  //          description "Do not enable payload scrambling";
  //          type empty;
  //        }
  //      }
  //    }
  //    choice z0-increment-choice {
  //      leaf z0-increment {
  //        description "Increment Z0 in SDH mode";
  //        type empty;
  //      }
  //      leaf no-z0-increment {
  //        description "Don't increment Z0 in SDH mode";
  //        type empty;
  //      }
  //    }
  //    choice loop-timing-choice {
  //      leaf loop-timing {
  //        description "Set loop timing for STM-1";
  //        type empty;
  //      }
  //      leaf no-loop-timing {
  //        description "Don't set loop timing for STM-1";
  //        type empty;
  //      }
  //    }
  //    container bytes {
  //      description "Set SONET header bytes";
  //      // uses apply-advanced;
  //      leaf e1-quiet {
  //        description "E1-quiet value";
  //        type union {
  //          type string {
  //            pattern "<.*>|$.*";
  //          }
  //          type uint32 {
  //            range "0 .. 255";
  //          }
  //        }
  //      }
  //      leaf f1 {
  //        description "F1 user value";
  //        type union {
  //          type string {
  //            pattern "<.*>|$.*";
  //          }
  //          type uint32 {
  //            range "0 .. 255";
  //          }
  //        }
  //      }
  //      leaf f2 {
  //        description "F2 user value";
  //        type union {
  //          type string {
  //            pattern "<.*>|$.*";
  //          }
  //          type uint32 {
  //            range "0 .. 255";
  //          }
  //        }
  //      }
  //      leaf s1 {
  //        description "S1/Z1 value (stratum clock by convention)";
  //        type union {
  //          type string {
  //            pattern "<.*>|$.*";
  //          }
  //          type uint32 {
  //            range "0 .. 255";
  //          }
  //        }
  //      }
  //      leaf z3 {
  //        description "Z3 user value";
  //        type union {
  //          type string {
  //            pattern "<.*>|$.*";
  //          }
  //          type uint32 {
  //            range "0 .. 255";
  //          }
  //        }
  //      }
  //      leaf z4 {
  //        description "Z4 user value";
  //        type union {
  //          type string {
  //            pattern "<.*>|$.*";
  //          }
  //          type uint32 {
  //            range "0 .. 255";
  //          }
  //        }
  //      }
  //      leaf c2 {
  //        description "C2 user value";
  //        type union {
  //          type string {
  //            pattern "<.*>|$.*";
  //          }
  //          type uint32 {
  //            range "0 .. 255";
  //          }
  //        }
  //      }
  //    }
  //    leaf rfc-2615 {
  //      description "RFC 2615 compliance";
  //      type empty;
  //    }
  //    leaf aggregate {
  //      description "Join a SONET aggregate";
  //      type union {
  //        type jt:interface-device;
  //        type string {
  //          pattern "<.*>|$.*";
  //        }
  //      }
  //    }
  //    container mpls {
  //      description "MPLS options";
  //      uses mpls_ifd_options;
  //    }
  //  }
  //  grouping tdm_options_type {
  //    // uses apply-advanced;
  //    leaf sfp-type {
  //      description "Smart SFP type";
  //      type enumeration {
  //        enum "T1" {
  //          description "T1 smart SFP";
  //        }
  //        enum "E1" {
  //          description "E1 smart SFP";
  //        }
  //        enum "DS3" {
  //          description "DS3 smart SFP";
  //        }
  //        enum "STM1" {
  //          description "STM1 smart SFP";
  //        }
  //        enum "STM4" {
  //          description "STM4 smart SFP";
  //        }
  //        enum "STM16" {
  //          description "STM16 smart SFP";
  //        }
  //      }
  //    }
  //    leaf tdm-in-loop {
  //      description "Configure port in TDM IN-LOOP mode";
  //      type empty;
  //    }
  //    leaf tdm-out-loop {
  //      description "Configure port in TDM OUT-LOOP mode";
  //      type empty;
  //    }
  //    leaf ces-psn-port-dmac-check-enable {
  //      description "Enable DMAC check on smart SFP";
  //      type empty;
  //    }
  //    container iwf-params {
  //      description "TDM interworking functionality (IWF) parameters";
  //      // uses apply-advanced;
  //      leaf decap-ecid {
  //        description "ECID for decapsulation";
  //        type union {
  //          type string {
  //            pattern "<.*>|$.*";
  //          }
  //          type uint32 {
  //            range "0 .. 1048575";
  //          }
  //        }
  //      }
  //      leaf encap-ecid {
  //        description "ECID for encapsulation";
  //        type union {
  //          type string {
  //            pattern "<.*>|$.*";
  //          }
  //          type uint32 {
  //            range "0 .. 1048575";
  //          }
  //        }
  //      }
  //    }
  //    container ces-psn-channel {
  //      description "CES PSN channel parameters";
  //      // uses apply-advanced;
  //      leaf dmac-address {
  //        description "Destination MAC-address to be paired with the Smart SFP";
  //        type jt:mac-addr;
  //      }
  //      leaf mode {
  //        description "PSN encapsulation mode";
  //        type enumeration {
  //          enum "MEF8" {
  //            description "MEF8 encapsulation";
  //          }
  //          enum "MPLS" {
  //            description "MPLS Encapsulation";
  //          }
  //        }
  //      }
  //      leaf vlan-id-1 {
  //        description "VLAN ID for encapsulation";
  //        type union {
  //          type string {
  //            pattern "<.*>|$.*";
  //          }
  //          type uint32 {
  //            range "0 .. 4094";
  //          }
  //        }
  //      }
  //      leaf vlan-id-2 {
  //        description "Outer VLAN ID for encapsulation";
  //        type union {
  //          type string {
  //            pattern "<.*>|$.*";
  //          }
  //          type uint32 {
  //            range "0 .. 4094";
  //          }
  //        }
  //      }
  //    }
  //  }
  //  grouping vlan_map {
  //    description "IEEE 802.1q Virtual LAN (VLAN) Tag mapping";
  //    // uses apply-advanced;
  //    choice operation_choices {
  //      case case_1 {
  //        leaf push {
  //          description "Push a VLAN tag";
  //          type empty;
  //        }
  //      }
  //      case case_2 {
  //        leaf swap {
  //          description "Swap a VLAN tag";
  //          type empty;
  //        }
  //      }
  //      case case_3 {
  //        leaf pop {
  //          description "Pop a VLAN tag";
  //          type empty;
  //        }
  //      }
  //      case case_4 {
  //        leaf push-push {
  //          description "Push two VLAN tags";
  //          type empty;
  //        }
  //      }
  //      case case_5 {
  //        leaf swap-push {
  //          description "Swap VLAN tag and push a new VLAN tag";
  //          type empty;
  //        }
  //      }
  //      case case_6 {
  //        leaf swap-swap {
  //          description "Swap both outer and inner VLAN tags";
  //          type empty;
  //        }
  //      }
  //      case case_7 {
  //        leaf pop-swap {
  //          description "Pop outer VLAN tag and swap inner VLAN tag";
  //          type empty;
  //        }
  //      }
  //      case case_8 {
  //        leaf pop-pop {
  //          description "Pop both outer and inner VLAN tags";
  //          type empty;
  //        }
  //      }
  //    }
  //    leaf tag-protocol-id {
  //      description "IEEE 802.1q Tag Protocol Identifier to rewrite";
  //      type string {
  //      }
  //    }
  //    leaf inner-tag-protocol-id {
  //      description "IEEE 802.1q Tag Protocol ID to rewrite for inner tag";
  //      type string;
  //    }
  //    leaf vlan-id {
  //      description "VLAN ID to rewrite";
  //      type string;
  //    }
  //    leaf inner-vlan-id {
  //      description "VLAN ID to rewrite for inner tag";
  //      type string;
  //    }
  //  }
   grouping vrrp-group {
     description "Virtual Router Redundancy Protocol group";
     leaf name {
       description "Identifier for VRRP group";
       type union {
         type string {
           pattern "<.*>|$.*";
         }
         type uint32 {
           range "0 .. 255";
         }
       }
     }
     // uses apply-advanced;
     choice address {
       case case_1 {
         leaf-list virtual-address {
           ordered-by user;
           description "One or more virtual IPv4 addresses";
           type jt:ipv4addr;
         }
       }
       case case_2 {
         leaf-list virtual-inet6-address {
           ordered-by user;
           description "One or more virtual inet6 addresses";
           type jt:ipv6addr;
         }
       }
     }
     leaf virtual-link-local-address {
       description "Virtual link-local addresses";
       type jt:ipv6addr;
     }
     leaf priority {
       description "Virtual router election priority";
       type union {
         type string {
           pattern "<.*>|$.*";
         }
         type uint32 {
           range "0 .. 255";
         }
       }
     }
    //  leaf preferred {
    //    description "Preferred group on subnet";
    //    type empty;
    //  }
    //  choice advertisement_type {
    //    case case_1 {
    //      leaf advertise-interval {
    //        description "Advertisement interval";
    //        units "seconds";
    //        type union {
    //          type string {
    //            pattern "<.*>|$.*";
    //          }
    //          type uint32 {
    //            range "1 .. 255";
    //          }
    //        }
    //      }
    //    }
    //    case case_2 {
    //      leaf fast-interval {
    //        description "Fast advertisement interval";
    //        units "milliseconds";
    //        type union {
    //          type string {
    //            pattern "<.*>|$.*";
    //          }
    //          type uint32 {
    //            range "10 .. 40950";
    //          }
    //        }
    //      }
    //    }
    //    case case_3 {
    //      leaf inet6-advertise-interval {
    //        description "Inet6 advertisement interval";
    //        units "milliseconds";
    //        type union {
    //          type string {
    //            pattern "<.*>|$.*";
    //          }
    //          type uint32 {
    //            range "100 .. 40000";
    //          }
    //        }
    //      }
    //    }
    //  }
    //  choice preempt_type {
    //    case case_1 {
    //      container preempt {
    //        presence "enable preempt";
    //        description "Allow preemption";
    //        // uses apply-advanced;
    //        leaf hold-time {
    //          description "Preemption hold time";
    //          units "seconds";
    //          type union {
    //            type string {
    //              pattern "<.*>|$.*";
    //            }
    //            type uint32 {
    //              range "0 .. 3600";
    //            }
    //          }
    //        }
    //      }
    //    }
    //    case case_2 {
    //      leaf no-preempt {
    //        description "Don't allow preemption";
    //        type empty;
    //      }
    //    }
    //  }
    //  choice accept_type {
    //    case case_1 {
    //      leaf accept-data {
    //        description "Accept packets destined for virtual IP address";
    //        type empty;
    //      }
    //    }
    //    case case_2 {
    //      leaf no-accept-data {
    //        description "Don't accept packets destined for virtual IP address";
    //        type empty;
    //      }
    //    }
    //  }
    //  leaf authentication-type {
    //    description "Authentication type";
    //    type enumeration {
    //      enum "md5" {
    //        description "HMAC-MD5-96";
    //      }
    //      enum "simple" {
    //        description "Simple password";
    //      }
    //    }
    //  }
    //  leaf authentication-key {
    //    description "Authentication key";
    //    type jt:unreadable;
    //  }
    //  container track {
    //    description "Interfaces to track for VRRP group";
    //    // uses apply-advanced;
    //    leaf priority-hold-time {
    //      description "Priority hold time";
    //      units "seconds";
    //      type union {
    //        type string {
    //          pattern "<.*>|$.*";
    //        }
    //        type uint32 {
    //          range "0 .. 3600";
    //        }
    //      }
    //    }
    //    list interface {
    //      key name;
    //      ordered-by user;
    //      description "Interface to track in VRRP group";
    //      leaf name {
    //        description "Name of interface";
    //        type union {
    //          type jt:interface-unit;
    //          type string {
    //            pattern "<.*>|$.*";
    //          }
    //        }
    //      }
    //      // uses apply-advanced;
    //      list bandwidth-threshold {
    //        key name;
    //        description "Track bandwidth of interface";
    //        leaf name {
    //          description "Interface speed below which priority cost is incurred";
    //          units "bits per second";
    //          type string;
    //        }
    //        leaf priority-cost {
    //          description "Value subtracted from priority when bandwidth is below threshold";
    //          type union {
    //            type string {
    //              pattern "<.*>|$.*";
    //            }
    //            type uint32 {
    //              range "1 .. 254";
    //            }
    //          }
    //        }
    //      }
    //      leaf priority-cost {
    //        description "Value to subtract from priority when interface is down";
    //        type union {
    //          type string {
    //            pattern "<.*>|$.*";
    //          }
    //          type uint32 {
    //            range "1 .. 254";
    //          }
    //        }
    //      }
    //    }
    //    list route {
    //      key "route_address routing-instance";
    //      ordered-by user;
    //      description "Route to track in VRRP group";
    //      leaf route_address {
    //        description "Route address";
    //        type jt:ipprefix-mandatory;
    //      }
    //      leaf routing-instance {
    //        description "Routing instance to which route belongs, or 'default'";
    //        type string {
    //        }
    //      }
    //      leaf priority-cost {
    //        description "Value to subtract from priority when route is down";
    //        type union {
    //          type string {
    //            pattern "<.*>|$.*";
    //          }
    //          type uint32 {
    //            range "1 .. 254";
    //          }
    //        }
    //      }
    //    }
    //  }
     container vrrp-inherit-from {
       description "VRRP group to follow for this VRRP group";
       // uses apply-advanced;
       leaf active-interface {
         description "Interface name of VRRP active group";
         type union {
           type jt:interface-unit;
           type string {
             pattern "<.*>|$.*";
           }
         }
       }
       leaf active-group {
         description "Identifier for VRRP active group";
         type union {
           type string {
             pattern "<.*>|$.*";
           }
           type uint32 {
             range "0 .. 255";
           }
         }
       }
     }
    //  leaf advertisements-threshold {
    //    description "Number of vrrp advertisements missed before declaring master down";
    //    type union {
    //      type string {
    //        pattern "<.*>|$.*";
    //      }
    //      type uint32 {
    //        range "1 .. 15";
    //      }
    //    }
    //  }
   }
 }
